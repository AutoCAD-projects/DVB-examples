Attribute VB_Name = "Module1"
'  ad_Utility
'
'  This file contains all non-dialog based VBA macros so you can reference
'     a single file for several routines.
'  All macros were developed in AutoCAD 2000.
'  Each routine includes a demand load line for macros.
'
'  12/1/2001 - Added 'ad_PlotToFile' & 'ad_PlotToFolder'
'
'  This file contains 32 macros:
'    ad_AcadDate         ad_AddDimStyle       ad_AddMenuItems
'    ad_AddWord          ad_CloseAllDrawings  ad_ColorToLayer
'    ad_CrossHairToggle  ad_DeleteBlankText   ad_DwgDate
'    ad_DwgList          ad_DwgVer            ad_FixBlocks
'    ad_FixPlotStyles    ad_FreezeAll         ad_FreezePick
'    ad_GraphScrColor    ad_LayoutLimits      ad_LoadProfile
'    ad_MatchLayer       ad_MatchProps        ad_OutlookOpenDwg
'    ad_OutlookCloseDwg  ad_PageLayout        ad_PlotLayouts
'    ad_PlotToFile       ad_PlotToFolder      ad_SaveProfile
'    ad_ScreenMenu       ad_SwapProfiles      ad_ThawAll
'    ad_TotalLines       ad_ToUpper           ad_VerifyDims
'    ad_VerifyDimsResetColor
'
'  Copyright©2001 ActiveDwg.com
'
'  These routines are provided for demonstration purposes only and must
'    not be used for critical applications without your verification
'    that these routines will perform as you intended.
'  These routines may be freely utilized for your own personal use so long
'    as the entire contents of this header remain intact.
'  These routines are provided "as-is" and no declaration, written or implied,
'    is made as to their reliability for any particular task. Any use of these
'    routines is solely at your own risk.
'
Option Explicit
Sub ad_AcadDate()
'  This routine demonstrates the retrieval and conversion of
'     drawing date information from the internal AutoCAD format
'     to Julian format and conversion of the elapsed timer.
'  Demand load:  -vbarun;ad_Utility.dvb!ad_AcadDate;
  Dim adDwgCreate As Date
  Dim adDwgUpdate As Date
  Dim adDwgEdit As Double
  Dim adDwgUsrTimer As Double
  
  adDwgCreate = ThisDrawing.GetVariable("TDCREATE") - 2415019
  adDwgUpdate = ThisDrawing.GetVariable("TDUPDATE") - 2415019
  adDwgEdit = ThisDrawing.GetVariable("TDINDWG")
  adDwgUsrTimer = ThisDrawing.GetVariable("TDUSRTIMER")
  
  adDwgEdit = adDwgEdit * 24
  adDwgUsrTimer = adDwgUsrTimer * 24
  
  adDwgEdit = Round(adDwgEdit, 2)
  adDwgUsrTimer = Round(adDwgUsrTimer, 2)
  
  MsgBox "Stats for " & ThisDrawing.Name & vbCrLf & _
         "Drawing Created " & adDwgCreate & vbCrLf & _
         "Drawing Last Updated " & adDwgUpdate & vbCrLf & _
         "Drawing Edit Time " & adDwgEdit & " hours" & vbCrLf & _
         "User Timer " & adDwgUsrTimer & " hours"
End Sub

Sub ad_AddDimStyle()
'  This routine demonstrates how to add a new dimension style and define
'    its various properties. We'll work on documenting all the system
'    variables in the near future. It was developed in AutoCAD 2000.
'Demand load:  -vbarun;ad_Utility.dvb!ad_AddDimStyle;
  Dim adDimStyle As AcadDimStyle

  Set adDimStyle = ThisDrawing.DimStyles.Add("adDimStyle")
  ThisDrawing.ActiveDimStyle = adDimStyle

  With ThisDrawing
  'The first group defines overall and linear scale factors
    .SetVariable "DimScale", 96    'Overall Scale Factor. Determined by 12/Scale Factor.
                                   '  96 is for 1/8"=1'-0" so that 12/.125=96.
    .SetVariable "DimLFac", 1      'Linear Scale Factor. '1'=1:1, '2'=2:1,'.5'=1:2, etc

  'This group defines the typical dimension properties
    .SetVariable "DimADec", 2      'Precision places for angular dimensions. May be 0-8.
    .SetVariable "DimAso", 1       'Dimensional associativity. 0=off, 1=on. 0 'explodes' dimensions.
                                   '  DimAso is stored by drawing, not by style.
    .SetVariable "DimASz", 0.09375 'Arrowhead size for dimensions and leaders.
    .SetVariable "DimAtFit", 1     'Defines placement of arrowheads and text if insufficient space for both.
                                   '  0=both outside, 1=force arrows outside, 2=force text outside, 3=best fit.
    .SetVariable "DimAUnit", 0     'Units for angular dimensions.
                                   '  0=decimal degrees, 1=degrees/minutes/seconds, 2=gradians, 3=radians
    .SetVariable "DimAZin", 0      'Zero suppression for angular dimensions.
                                   '  0=display all leading and trailing zeros, 1=suppress leading zeros,
                                   '  2=suppress trailing zeros, 3=suppress leading and trailing zeros
    .SetVariable "DimBlk", ""      'Defines typical arrow type. ' "" '=Closed-Filled, '.'=none.
                                   '  Others are:  '_ArchTick', '_BoxBlank', '_BoxFilled', '_Closed', '_ClosedBlank',
                                   '  '_DatumBlank', '_DatumFilled', '_Dot', '_DotSmall', '_DotBlank', '_Integral',
                                   '  '_None', '_Oblique', '_Origin', '_Origin2', '_Open', '_Open90', '_Open30', '_Small'.
    .SetVariable "DimBlk1", ""     'Defines 1st arrow type if 'DimSAH is '1'. See 'DimBlk' for type list.
    .SetVariable "DimBlk2", ""     'Defines 1st arrow type if 'DimSAH is '2'. See 'DimBlk' for type list.
    .SetVariable "DimCen", 0.09375 'Defines circle and arc center marks and lines. Show as mark size.
                                   '  0=No marks, <0=centerlines are drawn, >0=centermarks are drawn.
    .SetVariable "DimClrD", 256    'Color for dimlines, arrows, and leaders. 0=ByBlock, 256 = ByLayer, 1-255=color.
    .SetVariable "DimClrE", 256    'Color for dimension extension lines. 0=ByBlock, 256 = ByLayer, 1-255=color.
    .SetVariable "DimClrT", 256    'Color for dimension text. 0=ByBlock, 256 = ByLayer, 1-255=color.
    .SetVariable "DimDec", 4       'Decimal precision for normal dimensions.
    .SetVariable "DimDLE", 0       'For oblique marks in place of arrows: Distance dimlines extend beyond extension lines.
    .SetVariable "DimDLI", 0.3125  'Offset distance between dimension line rows.
    .SetVariable "DimDSep", "."    'Decimal separator for decimal format dimensions.
    .SetVariable "DimExe", 0.0625  'Extension distance of extension lines beyond dimension lines.
    .SetVariable "DimExO", 0.0625  'Offset distance from dimension origin to extension line.
    .SetVariable "DimFrac", 0      'Fraction format in fractional dimensions. 0=Horizontal, 1=diagonal, 2=not stacked.
    .SetVariable "DimGap", 0.015625 'Gap between dimlines and dimension text.
    .SetVariable "DimJust", 0      'Dimension text horizontal position. 0=Centered between extension lines,
                                   '  1=at 1st extension line, 2=at 2nd extension line, 3=above and at 1st extension line,
                                   '  4=above and at 2nd extension line.
    .SetVariable "DimLdrBlk", ""   'Defines leader arrow type. See DimBlk for type list.
    .SetVariable "DimLim", 0       'Defines whether dimension limits are generated. 1=On, 0=Off.
    .SetVariable "DimLUnit", 4     'Defines dimension unit types(except angular). 1=Scientific, 2=Decimal, 3=Engineering,
                                   '  4=Architectural, 5=Fractional, 6=Windows default
    .SetVariable "DimLwd", acLnWtByLayer 'Defines dimension line lineweight. 'ByBlock'=acLnWtByBlock, 'ByLayer'=acLnWtByLayer,
                                         '  also may be specified as millimeters.
    .SetVariable "DimLwe", acLnWtByLayer 'Defines extension line lineweight. 'ByBlock'=acLnWtByBlock, 'ByLayer'=acLnWtByLayer,
                                         '  also may be specified as millimeters.
    .SetVariable "DimPost", ""     'Defines dimension text prefix or suffix. Use brackets to specify prefix or suffix.
                                   '  '<>ft' will create a suffix of 'ft', while 'ft<>' will create a prefix of 'ft'.
    .SetVariable "DimRnd", 0       'Defines precision for rounding dimensions. '.5' will round to nearest half.
    .SetVariable "DimSAh", 0       'Defines arrowhead block display. 0=set per 'DIMBLK'(see 'DimLdrBlk' for list'),
                                   '  1=sets arrowhead 1('DIMBLK1') independently of arrowhead 2('DIMBLK2')(see 'DimLdrBlk' for list').
    .SetVariable "DimSD1", 0       'Defines display of 1st dimline and arrowhead. 0=Display, 1=Do not display.
    .SetVariable "DimSD2", 0       'Defines display of 2nd dimline and arrowhead. 0=Display, 1=Do not display.
    .SetVariable "DimSE1", 0       'Defines display of 1st extension line. 0=Display, 1=Do not display.
    .SetVariable "DimSE2", 0       'Defines display of 2nd extension line. 0=Display, 1=Do not display.
    .SetVariable "DimSho", 1       'Defines dynamic update of dimtext as defining points are dragged. 0=Update, 1=Do not update.
                                   '  DimSho is stored by drawing, not by style.
    .SetVariable "DimSOXD", 0      'Defines whether dimlines are drawn outside of extension lines.
                                   '  0=Drawn outside, 1=Not drawn outside.
    .SetVariable "DimTAD", 0       'Dimension text vertical position. 0=Centered between extension lines,
                                   '  1=above the dimension line, 2=dimensions placed on side of dimline away from defining points,
                                   '  3=placed according to Japanese Industrial Standards.
    .SetVariable "DimTIH", 0       'Defines position of dimtext between extension lines. 0=Align with dimline, 1=Always horizontal.
    .SetVariable "DimTIX", 0       'Defines how text is placed between extension lines. 0=Between if fits, 1=Always between.
    .SetVariable "DimTOFL", 0      'Defines how dimline is placed between extension lines. 0=In or out with arrowheads, 1=Always between.
    .SetVariable "DimTOH", 0       'Defines position of dimtext outside extension lines. 0=Align with dimline, 1=Always horizontal.
    .SetVariable "DimTSz", 0       'Defines size of Oblique strokes in place of arrowheads. 0=Draws arrowheads, >0=Oblique size.
    .SetVariable "DimTVP", 0
    .SetVariable "DimTxSty", "STANDARD"
    .SetVariable "DimTxt", 0.09375
    .SetVariable "DimUPT", 0
    .SetVariable "DimZIn", 0
  
  'This group defines the Alternate dimension properties
    .SetVariable "DimAlt", 0
    .SetVariable "DimAltD", 4
    .SetVariable "DimAltF", 25.4
    .SetVariable "DimAltRnd", 0
    .SetVariable "DimAltTD", 4
    .SetVariable "DimAltTZ", 0
    .SetVariable "DimAltU", 2
    .SetVariable "DimAltZ", 0
    .SetVariable "DimAPost", ""
  
  'This group defines the Tolerance dimension properties
    .SetVariable "DimTol", 0
    .SetVariable "DimTDec", 4
    .SetVariable "DimTFac", 1
    .SetVariable "DimTM", 0
    .SetVariable "DimTolJ", 1
    .SetVariable "DimTP", 0
    .SetVariable "DimTZin", 0
  End With
  adDimStyle.CopyFrom ThisDrawing
End Sub

Sub ad_AddMenuItems()
'  This routine demonstrates adding a new menu item in the 'Edit' pull-down
'     menu and adding a new toolbar and button.
'Demand load:  -vbarun;ad_Utility.dvb!ad_AddMenuItems;
    Dim objMenu As AcadPopupMenu
    Dim newMenuItem As AcadPopupMenuItem
    Dim MenuMacro As String
    Dim objToolbar As AcadToolbar
    Dim objToolbarButton As AcadToolbarItem
    Dim ButtonName As String
    Dim objMenuGroup As AcadMenuGroup
    Dim MenuName As String
    Dim SmallBitmap As String
    Dim LargeBitmap As String

'    On Error GoTo MENU_ERROR
    
'Create a menu item in the 'Edit' group
    Set objMenu = ThisDrawing.Application.MenuBar.Item("&Edit")
    MenuMacro = "Line "
    MenuName = "Acad"
    Set newMenuItem = objMenu.AddMenuItem(objMenu.Count + 1, "New Menu Item", MenuMacro)
 
'Create a toolbar and button
    ThisDrawing.Application.MenuGroups(MenuName).Toolbars.Add "MyToolBar"
    ButtonName = "MyButton"
    Set objToolbar = ThisDrawing.Application.MenuGroups(MenuName).Toolbars("MyToolBar")
    Set objToolbarButton = objToolbar.AddToolbarButton(1, "MyButton", "Draws a Line", MenuMacro)
 
'To add a bitmap to the new toolbar button, you need to have two icons available. One for
'  the small format is 16x16 pixels, and one for the large format is 32x32 pixels. They
'  should be available in AutoCAD's search path or you need to hard-wire the path.
'Also, be sure to uncomment these lines and the bitmap 'Dim' lines above.

   SmallBitmap = "FrzLayer.bmp"
   LargeBitmap = "Erase.bmp"
   objToolbarButton.SetBitmaps SmallBitmap, LargeBitmap

'Save the menu file
'    Set objMenuGroup = ThisDrawing.Application.MenuGroups(MenuName)
'    objMenuGroup.Save acMenuFileSource
    
    Exit Sub

MENU_ERROR:
    MsgBox Err.Description

End Sub
Sub ad_AddWord()
'  This routine demonstrates the insertion of new words into
'     an existing text string.
'  Demand load:  -vbarun;ad_Utility.dvb!ad_AddWord;
  Dim adTextObj As AcadObject
  Dim adBasePnt As Variant
  Dim adObjSel As Integer
  
  adObjSel = 1
  Do While adObjSel = 1
    On Error GoTo exitsub
    ThisDrawing.Utility.GetEntity adTextObj, adBasePnt, "Select Text to Update>> "
    If adTextObj.ObjectName = "AcDbText" Or adTextObj.ObjectName = "AcDbMText" Then
'This will preceed the line with 'Start ' and end it with ' End'
      adTextObj.TextString = "Start " & adTextObj.TextString & " End"
    End If
    adTextObj.Update
  Loop
exitsub:
End Sub

Sub ad_CloseAllDwgs()
'This routine closes all currently open drawings and saves them or not
'   according to user input.
'Demand load:  -vbarun;ad_Utility.dvb!ad_CloseAllDwgs;
    Dim Drawing As AcadDocument
    Dim StrMsg As String
    Dim StrTitle As String
    Dim Response

    If Documents.Count = 0 Then
        MsgBox "No drawings to close!"
        Exit Sub
    End If
    StrMsg = "Save all drawings before closing?"
    StrTitle = "Verify Close Mode"
    Response = MsgBox(StrMsg, vbYesNo, StrTitle)
    If Response = vbYes Then
        For Each Drawing In Documents
            Drawing.Close
        Next
    Else
        For Each Drawing In Documents
            Drawing.Close (False)
        Next
    End If
End Sub

Sub ad_ColorToLayer()
'  This routine places all objects on certain layers depending
'    on their 'hard-wired' color and then changes their color
'    to 'ByLayer'. Just insert your colors and target layers
'    into the code. We've used the color constants for the first
'    7 colors but you can also use a color number.
'Demand load:  -vbarun;ad_Utility.dvb!ad_ColorToLayer;
    Dim ent As AcadEntity
    On Error Resume Next
    For Each ent In ThisDrawing.ModelSpace
        Select Case ent.Color
            Case acRed         'Color #1, could also be input as: Case 1
                ent.Layer = "1"
                ent.Color = 256
                ent.Update
            Case acYellow      'Color #2
                ent.Layer = "2"
                ent.Color = 256
                ent.Update
            Case acGreen       'Color #3
                ent.Layer = "3"
                ent.Color = 256
                ent.Update
            Case acCyan        'Color #4
                ent.Layer = "4"
                ent.Color = 256
                ent.Update
            Case acBlue        'Color #5
                ent.Layer = "5"
                ent.Color = 256
                ent.Update
            Case acMagenta     'Color #6
                ent.Layer = "6"
                ent.Color = 256
                ent.Update
            Case acWhite       'Color #7
                ent.Layer = "7"
                ent.Color = 256
                ent.Update
        End Select
    Next ent
End Sub

Sub ad_CopyDim()
'  This routine copies a selected dimension's 'Measurement' property
'     to the Windows clipboard.
'Demand load:  -vbarun;ad_Utility.dvb!ad_CopyDim;
    Dim adDimension As AcadObject
    Dim DimtoCopy As DataObject
    Dim varPick As Variant
    
    With ThisDrawing.Utility
        .GetEntity adDimension, varPick, vbCr & "Pick a Dimension>> "
        If Err Then
            MsgBox "That is not an object"
            Exit Sub
        End If
    End With
    
    If adDimension.ObjectName = "AcDb2LineAngularDimension" Or _
        adDimension.ObjectName = "AcDb3PointAngularDimension" Or _
        adDimension.ObjectName = "AcDbAlignedDimension" Or _
        adDimension.ObjectName = "AcDbDiametricDimension" Or _
        adDimension.ObjectName = "AcDbOrdinateDimension" Or _
        adDimension.ObjectName = "AcDbRadialDimension" Or _
        adDimension.ObjectName = "AcDbRotatedDimension" Then
       
        If adDimension.Measurement <> "" Then
            Set DimtoCopy = New DataObject
            DimtoCopy.SetText adDimension.Measurement
            DimtoCopy.PutInClipboard
        End If
    End If
End Sub

Sub ad_CrossHairToggle()
'This routine toggles the display crosshair between 5% and 100%.
'Demand load:  -vbarun;ad_Utility.dvb!ad_CrossHairToggle;
    Dim PrefsDisplay As AcadPreferencesDisplay
    Set PrefsDisplay = ThisDrawing.Application.Preferences.Display
    If PrefsDisplay.CursorSize = 5 Then
        PrefsDisplay.CursorSize = 100
    Else: PrefsDisplay.CursorSize = 5
    End If
End Sub

Sub ad_DeleteBlankText()
'  This routine deletes all empty text and mtext entities in
'      modelspace.
'  Demand load:  -vbarun;ad_Utility.dvb!ad_DeleteBlankText;
    Dim adModelSS As AcadSelectionSet
    Dim adEnt As Object
    Dim itemCnt As Integer
    Set adModelSS = ThisDrawing.SelectionSets.Add("ModelSS")
    adModelSS.Clear
    adModelSS.Select (acSelectionSetAll)
    itemCnt = 0
    For Each adEnt In adModelSS
        If adEnt.ObjectName = "AcDbText" Or adEnt.ObjectName = "AcDbMtext" Then
            If adEnt.TextString = "" Then
                adEnt.Delete
                itemCnt = itemCnt + 1
            End If
        End If
    Next adEnt
    adModelSS.Delete
    ThisDrawing.Regen acAllViewports
    MsgBox itemCnt & " item(s) deleted."
End Sub

Sub ad_DwgDate()
'This routine inserts the current system date into the 'ad_DwgDate'
'  block on each layout of the current drawing. It uses the form
'  mm/dd/yy and is setup for paperspace.
'Demand load:  -vbarun;ad_Utility.dvb!ad_DwgDate;
    Dim DwgDate As Variant
    Dim DwgStr As Variant
    Dim PlotLayout As AcadLayout
    Dim CurrLayout As AcadLayout
    Dim PlotLayouts As AcadLayouts
    Dim ent As Object
    Dim BlockObjAttributes As Variant
    
    DwgDate = Date
    DwgStr = Format(DwgDate, "SHORT DATE")
    Set PlotLayouts = ThisDrawing.Layouts
    Set CurrLayout = ThisDrawing.ActiveLayout
    For Each PlotLayout In PlotLayouts
        ThisDrawing.ActiveLayout = PlotLayout
        If ThisDrawing.ActiveSpace = acPaperSpace Then
            For Each ent In ThisDrawing.PaperSpace
              If ent.EntityName = "AcDbBlockReference" Then
                If ent.Name = "ad_DwgDate" Then
                    BlockObjAttributes = ent.GetAttributes
                    BlockObjAttributes(0).TextString = DwgStr
                End If
              End If
            Next ent
        End If
    Next PlotLayout
    ThisDrawing.ActiveLayout = CurrLayout
End Sub

Sub ad_DwgList()
'  This routine creates a list of the currently open drawings
'     and writes them to the file "C:\adDwgList.txt". Each time
'     the routine is run, the file is overwritten.
'  Demand load:  -vbarun;ad_Utility.dvb!ad_DwgList;
  Dim adDwg As AcadDocument
  Dim adListFile As Integer
  Dim adList As String
  adList = ""
  For Each adDwg In Documents
    adList = adList & adDwg.Path & "\" & adDwg.Name & vbCrLf
  Next
  If Documents.Count > 0 Then
    adListFile = FreeFile()
    Open "C:/adDwgList.txt" For Binary As #adListFile
    Put #adListFile, , adList
  End If
  Close adListFile
End Sub

Public Sub ad_DwgVer()
'  This routine determines the AutoCAD version of the current drawing.
'  Demand load:  -vbarun;ad_Utility.dvb!ad_DwgVer;
   Dim DwgHeader As String * 6
   Dim DwgFile As Long
   DwgFile = FreeFile(0)
   Open ThisDrawing.FullName For Binary Access Read As #DwgFile
   Get #DwgFile, , DwgHeader
   Close #DwgFile
   Select Case DwgHeader
      Case "AC1015":
         MsgBox "Release 2000/2000i/2002"
      Case "AC1500":
         MsgBox "Internal - Version T"
      Case "AC1014":
         MsgBox "Release 14"
      Case "AC1013":
         MsgBox "Early Release 14"
      Case "AC1012":
         MsgBox "Release 13"
      Case "AC1011":
         MsgBox "Late Release 13"
      Case "AC1010":
         MsgBox "Early Release 13"
      Case "AC1009":
         MsgBox "Release 11/12"
      Case "AC1008":
         MsgBox "Internal - Late Z"
      Case "AC1007":
         MsgBox "Internal - Early Z"
      Case "AC1006":
         MsgBox "Release 10"
      Case "AC1005":
         MsgBox "Internal - Version Y"
      Case "AC1004":
         MsgBox "Release 9"
      Case "AC1003":
         MsgBox "Version 2.60"
      Case "AC1002":
         MsgBox "Version 2.50"
      Case "AC1001":
         MsgBox "Unix Version 2.22"
      Case "AC2.22":
         MsgBox "PC/MS-DOS Version 2.22"
      Case "AC2.21":
         MsgBox "Version 2.21"
      Case "AC2.20":
         MsgBox "Internal - Version 2.20"
      Case "AC2.10":
         MsgBox "Version 2.10"
      Case "AC1.50":
         MsgBox "Version 1.50"
      Case "AC1.40":
         MsgBox "Version 1.40"
      Case "AC1.2":
         MsgBox "Version 1.20"
      Case "MC0.0":
         MsgBox "Version 1.00"
      Case Else:
         MsgBox "Unknown Header"
   End Select
End Sub

Sub ad_FixBlocks()
'  This routine demonstrates the selective updating of particular
'     block attributes in a drawing.
'  Demand load:  -vbarun;ad_Utility.dvb!ad_FixBlocks;
  Dim adSS As AcadSelectionSet
  Dim adBlocktoFix As String
  Dim fType(0 To 1) As Integer, fData(0 To 1)
  Dim adDwgBlock As AcadBlockReference
  Dim adBlockAttributes As Variant
  Dim i As Integer
  On Error Resume Next
  adBlocktoFix = "Piece_Mark"  '<-- Your block name goes here
  Set adSS = objSelCol.Add("adSS")
  If Err Then Set adSS = ThisDrawing.SelectionSets.Add("adSS")
  adSS.Clear
  fType(0) = 0: fData(0) = "INSERT": fType(1) = 2: fData(1) = adBlocktoFix
  adSS.Select acSelectionSetAll, , , fType, fData
  i = 0
  For Each adDwgBlock In adSS
    If adDwgBlock.Name = adBlocktoFix Then
      adBlockAttributes = adDwgBlock.GetAttributes
      If adBlockAttributes(0).TextString = "W-28" Then  '<-- This is the search criteria
        adBlockAttributes(1).TextString = "250.00"      '<-- This is the update
        adBlockAttributes(2).TextString = "137.62"      '<-- This is the update
        i = i + 1
      ElseIf adBlockAttributes(0).TextString = "W-32" Then  '<-- This is the search criteria
        adBlockAttributes(1).TextString = "200.30"      '<-- This is the update
        adBlockAttributes(2).TextString = "105.65"      '<-- This is the update
        i = i + 1
      End If
    End If
  Next
  ThisDrawing.Application.Update
  MsgBox i & " blocks updated."
End Sub

Sub ad_FixPlotStyles()
'  This routine changes all layer plot styles to 'ad_NamedStyle.stb'.
'    It would be useful in bringing out of date or outside drawings up
'    to a current standard. This routine blindly changes all styles
'    to 'ad_NamedStyle', but you could insert a test to change particular
'    style names to one of several different styles.
'Demand load:  -vbarun;ad_Utility.dvb!ad_FixPlotStyles;
    Dim dwgLayer As AcadLayer
    
    For Each dwgLayer In ThisDrawing.Layers
        If dwgLayer.PlotStyleName <> "ad_NamedStyle" Then
            dwgLayer.PlotStyleName = "ad_NamedStyle"
        End If
    Next dwgLayer
End Sub

Sub ad_FreezeAll()
'This routine freezes all layers(except the current layer).
'Demand load:  -vbarun;ad_Utility.dvb!ad_FreezeAll;
    Dim adLayer As AcadLayer
    
    On Error Resume Next   'This is to bypass the current layer
    For Each adLayer In ThisDrawing.Layers
        adLayer.Freeze = True
    Next adLayer
End Sub

Sub ad_FreezePick()
'This routine freezes the selected entity's layer.
'Demand load:  -vbarun;ad_Utility.dvb!ad_FreezePick;
    Dim objSelected As AcadObject
    Dim FrzLayer As AcadLayer
    Dim varPick As Variant
                
    On Error Resume Next
    With ThisDrawing.Utility
        .GetEntity objSelected, varPick, vbCr & "Select object whose layer is to be made current>> "
    End With
    If objSelected Is Nothing Then
        MsgBox "Nothing was selected"
        Exit Sub
    End If
    Set FrzLayer = ThisDrawing.Layers(objSelected.Layer)
    FrzLayer.Freeze = True
End Sub

Sub ad_GraphScrColor()
'  This routine toggles the graphics window background color
'     between Black and White.
'Demand load:  -vbarun;ad_Utility.dvb!ad_GraphScrColor;
    Dim PrefsDisplay As AcadPreferencesDisplay
    Set PrefsDisplay = ThisDrawing.Application.Preferences.Display
        If PrefsDisplay.GraphicsWinModelBackgrndColor = vbBlack Then
            PrefsDisplay.GraphicsWinModelBackgrndColor = vbWhite
        Else: PrefsDisplay.GraphicsWinModelBackgrndColor = vbBlack
    End If
End Sub

Sub ad_LayoutLimits()
'  This gets the limits for all layouts in the current drawing and
'      displays the information in a message box.
'  Demand load:  -vbarun;ad_Utility.dvb!ad_LayoutLimits;
    Dim adLayout As AcadLayout
    Dim adLimMax As Variant, adLimMin As Variant
    For Each adLayout In ThisDrawing.Layouts
        ThisDrawing.ActiveLayout = adLayout
        adLimMin = ThisDrawing.GetVariable("LIMMIN")
        adLimMax = ThisDrawing.GetVariable("LIMMAX")
        MsgBox "Limits for " & adLayout.Name & vbCr & _
            "= " & adLimMin(0) & ", " & adLimMin(1) & " :" _
            & vbCr & "  " & adLimMax(0) & ", " & adLimMax(1)
    Next
End Sub

Sub ad_LoadProfile()
'This routine loads a saved User Profile.
'Demand load:  -vbarun;ad_Utility.dvb!ad_LoadProfile;
    Dim adPrefs As AcadPreferences
    Dim adLoadFile As String
    Dim adProfileName As String
  
    Set adPrefs = ThisDrawing.Application.Preferences
    adLoadFile = "AcadProfile.arg"
    adProfileName = "AcadProfile"
    
    On Error GoTo NoFile
    Preferences.Profiles.ImportProfile adProfileName, adLoadFile, True
    
    Exit Sub
NoFile:
        MsgBox "Profile Import Failed:" & Err.Description
     
End Sub

Sub ad_MatchLayer()
'This routine changes the current active layer based on a
'  selected entity command.
'Demand load:  -vbarun;ad_Utility.dvb!ad_MatchLayer;
    Dim objSelected As AcadObject
    Dim varPick As Variant
                
    On Error Resume Next
    With ThisDrawing.Utility
        .GetEntity objSelected, varPick, vbCr & "Select object whose layer is to be made current>> "
    End With
    If objSelected Is Nothing Then
        MsgBox "Nothing was selected"
        Exit Sub
    End If
    ThisDrawing.ActiveLayer = ThisDrawing.Layers(objSelected.Layer)
    ThisDrawing.SendCommand "_vbaunload" & vbCr & "MatchLayer.dvb" & vbCr
End Sub

Sub ad_MatchProps()
'This routine mimics the basic functionality of the '_MatchProp'
'  command.
'Demand load:  -vbarun;ad_Utility.dvb!ad_MatchProps;
    Dim sourceObj As AcadObject
    Dim destObj As AcadObject
    Dim basePnt As Variant
    Dim sourceType As String
    Dim objSelected As Integer
    
    objSelected = 1
    ThisDrawing.Utility.GetEntity sourceObj, basePnt, "Select Source Object>> "
    Do While objSelected = 1
        Set destObj = Nothing
        On Error GoTo exitsub
        ThisDrawing.Utility.GetEntity destObj, basePnt, "Select Destination Object(s)>> "
        destObj.Color = sourceObj.Color
        destObj.Layer = sourceObj.Layer
        destObj.Linetype = sourceObj.Linetype
        destObj.LinetypeScale = sourceObj.LinetypeScale
        destObj.Lineweight = sourceObj.Lineweight
        
        If destObj.ObjectName = "AcDbText" Then
            If sourceObj.ObjectName <> "AcDbText" Then
                GoTo NextObj
            End If
            destObj.Backward = sourceObj.Backward
            destObj.Height = sourceObj.Height
            destObj.ObliqueAngle = sourceObj.ObliqueAngle
            destObj.ScaleFactor = sourceObj.ScaleFactor
            destObj.StyleName = sourceObj.StyleName
            destObj.Width = sourceObj.Width
        End If
        If destObj.ObjectName = "AcDbMtext" Then
            If sourceObj.ObjectName <> "AcDbMtext" Then
                GoTo NextObj
            End If
            destObj.DrawingDirection = sourceObj.DrawingDirection
            destObj.Height = sourceObj.Height
            destObj.Rotation = sourceObj.Rotation
            destObj.StyleName = sourceObj.StyleName
            destObj.Width = sourceObj.Width
        End If
        If destObj.ObjectName = "AcDbHatch" Then
            If sourceObj.ObjectName <> "AcDbHatch" Then
                GoTo NextObj
            End If
            destObj.HatchStyle = sourceObj.HatchStyle
            destObj.PatternAngle = sourceObj.PatternAngle
            destObj.PatternDouble = sourceObj.PatternDouble
            destObj.PatternName = sourceObj.PatternName
            destObj.PatternScale = sourceObj.PatternScale
            destObj.PatternSpace = sourceObj.PatternSpace
            destObj.PatternType = sourceObj.PatternType
        End If
        If destObj.ObjectName = "AcDbDimension" Then
            If sourceObj.ObjectName <> "AcDbDimension" Then
                GoTo NextObj
            End If
            destObj.StyleName = sourceObj.StyleName
        End If
        destObj.Update
NextObj:
    Loop
exitsub:
End Sub

Sub ad_OutlookOpenDwg()
'Demand load:  -vbarun;ad_Utility.dvb!ad_OutlookOpenDwg;
'Creates a Journal entry in the format:
' FullDwgPath -OPENED- CurrentSystemTime
  Dim adOutlookApp As Object
  Dim adCadItem As Object
  Dim adJournalEntryName As String
  Dim adSysTime As Variant
  adSysTime = Time
  adJournalEntryName = ThisDrawing.Path
  Set adOutlookApp = CreateObject("Outlook.Application")
  Set adCadItem = adOutlookApp.CreateItem(olJournalItem)
  With adCadItem
    .Type = "AutoCAD"
    .Subject = adJournalEntryName & " -OPENED- " & adSysTime
    .StartTimer
    .Save
  End With
End Sub

Sub ad_OutlookCloseDwg()
'Demand load:  -vbarun;ad_Utility.dvb!ad_OutlookCloseDwg;
'Creates a Journal entry in the format:
' FullDwgPath -CLOSED- CurrentSystemTime
  Dim adOutlookApp As Object
  Dim adCadItem As Object
  Dim adJournalEntryName As String
  Dim adSysTime As Variant
  adSysTime = Time
  adJournalEntryName = ThisDrawing.Path
  Set adOutlookApp = CreateObject("Outlook.Application")
  Set adCadItem = adOutlookApp.CreateItem(olJournalItem)
  With adCadItem
    .Type = "AutoCAD"
    .Subject = adJournalEntryName & " -CLOSED- " & adSysTime
    .StartTimer
    .Save
  End With
End Sub

Sub ad_PageLayout()
'  This routine assigns a particular Layout as the Active Layout.
'Demand load:  -vbarun;ad_Utility.dvb!ad_PageLayout;
    Dim newLayout As AcadLayout
    Dim PageLayouts As AcadLayouts
    Dim newLayoutName As String
    
    Set PageLayouts = ThisDrawing.Layouts
    newLayoutName = "Model"
    Set newLayout = ThisDrawing.Layouts(newLayoutName)
    ThisDrawing.ActiveLayout = newLayout
End Sub

Sub ad_PlotToFile()
'  This routine plots all paperspace layouts in the current drawing
'    to a file. It uses the current layout plot settings.
'  Demand load:  -vbarun;ad_Utility.dvb!ad_PlotToFile;
  On Error Resume Next
  Dim adPlotLayout As AcadLayout
  Dim adStrMsg As String
  Dim adStrTitle As String
  Dim adResponse
  Dim adPlotFileName As String
  Dim adResult As Boolean
  adStrMsg = "Plot " & ThisDrawing.Layouts.Count - 1 & " Layout(s) to Files?"
  adStrTitle = "Verify Create Plot File(s)"
  adResponse = MsgBox(adStrMsg, vbYesNo, StrTitle)
  If adResponse = vbYes Then
    For Each adPlotLayout In ThisDrawing.Layouts
      If adPlotLayout.Name <> "Model" Then
        ThisDrawing.ActiveLayout = adPlotLayout
        adPlotFileName = adPlotLayout.Name & ".plt"
        adResult = ThisDrawing.Plot.PlotToFile(adPlotFileName)
      End If
    Next
  End If
End Sub

Sub ad_PlotToFolder()
'  This routine plots all paperspace layouts in the current drawing
'    to a specific folder. It uses the current layout plot settings.
'  Demand load:  -vbarun;ad_Utility.dvb!ad_PlotToFolder;
  On Error Resume Next
  Dim adPlotLayout As AcadLayout
  Dim adStrMsg As String
  Dim adStrTitle As String
  Dim adResponse
  Dim adFolderName As String
  Dim adResult As Boolean
  adStrMsg = "Plot " & ThisDrawing.Layouts.Count - 1 & " Layout(s) to Files?"
  adStrTitle = "Verify Create Plot File(s)"
  adResponse = MsgBox(adStrMsg, vbYesNo, StrTitle)
  If adResponse = vbYes Then
'Reset adFolderName to an existing path
    adFolderName = "C:\Plots\"
    For Each adPlotLayout In ThisDrawing.Layouts
      If adPlotLayout.Name <> "Model" Then
        ThisDrawing.ActiveLayout = adPlotLayout
        adResult = ThisDrawing.Plot.PlotToFile(adFolderName)
      End If
    Next
  End If
End Sub

Sub ad_PlotLayouts()
'This routine plots all layouts(except modelspace) in the current drawing.
'  It uses the current layout plot settings.
'Demand load:  -vbarun;ad_Utility.dvb!ad_PlotLayouts;
    Dim PlotLayout As AcadLayout
    Dim PlotLayouts As AcadLayouts
    Dim StrMsg As String
    Dim StrTitle As String
    Dim Response
    
    On Error Resume Next
    If ThisDrawing.ActiveSpace = acModelSpace Then _
            ThisDrawing.ActiveSpace = acPaperSpace
    Set PlotLayouts = ThisDrawing.Layouts
    StrMsg = "Plot " & PlotLayouts.Count - 1 & " Layout(s)?"
    StrTitle = "Verify Plot All Layouts"
    Response = MsgBox(StrMsg, vbYesNo, StrTitle)
    If Response = vbYes Then
        For Each PlotLayout In PlotLayouts
            If PlotLayout.Name <> "Model" Then
                    ThisDrawing.ActiveLayout = PlotLayout
                    ThisDrawing.Plot.PlotToDevice
            End If
        Next
    End If
End Sub

Sub ad_SaveProfile()
'This routine saves the Active User Profile.
'Demand load:  -vbarun;ad_Utility.dvb!ad_SaveProfile;
    Dim adPrefs As AcadPreferences
    Dim adCurrentProfile As String
    Dim adSaveFile As String
  
    Set adPrefs = ThisDrawing.Application.Preferences
    adSaveFile = "AcadProfile.arg"
    adCurrentProfile = Preferences.Profiles.ActiveProfile
    Preferences.Profiles.ExportProfile adCurrentProfile, adSaveFile
End Sub

Sub ad_ScreenMenu()
'This routine toggles the AutoCAD screen menu on/off.
'Demand load:  -vbarun;ad_Utility.dvb!ad_ScreenMenu;
    Dim Prefs As AcadPreferences
    Dim MenuDisplay As Boolean
    Set Prefs = ThisDrawing.Application.Preferences
    MenuDisplay = Preferences.Display.DisplayScreenMenu
    Prefs.Display.DisplayScreenMenu = Not (MenuDisplay)
End Sub

Sub ad_SwapProfiles()
'This routine toggles between two profiles.
'Demand load:  -vbarun;ad_Utility.dvb!ad_SwapProfiles;
  Dim adPrefs As AcadPreferences
  Dim adLoadFile As String
  Dim adProfileName As String
  Set adPrefs = ThisDrawing.Application.Preferences
  If adPrefs.Profiles.ActiveProfile = "Profile1" Then
    adLoadFile = "Profile2.arg"
    adProfileName = "Profile2"
  Else
    adLoadFile = "Profile1.arg"
    adProfileName = "Profile1"
  End If
  On Error GoTo NoFile
  Preferences.Profiles.ImportProfile adProfileName, adLoadFile, True
  Exit Sub
NoFile:
  MsgBox "Profile Import Failed:" & Err.Description
End Sub

Sub ad_ThawAll()
'This routine thaws all layers.
'Demand load:  -vbarun;ad_Utility.dvb!ad_ThawAll;
    Dim adLayer As AcadLayer
    
    On Error Resume Next   'This is to bypass the current layer
    For Each adLayer In ThisDrawing.Layers
        adLayer.Freeze = False
    Next adLayer
    ThisDrawing.Regen acAllViewports
End Sub

Sub ad_TotalLines()
'  This routine demonstrates a method for retrieving the cumulative
'     length of all lines on a particular layer.
'  Demand load:  -vbarun;ad_Utility.dvb!ad_TotalLines;
  Dim adLine As AcadObject
  Dim adTotalLen As Double
  Dim adWorkLayer As String
  adWorkLayer = "0"
  adTotalLen = 0
  For Each adLine In ThisDrawing.ModelSpace
    If adLine.ObjectName = "AcDbLine" Then
      If adLine.Layer = adWorkLayer Then
        adTotalLen = adTotalLen + adLine.Length
      End If
    End If
  Next adLine
  adTotalLen = Round(adTotalLen, 2)
  MsgBox "Total of line segments" & vbCr & _
    "on layer " & adWorkLayer & " is:" & vbCr & _
    adTotalLen
End Sub

Sub ad_ToUpper()
'This routine changes all MText and Text in a drawing to all uppercase.
'Demand load:  -vbarun;ad_Utility.dvb!ad_ToUpper;
  Dim adText As AcadText
  Dim adMText As AcadMText
  Dim adSS As AcadSelectionSet
  Dim fType(0 To 1) As Integer, fData(0 To 1)
  
  Set adSS = ThisDrawing.SelectionSets.Add("adSS")
  If Err Then Set adSS = ThisDrawing.SelectionSets.Add("adSS")
  adSS.Clear
  
  fType(0) = 0: fData(0) = "TEXT": fType(1) = 8: fData(1) = "*"
  adSS.Select acSelectionSetAll, , , fType, fData
  For Each adText In adSS
    adText.TextString = UCase(adText.TextString)
  Next adText
  
  adSS.Clear
  fType(0) = 0: fData(0) = "MTEXT": fType(1) = 8: fData(1) = "*"
  adSS.Select acSelectionSetAll, , , fType, fData
  For Each adMText In adSS
    adMText.TextString = UCase(adMText.TextString)
  Next adMText
  
  adSS.Delete
End Sub

Sub ad_VerifyDims()
'This routine highlights dimensions with overrides.
'Demand load:  -vbarun;ad_Utility.dvb!ad_VerifyDims;
  Dim adDimension As AcadDimension
  Dim adSS As AcadSelectionSet
  Dim fType(0 To 1) As Integer, fData(0 To 1)
  Dim adOverRideCount As Integer
  adOverRideCount = 0
  
  Set adSS = ThisDrawing.SelectionSets.Add("adSS")
  If Err Then Set adSS = ThisDrawing.SelectionSets.Add("adSS")
  adSS.Clear

  fType(0) = 0: fData(0) = "DIMENSION": fType(1) = 100: fData(1) = "*"
  adSS.Select acSelectionSetAll, , , fType, fData
  
  For Each adDimension In adSS
    If adDimension.TextOverride <> "" Then
      adDimension.TextColor = acYellow
      adOverRideCount = adOverRideCount + 1
    End If
  Next adDimension
  ThisDrawing.Application.Update
  MsgBox adOverRideCount & " dimension override(s) found..."
  adSS.Delete
End Sub

Sub ad_VerifyDimsResetColor()
'This routine restores dimension colors highlighted by 'ad_VerifyDims'.
'Demand load:  -vbarun;ad_Utility.dvb!ad_VerifyDimsResetColor;
  Dim adDimension As AcadDimension
  Dim adSS As AcadSelectionSet
  Dim fType(0 To 1) As Integer, fData(0 To 1)
  Dim adOverRideCount As Integer

  Set adSS = ThisDrawing.SelectionSets.Add("adSS")
  If Err Then Set adSS = ThisDrawing.SelectionSets.Add("adSS")
  adSS.Clear

  fType(0) = 0: fData(0) = "DIMENSION": fType(1) = 100: fData(1) = "*"
  adSS.Select acSelectionSetAll, , , fType, fData
    
  For Each adDimension In adSS
    If adDimension.TextColor = acYellow Then
      adDimension.TextColor = ThisDrawing.GetVariable("DimClrT")
    End If
  Next adDimension
  ThisDrawing.Application.Update
  adSS.Delete
End Sub

Public Function Round(adNum As Double, adPlaces As Integer) As Double
  Dim adTmp As Integer
  adNum = CDbl(adNum)
  adTmp = Fix(adNum)
  adNum = CInt((adNum - adTmp) * 10 ^ adPlaces)
  Round = adTmp + adNum / 10 ^ adPlaces
End Function
