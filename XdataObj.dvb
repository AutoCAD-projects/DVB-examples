Attribute VB_Name = "Xdata"
Attribute VB_Base = "0{FCFB3D2A-A0FA-1068-A738-08002B3371B5}"
Attribute VB_Creatable = True
Attribute VB_PredeclaredId = False
Attribute VB_Exposed = False
Attribute VB_TemplateDerived = False
Attribute VB_Customizable = False
Option Explicit

Public XdataType As Variant
Public XdataValue As Variant
Public AppNames As New Collection
Public ItemsCount As Long
Public aryXdata As Variant
Public EntityType As Long
Public Sub Split(lstArray As Variant)
' take the two dimensional array used for listboxes and split it into
' the XdataType And XdataValue
    aryXdata = lstArray
    If Not IsEmpty(aryXdata) Then
        XdataType = Empty             ' clear the arrays
        XdataValue = Empty
        Dim holdXdataType() As Variant, holdXdataValue() As Variant
        Dim lngI As Long
        Dim strTemp As String
        Dim arrayData(0 To 2) As Variant
        For lngI = LBound(aryXdata) To UBound(aryXdata)
            ReDim Preserve holdXdataType(lngI)
            ReDim Preserve holdXdataValue(lngI)
            holdXdataType(lngI) = CInt(aryXdata(lngI, 0))
            If (aryXdata(lngI, 0) = 1010) Or (aryXdata(lngI, 0) = 1011) Or (aryXdata(lngI, 0) = 1012) Or (aryXdata(lngI, 0) = 1013) Then
                strTemp = aryXdata(lngI, 1)
                arrayData(0) = CLng(parse(strTemp, ",", 1))
                arrayData(1) = CLng(parse(strTemp, ",", 2))
                arrayData(2) = CLng(parse(strTemp, ",", 3))
                holdXdataValue(lngI) = arrayData
            Else
                holdXdataValue(lngI) = aryXdata(lngI, 1)
            End If
        Next lngI
        XdataType = holdXdataType
        XdataValue = holdXdataValue
        StoreAppNames                  ' stores the appname in the xdata objects appnames collection
        ItemsCount = UBound(XdataValue)     ' store the number of items in the xdata in the xdata objects itemscount property
    Else
        MsgBox "No data in aryXdata to split.", , "Error"
    End If
    
End Sub
Public Sub List(Optional Listmode As String, Optional frmList As ListBox)
' fill the objects property called aryXdata
'(2 dimensional array) and set up for display
' possible display list modes are:   "D" for debug.print (default)
'                                    "M" for message box
'                                    "L" for list box
    If Not IsEmpty(XdataType) Then
        ' put the two seperate array's data into a two dimensional array
        Dim inti, intj As Integer
        inti = UBound(XdataType)
        ItemsCount = inti            ' store the number of items in the xdata in the xdata objects itemscount property
        ReDim aryXdata(inti, 2)
        Dim I As Integer
        Dim arrayData As Variant
        For I = 0 To inti
            aryXdata(I, 0) = XdataType(I)
        Next I
        For I = 0 To inti
            If (XdataType(I) = 1010) Or (XdataType(I) = 1011) Or (XdataType(I) = 1012) Or (XdataType(I) = 1013) Then
                arrayData = XdataValue(I)
                aryXdata(I, 1) = arrayData(0) & "," & arrayData(1) & "," & arrayData(2)
            Else
                aryXdata(I, 1) = XdataValue(I)
            End If
        Next I
        Dim lngI As Long
        Select Case UCase(Listmode)
            Case "L"
                ' load the list control passed in
                frmList.Clear
                frmList.List = aryXdata
            Case "M"
                Dim strMsg As String
                strMsg = ""
                For lngI = LBound(aryXdata) To UBound(aryXdata)
                    strMsg = strMsg & aryXdata(lngI, 0) & ": " & aryXdata(lngI, 1) & vbCrLf
                Next lngI
                MsgBox strMsg, , "Xdata List"
            Case Else
                For lngI = LBound(aryXdata) To UBound(aryXdata)
                    Debug.Print aryXdata(lngI, 0) & ": " & aryXdata(lngI, 1)
                Next lngI
        End Select
    End If
End Sub

Public Function AppExist(appname) As Boolean
' See if the appname is present in the xdata
' using the appnames collection of the object
    Dim result As Boolean
    On Error Resume Next
    Debug.Print AppNames.item(appname)
    If Err.Number > 0 Then
        Err.Clear
    Else
        result = True
    End If
    AppExist = result
End Function
Public Function SetXdata(OriginalObject As Object, MasterObject As Xdata, appname) As Boolean
' Exposed function to user on the object for setting the xdata onto the entity or group
' The OriginalObject is the entity or group
' the MasterObject is the new xdata for placement
' the Appname is the application name to update ("" means update all apps on the entity)
    Dim result As Boolean
    Dim lngEtype As Long
    On Error Resume Next
    lngEtype = OriginalObject.EntityType
    If Err.Number > 0 Or lngEtype = 0 Then          ' is it a legal object (lngetype = 0 is an Xdata object)
        MsgBox "Invalid Object type passed in.", , "Error"
        Err.Clear
    Else
        Dim TempOrigObj As New Xdata
        TempOrigObj.GetXdata OriginalObject, ""         ' store the entity or group
        Dim lngI As Long
        If Not IsEmpty(TempOrigObj.XdataType) Then      ' do we have xdata to work with on the original object?
            ' now process the xdata - if any
            If Not IsEmpty(MasterObject.XdataType) Then ' any new xdata loaded on the masterobject?
                RegisterApps MasterObject               ' register all apps
                If appname = "" Then                    ' replace all apps?
                    PlaceXdata OriginalObject, MasterObject
                    result = True
                Else                                    ' just replace one app
                    Dim TempXdataObj As New Xdata
                    Dim TargetXdataType() As Variant, TargetXdataValue() As Variant
                    If MasterObject.AppExist(appname) Then
                        ' first find the application in the masterobject that was requested
                        ' and place it into an xdata object by itself
                        TempXdataObj.GetXdata MasterObject, appname
                        ' next spin through the original object's xdata and place each into
                        ' a temp xdata object (except the requested app name data)
                        Dim lngK As Long
                        Dim ChildTempOrigObj As New Xdata
                        For lngI = 1 To TempOrigObj.AppNames.Count
                            ' next put all of the temp xdata into a target array
                            Set ChildTempOrigObj = Nothing      ' clear it each time
                            If TempOrigObj.AppNames(lngI) = appname Then
                            Else
                                ChildTempOrigObj.GetXdata TempOrigObj, TempOrigObj.AppNames(lngI)
                                AddArrays TargetXdataType, ChildTempOrigObj.XdataType
                                AddArrays TargetXdataValue, ChildTempOrigObj.XdataValue
                            End If
                        Next lngI
                        ' when the target arrays are built (both type and value)
                        ' add the masterobject xdata type & value arrays to
                        ' the target arrays
                        AddArrays TargetXdataType, TempXdataObj.XdataType
                        AddArrays TargetXdataValue, TempXdataObj.XdataValue
                        Dim NewMasterObj As New Xdata
                        NewMasterObj.XdataType = TargetXdataType
                        NewMasterObj.XdataValue = TargetXdataValue
                        ' Now set the xdata on the entity using the target arrays
                        PlaceXdata OriginalObject, NewMasterObj
                        result = True
                    Else
                        MsgBox "Could not find " & appname & " application in the MasterObject." & _
                               "No Xdata set.", , "Error"
                    End If
                End If
            Else
                MsgBox "No Xdata in the MasterObject for placement.", , "Error"
            End If
        Else
            ' no xdata on the original object so just add the new xdata
            RegisterApps MasterObject                   ' always register the apps first
            PlaceXdata OriginalObject, MasterObject     ' set the xdata on the object
            result = True
        End If
    End If
    SetXdata = result
End Function
Public Function GetXdata(object As Object, appname) As Boolean
' This method is exposed to the user and is used to take
' the entity or group object and the appname
' and retrieves (and loads) the xdata from the object into the xdata object
' when appname = "" then all applications are retrieved and loaded from the object
    Dim result As Boolean
    Dim lngEtype As Long
    On Error Resume Next
    lngEtype = object.EntityType
    If Err.Number > 0 Then
        MsgBox "Invalid Object type passed in.", , "Error"
        Err.Clear
    Else
        RetrieveXdata object, appname           ' go get the data
        ' now process the xdata - if any
        If Not IsEmpty(XdataType) Then          ' any xdata loaded?
            result = True                       ' return xdata found flag
            StoreAppNames appname               ' stores the appname in the xdata objects appnames collection
            ItemsCount = UBound(XdataValue)     ' store the number of items in the xdata in the xdata objects itemscount property
            List                                ' builds the two dimensional array (aryxdata) property from the xdata in the object and optionally lists it out
        End If
    End If
    GetXdata = result
End Function
Public Sub StoreAppNames(Optional appname As Variant)
' now that the xdata is loaded into the xdatatype
' extract application names into the names collection
    If IsMissing(appname) Then
        appname = ""
    End If
    If appname = "" Then
        Dim lngI As Long
        On Error Resume Next
        lngI = LBound(XdataType)
        If Err.Number = 0 Then
            For lngI = LBound(XdataType) To UBound(XdataType)
                Select Case XdataType(lngI)
                    Case 1001
                        AppNames.Add XdataValue(lngI), XdataValue(lngI)
                    Case Else
                End Select
            Next lngI
        Else
            MsgBox "Unsucessful. Xdata not present.", , "Error"
        End If
    Else                    ' just requested one app so store it
        AppNames.Add appname, appname
    End If
End Sub
Private Sub RegisterApps(MasterObject As Xdata)
' toolbox function to register all apps in the xdata object
    Dim lngI As Long
    ' make sure all appnames in the master object are registered
    ' if not, register them before proceeding
    For lngI = 1 To MasterObject.AppNames.Count
        On Error Resume Next
        With ThisDrawing
            .RegisteredApplications.item (MasterObject.AppNames.item(lngI))
            If Err.Number <> 0 Then      ' wasn't there so add it
                .RegisteredApplications.Add MasterObject.AppNames.item(lngI)
                Err.Clear
            End If
        End With
    Next lngI
End Sub
Private Sub PlaceXdata(OriginalObject As Object, MasterObject As Xdata)
' put the xdata onto the entity or group
    On Error GoTo errorhandler
    Dim aryXdataType() As Integer, aryXdataValue() As Variant
    Dim lngX As Long, atype As Long
    ' load the arrays from the masterobject
    For lngX = LBound(MasterObject.XdataType) To UBound(MasterObject.XdataType)
        ReDim Preserve aryXdataType(lngX)
        ReDim Preserve aryXdataValue(lngX)
        aryXdataType(lngX) = CInt(MasterObject.XdataType(lngX))
        atype = aryXdataType(lngX)
        If atype = 1010 Or atype = 1011 Or atype = 1012 Or atype = 1013 Then
            Dim aryTemp(0 To 2) As Double                   ' fix the longs in the array to doubles
            aryTemp(0) = MasterObject.XdataValue(lngX)(0)
            aryTemp(1) = MasterObject.XdataValue(lngX)(1)
            aryTemp(2) = MasterObject.XdataValue(lngX)(2)
            aryXdataValue(lngX) = aryTemp
        Else
            aryXdataValue(lngX) = MasterObject.XdataValue(lngX)
        End If
    Next lngX
    Debug.Print "Placexdata"
    'frmXdata.ShowVarTypes aryXdataType, aryXdataValue
    Select Case OriginalObject.EntityType
        Case acArc
            Dim cadArc As AcadArc
            Set cadArc = OriginalObject
            cadArc.SetXdata aryXdataType, aryXdataValue
        Case acCircle
            Dim cadCircle As AcadCircle
            Set cadCircle = OriginalObject
            cadCircle.SetXdata aryXdataType, aryXdataValue
            cadCircle.SetXdata aryXdataType, aryXdataValue
        Case acEllipse
            Dim cadEllipse As AcadEllipse
            Set cadEllipse = OriginalObject
            cadEllipse.SetXdata aryXdataType, aryXdataValue
        Case acLine
            Dim cadLine As AcadLine
            Set cadLine = OriginalObject
            cadLine.SetXdata aryXdataType, aryXdataValue
        Case acPoint
            Dim cadPoint As AcadPoint
            Set cadPoint = OriginalObject
            cadPoint.SetXdata aryXdataType, aryXdataValue
        Case acRay
            Dim cadray As AcadRay
            Set cadray = OriginalObject
            cadray.SetXdata aryXdataType, aryXdataValue
        Case ac3dFace
            Dim cad3dface As Acad3DFace
            Set cad3dface = OriginalObject
            cad3dface.SetXdata aryXdataType, aryXdataValue
        Case ac3dPolyline
            Dim cad3dpolyline As Acad3DPolyline
            Set cad3dpolyline = OriginalObject
            cad3dpolyline.SetXdata aryXdataType, aryXdataValue
        Case ac3dSolid
            Dim cad3dsolid As Acad3DSolid
            Set cad3dsolid = OriginalObject
            cad3dsolid.SetXdata aryXdataType, aryXdataValue
        Case acAttribute
            Dim cadAttribute As AcadAttribute
            Set cadAttribute = OriginalObject
            cadAttribute.SetXdata aryXdataType, aryXdataValue
        Case acDimAligned
            Dim cadDimAligned As AcadDimAligned
            Set cadDimAligned = OriginalObject
            cadDimAligned.SetXdata aryXdataType, aryXdataValue
        Case acDimAngular
            Dim cadDimAngular As AcadDimAngular
            Set cadDimAngular = OriginalObject
            cadDimAngular.SetXdata aryXdataType, aryXdataValue
        Case acDimDiametric
            Dim cadDimDiametric As AcadDimDiametric
            Set cadDimDiametric = OriginalObject
            cadDimDiametric.SetXdata aryXdataType, aryXdataValue
        Case acDimOrdinate
            Dim cadDimOrdinate As AcadDimOrdinate
            Set cadDimOrdinate = OriginalObject
            cadDimOrdinate.SetXdata aryXdataType, aryXdataValue
        Case acDimRadial
            Dim cadDimRadial As AcadDimRadial
            Set cadDimRadial = OriginalObject
            cadDimRadial.SetXdata aryXdataType, aryXdataValue
        Case acDimRotated
            Dim cadDimRotated As AcadDimRotated
            Set cadDimRotated = OriginalObject
            cadDimRotated.SetXdata aryXdataType, aryXdataValue
        Case acGroup
            Dim cadGroup As AcadGroup
            Set cadGroup = OriginalObject
            cadGroup.SetXdata aryXdataType, aryXdataValue
        Case acHatch
            Dim cadHatch As AcadHatch
            Set cadHatch = OriginalObject
            cadHatch.SetXdata aryXdataType, aryXdataValue
        Case acLeader
            Dim cadLeader As AcadLeader
            Set cadLeader = OriginalObject
            cadLeader.SetXdata aryXdataType, aryXdataValue
        Case acMtext
            Dim cadMtext As AcadMtext
            Set cadMtext = OriginalObject
            cadMtext.SetXdata aryXdataType, aryXdataValue
        Case acPolyline
            Dim cadPolyline As AcadPolyline
            Set cadPolyline = OriginalObject
            cadPolyline.SetXdata aryXdataType, aryXdataValue
        Case acPolylineLight
            Dim cadPoly As AcadLWPolyline
            Set cadPoly = OriginalObject
            cadPoly.SetXdata aryXdataType, aryXdataValue
        Case acPolymesh
            Dim cadPolyMesh As AcadPolygonMesh
            Set cadPolyMesh = OriginalObject
            cadPolyMesh.SetXdata aryXdataType, aryXdataValue
        Case acRaster
            Dim cadRaster As AcadRasterImage
            Set cadRaster = OriginalObject
            cadRaster.SetXdata aryXdataType, aryXdataValue
        Case acRegion
            Dim cadRegion As AcadRegion
            Set cadRegion = OriginalObject
            cadRegion.SetXdata aryXdataType, aryXdataValue
        Case acShape
            Dim cadShape As AcadShape
            Set cadShape = OriginalObject
            cadShape.SetXdata aryXdataType, aryXdataValue
        Case acSolid
            Dim cadSolid As AcadSolid
            Set cadSolid = OriginalObject
            cadSolid.SetXdata aryXdataType, aryXdataValue
        Case acSpline
            Dim cadSpline As AcadSpline
            Set cadSpline = OriginalObject
            cadSpline.SetXdata aryXdataType, aryXdataValue
        Case acText
            Dim cadText As AcadText
            Set cadText = OriginalObject
            cadText.SetXdata aryXdataType, aryXdataValue
        Case acTolerance
            Dim cadTolerance As AcadTolerance
            Set cadTolerance = OriginalObject
            cadTolerance.SetXdata aryXdataType, aryXdataValue
        Case acTrace
            Dim cadTrace As AcadTrace
            Set cadTrace = OriginalObject
            cadTrace.SetXdata aryXdataType, aryXdataValue
        Case acXline
            Dim cadXline As AcadXline
            Set cadXline = OriginalObject
            cadXline.SetXdata aryXdataType, aryXdataValue
    End Select
    
exitsub:
    Exit Sub
errorhandler:
    MsgBox Err.Number & vbTab & Err.Description & " in PlaceXdata", , "Error"
End Sub
Private Sub Retrievedata(Xobject As Xdata, lngI As Long)
    Dim lngK As Long, cnt As Long
    Dim tempXdataType() As Integer, tempXdataValue() As Variant
    With Xobject
        lngK = lngI
        cnt = 0
        On Error GoTo errorhandler
        Dim Trigger As Boolean
        Trigger = True
        Do While Trigger
            ReDim Preserve tempXdataType(cnt)
            ReDim Preserve tempXdataValue(cnt)
            tempXdataType(cnt) = .XdataType(lngK)
            tempXdataValue(cnt) = .XdataValue(lngK)
            cnt = cnt + 1
            lngK = lngK + 1
            On Error Resume Next
            Dim lngCode As Long
            lngCode = .XdataType(lngK)
            If Err.Number > 0 Then
                Trigger = False
                Err.Clear
            Else
                If lngCode = 1001 Then
                    Trigger = False
                End If
            End If
            'Debug.Print tempXdataValue(cnt - 1)
        Loop
    End With
    XdataType = tempXdataType
    XdataValue = tempXdataValue

exitsub:
    Exit Sub
errorhandler:
    MsgBox Err.Number & vbTab & Err.Description & " in RetrieveXdata", , "Error"
End Sub

Private Sub RetrieveXdata(object As Object, appname, Optional mode As Boolean)
     Select Case object.EntityType
        Case acArc
            Dim cadArc As AcadArc
            Set cadArc = object
            cadArc.GetXdata appname, XdataType, XdataValue
        Case acCircle
            Dim cadCircle As AcadCircle
            Set cadCircle = object
            cadCircle.GetXdata appname, XdataType, XdataValue
        Case acEllipse
            Dim cadEllipse As AcadEllipse
            Set cadEllipse = object
            cadEllipse.GetXdata appname, XdataType, XdataValue
        Case acLine
            Dim cadLine As AcadLine
            Set cadLine = object
            cadLine.GetXdata appname, XdataType, XdataValue
        Case acPoint
            Dim cadPoint As AcadPoint
            Set cadPoint = object
            cadPoint.GetXdata appname, XdataType, XdataValue
        Case acRay
            Dim cadray As AcadRay
            Set cadray = object
            cadray.GetXdata appname, XdataType, XdataValue
        Case ac3dFace
            Dim cad3dface As Acad3DFace
            Set cad3dface = object
            cad3dface.GetXdata appname, XdataType, XdataValue
        Case ac3dPolyline
            Dim cad3dpolyline As Acad3DPolyline
            Set cad3dpolyline = object
            cad3dpolyline.GetXdata appname, XdataType, XdataValue
        Case ac3dSolid
            Dim cad3dsolid As Acad3DSolid
            Set cad3dsolid = object
            cad3dsolid.GetXdata appname, XdataType, XdataValue
        Case acAttribute
            Dim cadAttribute As AcadAttribute
            Set cadAttribute = object
            cadAttribute.GetXdata appname, XdataType, XdataValue
        Case acDimAligned
            Dim cadDimAligned As AcadDimAligned
            Set cadDimAligned = object
            cadDimAligned.GetXdata appname, XdataType, XdataValue
        Case acDimAngular
            Dim cadDimAngular As AcadDimAngular
            Set cadDimAngular = object
            cadDimAngular.GetXdata appname, XdataType, XdataValue
        Case acDimDiametric
            Dim cadDimDiametric As AcadDimDiametric
            Set cadDimDiametric = object
            cadDimDiametric.GetXdata appname, XdataType, XdataValue
        Case acDimOrdinate
            Dim cadDimOrdinate As AcadDimOrdinate
            Set cadDimOrdinate = object
            cadDimOrdinate.GetXdata appname, XdataType, XdataValue
        Case acDimRadial
            Dim cadDimRadial As AcadDimRadial
            Set cadDimRadial = object
            cadDimRadial.GetXdata appname, XdataType, XdataValue
        Case acDimRotated
            Dim cadDimRotated As AcadDimRotated
            Set cadDimRotated = object
            cadDimRotated.GetXdata appname, XdataType, XdataValue
        Case acGroup
            Dim cadGroup As AcadGroup
            Set cadGroup = object
            cadGroup.GetXdata appname, XdataType, XdataValue
        Case acHatch
            Dim cadHatch As AcadHatch
            Set cadHatch = object
            cadHatch.GetXdata appname, XdataType, XdataValue
        Case acLeader
            Dim cadLeader As AcadLeader
            Set cadLeader = object
            cadLeader.GetXdata appname, XdataType, XdataValue
        Case acMtext
            Dim cadMtext As AcadMtext
            Set cadMtext = object
            cadMtext.GetXdata appname, XdataType, XdataValue
        Case acPolyline
            Dim cadPolyline As AcadPolyline
            Set cadPolyline = object
            cadPolyline.GetXdata appname, XdataType, XdataValue
        Case acPolylineLight
            Dim cadPoly As AcadLWPolyline
            Set cadPoly = object
            cadPoly.GetXdata appname, XdataType, XdataValue
        Case acPolymesh
            Dim cadPolyMesh As AcadPolygonMesh
            Set cadPolyMesh = object
            cadPolyMesh.GetXdata appname, XdataType, XdataValue
        Case acRaster
            Dim cadRaster As AcadRasterImage
            Set cadRaster = object
            cadRaster.GetXdata appname, XdataType, XdataValue
        Case acRegion
            Dim cadRegion As AcadRegion
            Set cadRegion = object
            cadRegion.GetXdata appname, XdataType, XdataValue
        Case acShape
            Dim cadShape As AcadShape
            Set cadShape = object
            cadShape.GetXdata appname, XdataType, XdataValue
        Case acSolid
            Dim cadSolid As AcadSolid
            Set cadSolid = object
            cadSolid.GetXdata appname, XdataType, XdataValue
        Case acSpline
            Dim cadSpline As AcadSpline
            Set cadSpline = object
            cadSpline.GetXdata appname, XdataType, XdataValue
        Case acText
            Dim cadText As AcadText
            Set cadText = object
            cadText.GetXdata appname, XdataType, XdataValue
        Case acTolerance
            Dim cadTolerance As AcadTolerance
            Set cadTolerance = object
            cadTolerance.GetXdata appname, XdataType, XdataValue
        Case acTrace
            Dim cadTrace As AcadTrace
            Set cadTrace = object
            cadTrace.GetXdata appname, XdataType, XdataValue
        Case acXline
            Dim cadXline As AcadXline
            Set cadXline = object
            cadXline.GetXdata appname, XdataType, XdataValue
        Case Else
            ' must be an xdata object since no matching acad entitytype
            Dim newXdataObj As Xdata
            Set newXdataObj = object
            With newXdataObj
                Dim lngI As Long
                For lngI = LBound(.XdataType) To UBound(.XdataType)
                    ' first find the requested application xdata
                    On Error GoTo errorhandler
                    If .XdataType(lngI) = 1001 Then
                        If IsMissing(mode) Then
                            If .XdataValue(lngI) = appname Then
                            Else                                ' all apps except the requested one
                                Retrievedata newXdataObj, lngI
                                Exit For
                            End If
                        Else
                            If .XdataValue(lngI) = appname Then
                                Retrievedata newXdataObj, lngI    ' only the requested app
                                Exit For
                            End If
                        End If
                    End If
                Next lngI
            End With
    End Select

exitsub:
    Exit Sub
errorhandler:
    MsgBox Err.Number & vbTab & Err.Description & " in RetrieveXdata", , "Error"
End Sub
Private Function parse(strLine As String, strDelimit As String, lngPosition As Long) As String
' this function takes the
'                                    position    position   position
'                                       1            2         3
' strLine holds the string  ie. "All good | men are | leaving the boat."
'                                              ^
'                                           boundary
' strdelimit is a one character string containing the delimiter to be used
' tempvar is returned
' lngPosition is what information position in the string you want
' Lpipe and Rpipe are the boundaries around the data

    Dim c As Long
    Dim Lpipe As Long
    Dim Rpipe As Long
    Dim mark As Long
    Dim tempvar As String
    Dim start As Long
    Dim datalen As Long
    Dim cnt As Long
    c = 1
    Lpipe = 0
    mark = 1
    tempvar = ""
    For cnt = 1 To lngPosition
        Do While Mid(strLine, c, 1) <> strDelimit And Len(strLine) >= c
            c = c + 1
        Loop
        Rpipe = c
        If mark = lngPosition - 1 Then
            Lpipe = c
        End If
        c = c + 1
        mark = mark + 1
    Next cnt
    start = Lpipe + 1
    datalen = (Rpipe - Lpipe) - 1
    parse = Mid(strLine, start, datalen)
End Function
Private Sub AddArrays(OriginalArray As Variant, AdditionalArray As Variant)
' toolbox function takes and adds the additionalarray to the original array
    Dim cnt As Long, lngI As Long
    On Error Resume Next
    cnt = UBound(OriginalArray) + 1
    If Err.Number > 0 Then
        cnt = 0
    End If
    For lngI = 0 To UBound(AdditionalArray)
        ReDim Preserve OriginalArray(cnt)
        OriginalArray(cnt) = AdditionalArray(lngI)
        cnt = cnt + 1
    Next lngI
End Sub

Attribute VB_Name = "basGlobal"
Option Explicit

Public Ent As Object
Public Sub Xdata()
    frmXdata.Show
    frmXdata.MultiPage1.SetFocus
    frmXdata.lstXdata.SetFocus

End Sub
Public Sub GetEnt(Ent As Object, Pnt As Variant)
' This subroutine waits for input from user
    Dim returnObject As Object
    Set returnObject = Nothing
    On Error Resume Next
   
Retry:
    
    ThisDrawing.Utility.GetEntity Ent, Pnt, "Select an object: "
    
    If Err <> 0 Then
        Err.Clear
        Dim selectedButton As Integer
        selectedButton = MsgBox("Please select an object. Cancel to return to the dialog box.", vbOKCancel, "Selection Error")
        If selectedButton = vbOK Then
            GoTo Retry
        End If
    End If
    If Ent Then
        Ent.Highlight (True)
    End If
   
End Sub
Public Sub Blink(cnt As Long, FrmCtrl As Control, message As String)
    If cnt > 0 Then
        Dim x As Long
        Dim y As Long
        For x = 1 To cnt
            FrmCtrl.Caption = message
            For y = 1 To 1000
                DoEvents
                FrmCtrl.Caption = CStr(y)
            Next y
        Next x
    End If
End Sub
Public Sub AddArrays(OriginalArray As Variant, AdditionalArray As Variant)
' toolbox function takes and adds the additionalarray to the original array
    Dim cnt As Long, lngI As Long
    On Error Resume Next
    cnt = UBound(OriginalArray) + 1
    If Err.Number > 0 Then
        cnt = 0
    End If
    For lngI = 0 To UBound(AdditionalArray)
        ReDim Preserve OriginalArray(cnt)
        OriginalArray(cnt) = AdditionalArray(lngI)
        cnt = cnt + 1
    Next lngI
End Sub

Attribute VB_Name = "fmAppName"
Attribute VB_Base = "0{B6111D1A-D5D6-11D2-99E0-C2B595000000}{B6111D0A-D5D6-11D2-99E0-C2B595000000}"
Attribute VB_Creatable = False
Attribute VB_PredeclaredId = True
Attribute VB_Exposed = False
Attribute VB_TemplateDerived = False
Attribute VB_Customizable = False
Option Explicit

Private Sub btnCancel_Click()
    fmAppName.Hide
End Sub

Private Sub btnOK_Click()
    frmXdata.NewAppName = fmAppName.edAppName
    fmAppName.Hide
End Sub

Private Sub edAppName_Change()
    If Len(edAppName.Text) > 0 Then
        fmAppName.btnOK.Enabled = True
    Else
        fmAppName.btnOK.Enabled = False
    End If
End Sub

Private Sub UserForm_Initialize()
        fmAppName.btnOK.Enabled = False
End Sub

Attribute VB_Name = "frmGroupNames"
Attribute VB_Base = "0{B6111D16-D5D6-11D2-99E0-C2B595000000}{B6111D08-D5D6-11D2-99E0-C2B595000000}"
Attribute VB_Creatable = False
Attribute VB_PredeclaredId = True
Attribute VB_Exposed = False
Attribute VB_TemplateDerived = False
Attribute VB_Customizable = False
Option Explicit

Private Sub btnCancel_Click()
    Unload Me
End Sub

Private Sub btnOK_Click()
        
    Me.Hide
End Sub

Private Sub lstGroupNames_Click()
    frmXdata.lstXdata.Clear
    frmXdata.lstAppNamePlace.Clear
    frmXdata.lblMessage.Caption = ""

End Sub

Attribute VB_Name = "frmXdata"
Attribute VB_Base = "0{B6111D7A-D5D6-11D2-99E0-C2B595000000}{B6111D00-D5D6-11D2-99E0-C2B595000000}"
Attribute VB_Creatable = False
Attribute VB_PredeclaredId = True
Attribute VB_Exposed = False
Attribute VB_TemplateDerived = False
Attribute VB_Customizable = False
Option Explicit
Public ChildObjs As New Collection
Public MasterObj As New Xdata
Public Ent As Object
Public NewAppName As String


Private Sub btnUpdate_Click()
    If MasterObj.ItemsCount > 0 Then
        MasterObj.SetXdata Ent, MasterObj, ""
    End If
End Sub

Private Sub btnBuildNew_Click()
    ' first make sure that there is no New_App already in the child collection
    Dim TempChildXobj As New Xdata
    On Error Resume Next
    Set TempChildXobj = ChildObjs.item("New_App")
    If Err.Number = 0 Then
        Err.Clear
        MsgBox "New_App has already been created. Please rename the application and try again.", , "Error"
    Else
        fmAppName.Show                          ' get the new application name
        If Len(NewAppName) > 0 Then             ' only continue if they got one
            Dim Exist As Boolean
            Exist = MasterObj.AppExist(NewAppName)
            If Not Exist Then                   ' add it if it is not already there
                Err.Clear
                lstXdata.Clear
                lstAppNamePlace.Clear
                frType.Enabled = True
                rdAppName.Value = True
                lstXdata.AddItem 1001, 0
                lstXdata.Column(1, 0) = NewAppName
                lstXdata.AddItem 1000, 1
                lstXdata.Column(1, 1) = " "
                ' build a new child object
                Dim aryTemp As Variant
                aryTemp = lstXdata.List
                ' load the list box array into the new child
                TempChildXobj.Split (aryTemp)
                ' add it to the child collection
                ChildObjs.Add TempChildXobj, NewAppName
                ' rebuild the child collection and the master object
                RebuildMasterObj
                MasterObj.StoreAppNames                  ' stores the appname in the xdata objects appnames collection
                LoadLists MasterObj                      ' load the listbox lists from the master object
                ' now make sure lstappnameplace is set to the new app
                lstAppNamePlace.Text = NewAppName
                lstXdata.Text = " "
                ThisDrawing.RegisteredApplications.Add NewAppName
                BuildRegistration
                edXdata.SetFocus
            Else
                MsgBox "The requested Application Name already exists on the object."
            End If
        End If
    End If

End Sub
Private Sub btnRemove_Click()
    Dim indx As Integer
    indx = lstXdata.ListIndex
    If indx = -1 Then
        GoTo exitsub
    Else
        lstXdata.RemoveItem (indx)
        RebuildXdata
        MasterObj.List
    End If
exitsub:
End Sub
Private Sub btnAdd_Click()
    Dim indx As Integer
    indx = lstXdata.ListIndex
    If indx = -1 Then
        indx = 0
    End If
    Dim code As Variant
    code = GetCode(frType)
    lstXdata.AddItem code, indx + 1
    lstXdata.Column(1, indx + 1) = edXdata.Text
    RebuildXdata
    lstXdata.ListIndex = indx + 1
End Sub

Private Sub btnReplace_Click()
    Dim indx As Integer
    Dim strTemp As String
    strTemp = edXdata.Text
    ' get the selected line index
    indx = lstXdata.ListIndex
    Dim code As Integer
    ' get the selected code from the frame tag for the data type buttons
    code = GetCode(frType)
    Dim LegalLayer As Boolean
    Select Case code
        Case 1003           ' check for a legal layer name
            LegalLayer = IsLegalLayer(strTemp)
            If Not LegalLayer Then
                MsgBox "Not an existing layer name", , "Error"
                GoTo exitsub
            End If
    End Select
    If indx = -1 Then
        GoTo exitsub
    Else
        ' remove the old item from the listbox
        lstXdata.RemoveItem (indx)
        ' update the listbox item with the new data
        lstXdata.AddItem code, indx
        lstXdata.Column(1, indx) = strTemp
        RebuildXdata
        MasterObj.List
    End If
exitsub:

End Sub
Private Sub RebuildXdata()
    Dim aryTemp  As Variant
    ' load the xdata arrays and the two dimension array from the listbox
    aryTemp = lstXdata.List
    Dim appname As String
    appname = lstAppNamePlace.Value
    If appname = "All Applications" Then
        Set MasterObj = Nothing
        ' load the xdata object
        MasterObj.Split (aryTemp)
        ' now reload the child object collection
        SetChildObjs
    Else
        RebuildChildThenMasterObjs appname, aryTemp
    End If
End Sub
Public Function IsLegalLayer(strLayer As String) As Boolean
    Dim result As Boolean
    Dim objLayer As AcadLayer
    On Error Resume Next
    Set objLayer = ThisDrawing.Layers(strLayer)
    If Err.Number = 0 Then
        result = True
    End If
    IsLegalLayer = result
End Function

Public Sub RebuildChildThenMasterObjs(appname, aryTemp)
    Dim intCnt As Integer
    Dim colTemp As New Collection
    ' store the collection count for future use
    intCnt = ChildObjs.Count
    ' store the child objects collection for future use
    Set colTemp = ChildObjs
    ' clear out the child collection and the master xdata object
    Set ChildObjs = Nothing
    Set MasterObj = Nothing
    Dim TempChildXobj As New Xdata
    Dim lngI As Long
    ' get all the child objects from the collection
    ' and rebuild the child objects collection
    For lngI = 1 To intCnt
        ' load the xdata object to check the app name
        Set TempChildXobj = colTemp.item(lngI)
        If appname = TempChildXobj.AppNames(1) Then
            ' found the app name being worked on in the listbox
            ' now clear the xdata obj for use
            Set TempChildXobj = Nothing
            ' load the xdata object with the listbox array
            TempChildXobj.Split (aryTemp)
        End If
        ' store the xdata object in the child collection
        ChildObjs.Add TempChildXobj, TempChildXobj.AppNames(1)
    Next lngI
    RebuildMasterObj
End Sub
Public Sub RebuildMasterObj()
    ' now rebuild the master object
    ' set up temporary arrays to build the xdata
    Dim aryXdataTypeTemp As Variant, aryXdataValueTemp As Variant
    Dim aryMasterTypeTemp() As Variant, aryMasterValueTemp() As Variant
    ' spin through the child collection
    ' and build a new master array for the type and the value
    Dim lngI As Long
    Dim TempChildXobj As New Xdata
    For lngI = 1 To ChildObjs.Count
        ' clear the temporary xdata object
        Set TempChildXobj = Nothing
        ' load it with a child xdata object from the collection
        Set TempChildXobj = ChildObjs.item(lngI)
        ' clear the arrays
        aryXdataTypeTemp = Empty
        aryXdataValueTemp = Empty
        ' load each array with the xdata object's xdata
        aryXdataTypeTemp = TempChildXobj.XdataType
        aryXdataValueTemp = TempChildXobj.XdataValue
        ' add the data to a master array
        AddArrays aryMasterTypeTemp, aryXdataTypeTemp
        AddArrays aryMasterValueTemp, aryXdataValueTemp
    Next lngI
    ' load the master array into the master xdata object
    MasterObj.XdataType = aryMasterTypeTemp
    MasterObj.XdataValue = aryMasterValueTemp
    ' load the rest of the master object's properties
    MasterObj.List

End Sub

Private Function GetCode(frType As Control) As Variant
    Dim result As Integer
    Select Case frType.Tag
        Case "String"
            result = 1000
        Case "AppName"
            result = 1001
        Case "Group"
            result = 1002
        Case "Layer"
            result = 1003
        Case "Binary"
            result = 1004
        Case "Handle"
            result = 1005
        Case "3Real"
            result = 1010
        Case "Position"
            result = 1011
        Case "Displacement"
            result = 1012
        Case "Direction"
            result = 1013
        Case "Real"
            result = 1040
        Case "Distance"
            result = 1041
        Case "Scale"
            result = 1042
        Case "Integer"
            result = 1070
        Case "Long"
            result = 1071
    End Select
    GetCode = result
End Function
Private Sub btnAddAppName_Click()
    Dim strValue As String
    strValue = edAppName.Text
    On Error Resume Next
    ThisDrawing.RegisteredApplications.item (strValue)
    If Err.Number <> 0 Then     ' not registered, add it
        ThisDrawing.RegisteredApplications.Add (strValue)
        MsgBox "Application registered.", , "Alert"
        BuildRegistration
    Else
        MsgBox "Application already registered.", , "Error"
    End If
End Sub

Private Sub edAppName_Change()
    If Len(edAppName) = 0 Then
        btnAddAppName.Enabled = False
    Else
        btnAddAppName.Enabled = True
    End If
End Sub

Private Sub lstAppNamePlace_Change()
    If lstAppNamePlace.Value = "All Applications" Then
        lstXdata.List = MasterObj.aryXdata
    Else
        Dim TempChildXobj As New Xdata
        If lstAppNamePlace.Value = "" Then
        Else
            Set TempChildXobj = ChildObjs.item(lstAppNamePlace.Value)
            lstXdata.List = TempChildXobj.aryXdata
        End If
    End If
    
End Sub

Private Sub btnCancel_Click()
    On Error Resume Next
    Ent.Highlight (False)
    End
End Sub
Private Sub btnSelectObject_Click()
    On Error Resume Next
    Ent.Highlight (False)
    If Err.Number <> 0 Then
        Err.Clear
    End If
    Me.Hide
    lstXdata.Clear
    lstAppNamePlace.Clear
    lblMessage.Caption = ""
    edXdata.Text = ""
    Dim Pnt As Variant
    Call GetEnt(Ent, Pnt)
    On Error Resume Next
    Debug.Print Ent.EntityType          'force an error for missing entities
    If Err.Number = 0 Then              ' if no entity was selected err.number > 0
        Set MasterObj = Nothing
        MasterObj.GetXdata Ent, ""
        If MasterObj.ItemsCount > 0 Then
            LoadLists MasterObj
            SetChildObjs
        End If
        lblMessage.Caption = "Entity: " & Ent.Handle
        btnBuildNew.Enabled = True
    End If
'    btnEnabled True
    If lblMessage.Caption = "" Then
        btnBuildNew.Enabled = False
        btnReplace.Enabled = False
        btnAdd.Enabled = False
        btnRemove.Enabled = False
        frType.Enabled = False
        edXdata.Text = ""
        edXdata.Enabled = False
    Else
        btnBuildNew.Enabled = True
        btnReplace.Enabled = True
        btnAdd.Enabled = True
        btnRemove.Enabled = True
        frType.Enabled = True
        edXdata.Enabled = True
    End If
    Me.Show
    
End Sub

Private Sub btnSelectGroup_Click()
        
    ' are there any groups in the drawing?
    If ThisDrawing.groups.Count <> 0 Then
        ' get all of their names into a collection for processing
        Dim GroupNames As New Collection
        Dim group As AcadGroup
        Dim x As Long
        For x = 0 To ThisDrawing.groups.Count - 1
            Set group = ThisDrawing.groups.item(x)
            GroupNames.Add group.Name
        Next x
        ' now show the group names and get the one they want to use
        Call Show_Group_names(GroupNames)
        frmGroupNames.Show
        Dim groupname As Variant
        groupname = frmGroupNames.lstGroupNames.Value
        ' check if the groupname is null or has no text
        ' this bit of code is a little unusal but it works because the '&' takes a variant
        ' and a zero length string and adds them together to get a zero length string
        ' but if the variant has anything in it, that is added and the length is
        ' greater than zero.
        If Len(groupname & "") > 0 Then
            ' now get any xdata attached to the requested group
            On Error Resume Next
            Ent.Highlight (False)
            If Err.Number <> 0 Then
                Err.Clear
            End If
            Set group = ThisDrawing.groups.item(groupname)
            Dim appname As String
            appname = ""
            Dim XdataType() As Variant, XdataValue() As Variant
            group.GetXdata appname, XdataType, XdataValue  ' get the xdata from the object
            Set Ent = group
            Set MasterObj = Nothing
            MasterObj.GetXdata Ent, ""
            If MasterObj.ItemsCount > 0 Then
                LoadLists MasterObj
                SetChildObjs
            'Else
                'lstXdata.Clear
                'lstAppNamePlace.Clear
            End If
            'ShowVarTypes MasterObj.XdataType, MasterObj.XdataValue
            lblMessage.Caption = "Group: " & groupname
            edXdata.Text = ""
            frType.Enabled = True
            btnBuildNew.Enabled = True
        End If
    Else
        MsgBox "No Groups present in this drawing."
    End If
    If lblMessage.Caption = "" Then
        btnBuildNew.Enabled = False
        btnReplace.Enabled = False
        btnAdd.Enabled = False
        btnRemove.Enabled = False
        frType.Enabled = False
        edXdata.Text = ""
        edXdata.Enabled = False
    Else
        btnBuildNew.Enabled = True
        btnReplace.Enabled = True
        btnAdd.Enabled = True
        btnRemove.Enabled = True
        frType.Enabled = True
        edXdata.Enabled = True
    End If

End Sub
Private Sub SetChildObjs()
    Dim lngI As Long
    Dim TempChildXobj As New Xdata
    Set ChildObjs = Nothing
    For lngI = 1 To MasterObj.AppNames.Count
        Set TempChildXobj = Nothing
        TempChildXobj.GetXdata MasterObj, MasterObj.AppNames(lngI)
        ChildObjs.Add TempChildXobj, MasterObj.AppNames(lngI)
    Next lngI

End Sub
Private Sub LoadLists(MasterObj As Xdata)
    lstXdata.Clear
    lstAppNamePlace.Clear
    ' load the main Xdata listbox
    MasterObj.List "L", lstXdata
    lstXdata.ListIndex = -1
    Dim lngI As Long
    Dim aryAppNames() As String
    ReDim Preserve aryAppNames(0)
    ' load the Applications listbox
    aryAppNames(0) = "All Applications"
    For lngI = 1 To MasterObj.AppNames.Count
        ReDim Preserve aryAppNames(lngI)
        aryAppNames(lngI) = MasterObj.AppNames.item(lngI)
    Next lngI
    lstAppNamePlace.List = aryAppNames
    lstAppNamePlace.ListIndex = 0
End Sub

Private Sub lstAppNames_Click()
    Dim indx As Integer
    indx = lstAppNames.ListIndex
    If indx = -1 Then
        GoTo exitsub
    Else
        edAppName.Text = lstAppNames.Value
    btnAddAppName.Enabled = True
    End If
exitsub:
End Sub

Private Sub lstXdata_Click()
    frType.Enabled = True
    btnEnabled True
    Dim code As Variant
    code = lstXdata.Column(0)
    EnableCodeButtons (code)
    edXdata.Text = lstXdata.Column(1)
    If frType.Tag = "Binary" Then
        edXdata.Enabled = False
    Else
        edXdata.Enabled = True
    End If
    If frType.Tag = "AppName" Then
        btnReplace.Enabled = False
        btnAdd.Enabled = False
        btnRemove.Enabled = False
        frType.Enabled = False
        edXdata.Text = ""
        edXdata.Enabled = False
    Else
        btnReplace.Enabled = True
        btnAdd.Enabled = True
        btnRemove.Enabled = True
        frType.Enabled = True
        edXdata.Enabled = True
    End If
End Sub
Private Sub EnableCodeButtons(code As Integer)
    Select Case code
        Case 1000
            rdString.Value = True
        Case 1001
            rdAppName.Value = True
        Case 1002
            rdGroup.Value = True
        Case 1003
            rdLayer.Value = True
        Case 1004
            rdBinary.Value = True
        Case 1005
            rdHand.Value = True
        Case 1010
            rd3Real.Value = True
        Case 1011
            rdPos.Value = True
        Case 1012
            rdDisp.Value = True
        Case 1013
            rdDir.Value = True
        Case 1040
            rdReal.Value = True
        Case 1041
            rdDist.Value = True
        Case 1042
            rdScale.Value = True
        Case 1070
            rdInt.Value = True
        Case 1071
            rdLong.Value = True
            
    End Select
End Sub
Private Sub rd3Real_Click()
    frType.Tag = "3Real"
End Sub

Private Sub rdAppName_Click()
    frType.Tag = "AppName"
End Sub

Private Sub rdBinary_Click()
    frType.Tag = "Binary"
End Sub

Private Sub rdDir_Click()
    frType.Tag = "Direction"
End Sub

Private Sub rdDisp_Click()
    frType.Tag = "Displacement"
End Sub

Private Sub rdDist_Click()
    frType.Tag = "Distance"
End Sub

Private Sub rdGroup_Click()
    frType.Tag = "Group"
End Sub

Private Sub rdHand_Click()
    frType.Tag = "Handle"
End Sub

Private Sub rdHideCodes_Click()
    Dim item As Variant
    item = lstXdata.ListIndex
    lstXdata.ColumnWidths = "0pt"
    If item > -1 Then
        lstXdata.ListIndex = item
    End If
End Sub

Private Sub rdInt_Click()
    frType.Tag = "Integer"
End Sub

Private Sub rdLayer_Click()
    frType.Tag = "Layer"
End Sub

Private Sub rdLong_Click()
    frType.Tag = "Long"
End Sub

Private Sub rdPos_Click()
    frType.Tag = "Position"
End Sub

Private Sub rdReal_Click()
    frType.Tag = "Real"
End Sub

Private Sub rdScale_Click()
    frType.Tag = "Scale"
End Sub

Private Sub rdShowCodes_Click()
    lstXdata.ColumnWidths = "40pt,250pt"
    Dim item As Variant
    item = lstXdata.ListIndex
    lstXdata.SetFocus
    If item > -1 Then
        lstXdata.ListIndex = item
    End If
End Sub

Private Sub rdString_Click()
    frType.Tag = "String"
End Sub

Private Sub UserForm_Initialize()
    rdString.Value = True
    'Turn_off_object_fields
    ' load the registered applications list
    BuildRegistration
    frType.Enabled = False
    rdHideCodes.Value = True
    btnEnabled False
    btnBuildNew.Enabled = False
    btnAddAppName.Enabled = False
End Sub
Private Sub BuildRegistration()
    Dim aryAppNames() As Variant
    Dim lngI As Long, cnt As Long
    Dim RegApp As AcadRegisteredApplication
    Dim strTemp As String
    cnt = ThisDrawing.RegisteredApplications.Count
    For lngI = 0 To cnt - 1
        ReDim Preserve aryAppNames(lngI)
        Set RegApp = ThisDrawing.RegisteredApplications.item(lngI)
        strTemp = RegApp.Name
        aryAppNames(lngI) = strTemp
    Next lngI
    lstAppNames.Clear
    lstAppNames.List = aryAppNames

End Sub

Private Sub btnEnabled(mode As Boolean)
    btnAdd.Enabled = mode
    btnRemove.Enabled = mode
    btnReplace.Enabled = mode

End Sub
Private Sub btnGetXData_Click()
' Creates a group named "TEST" in current drawing
    Dim group As AcadGroup
    Set group = ThisDrawing.groups.Add("TEST")  'create the group named TEST
  
    Dim anObj(1) As AcadLine
    Dim XdataType As Variant, XdataValue As Variant
    Dim appname As String
    ' The following code retrieves all the xdata of attached on an object
    ' Initialize anObj variable to any object that supports
    ' setxdata method.  This example creates 2 lines that are then added to a group
    Dim startpt(0 To 2) As Double, endpt(0 To 2) As Double
    startpt(0) = 0#: startpt(1) = 0#: startpt(2) = 0#
    endpt(0) = 5#: endpt(1) = 5#: endpt(2) = 0#
    Set anObj(0) = ThisDrawing.ModelSpace.AddLine(startpt, endpt)
    startpt(0) = 5#: startpt(1) = 0#: startpt(2) = 0#
    endpt(0) = 0#: endpt(1) = 5#: endpt(2) = 0#
    Set anObj(1) = ThisDrawing.ModelSpace.AddLine(startpt, endpt)
    
    group.AppendItems (anObj)  ' add the lines to the group TEST
    
Dim dataType(0 To 9) As Integer
    Dim data(0 To 9) As Variant
    Dim reals3(0 To 2) As Double
    Dim worldPos(0 To 2) As Double
    ' Initialize all the xdata value. Note that first data in the list should be
    ' application name and first datatype code should be 1001
    dataType(0) = 1001: data(0) = "TEST_APP"
    dataType(1) = 1000: data(1) = "This is a test for xdata"

dataType(2) = 1003: data(2) = "0"               ' layer
    dataType(3) = 1040: data(3) = 1.23479137438413E+40          ' real
    dataType(4) = 1041: data(4) = 1237324938            ' distance
    dataType(5) = 1070: data(5) = 32767                 ' 16 bit Integer
    dataType(6) = 1071: data(6) = 32767                 ' 32 bit Integer
    dataType(7) = 1042: data(7) = 10                ' scaleFactor

reals3(0) = -2.95: reals3(1) = 100: reals3(2) = -20
    dataType(8) = 1010: data(8) = reals3                ' real
    worldPos(0) = 4: worldPos(1) = 400.99999999: worldPos(2) = 2.798989
    dataType(9) = 1011: data(9) = worldPos          ' world space position
' The following code attaches xdata to an object
    group.SetXdata dataType, data
' The following code shows how to retrive information from XData
    appname = "TEST_APP"
    group.GetXdata appname, XdataType, XdataValue  ' get the xdata from the group

    Dim lbnd As Integer, ubnd As Integer
    Dim I As Integer
    Dim arrayData As Variant
    Dim resultString As String
    If VarType(XdataType) > vbNull Then
        lbnd = LBound(XdataType)
        ubnd = UBound(XdataType)
        For I = lbnd To ubnd

            If (XdataType(I) = 1010) Or (XdataType(I) = 1011) Or (XdataType(I) = 1012) Or (XdataType(I) = 1013) Then
                arrayData = XdataValue(I)
                resultString = "XData Type: " & XdataType(I) & "  Xdata Value: " & arrayData(0) & "," & arrayData(1) & "," & arrayData(2)
            Else
                resultString = "XData Type: " & XdataType(I) & "  Xdata Value: " & XdataValue(I)
End If
Debug.Print resultString   ' print all the xdata in the immedate window
        Next
    End If
End Sub
Public Sub Show_Group_names(GroupNames As Collection)
    frmGroupNames.lstGroupNames.Clear
    Dim x As Long
    For x = 1 To GroupNames.Count
        frmGroupNames.lstGroupNames.AddItem GroupNames.item(x)
    Next x
End Sub

Private Sub CommandButton1_Click()
    Dim anObj As AcadLine
    ' Initialize anObj variable to any object that supports
    ' setxdata method.  This example creates a line for that
    ' purpose
    Dim startpt(0 To 2) As Double, endpt(0 To 2) As Double
    startpt(0) = 0#: startpt(1) = 0#: startpt(2) = 0#
    endpt(0) = 5#: endpt(1) = 5#: endpt(2) = 0#
    Set anObj = ThisDrawing.ModelSpace.AddLine(startpt, endpt)

Dim dataType(0 To 9) As Integer
    Dim data(0 To 9) As Variant
    Dim reals3(0 To 2) As Double
    Dim worldPos(0 To 2) As Double
    ' Initialize all the xdata value. Note that first data in the list should be
    ' application name and first datatype code should be 1001
    dataType(0) = 1001: data(0) = "Another_Test_Application"
    dataType(1) = 1000: data(1) = "This is a test for xdata"

dataType(2) = 1003: data(2) = "0"               ' layer
    dataType(3) = 1040: data(3) = 1.23479137438413E+40          ' real
    dataType(4) = 1041: data(4) = 1237324938            ' distance
    dataType(5) = 1070: data(5) = 32767                 ' 16 bit Integer
    dataType(6) = 1071: data(6) = 32767                 ' 32 bit Integer
    dataType(7) = 1042: data(7) = 10                ' scaleFactor

reals3(0) = -2.95: reals3(1) = 100: reals3(2) = -20
    dataType(8) = 1010: data(8) = reals3                ' real
    worldPos(0) = 4: worldPos(1) = 400.99999999: worldPos(2) = 2.798989
    dataType(9) = 1011: data(9) = worldPos          ' world space position
    ' The following code attaches xdata to an object
    anObj.SetXdata dataType, data
End Sub

Private Sub CommandButton2_Click()
            Dim dType As Integer
            dType = 1000             ' hard line for testing
            dType = UCase(dType)
            Select Case dType
                Case dType = 1000
                    dType = 1000
                Case Else
                    dType = 1000       ' default type is string
            End Select
            ' attached it
            Dim dataType(0 To 1) As Integer
            Dim data(0 To 1) As Variant
            Dim reals3(0 To 2) As Double
            Dim worldPos(0 To 2) As Double
            ' Initialize all the xdata value. Note that first data in the list should be
            ' application name and first datatype code should be 1001
            dataType(0) = 1001: data(0) = "test app"
            dataType(1) = 1000: data(1) = "a sting"

            'dataType(2) = 1003: data(2) = "0"               ' layer
            '    dataType(3) = 1040: data(3) = 1.23479137438413E+40          ' real
            '    dataType(4) = 1041: data(4) = 1237324938            ' distance
            '   dataType(5) = 1070: data(5) = 32767                 ' 16 bit Integer
            '   dataType(6) = 1071: data(6) = 32767                 ' 32 bit Integer
            '   dataType(7) = 1042: data(7) = 10                ' scaleFactor

            reals3(0) = -2.95: reals3(1) = 100: reals3(2) = -20
            '    dataType(8) = 1010: data(8) = reals3                ' real
                worldPos(0) = 4: worldPos(1) = 400.99999999: worldPos(2) = 2.798989
            '    dataType(9) = 1011: data(9) = worldPos          ' world space position
            ' The following code attaches xdata to an object
    Me.Hide
    Dim Pnt As Variant
    Dim Ent As Object
    Call GetEnt(Ent, Pnt)
    Ent.SetXdata dataType, data

End Sub

Public Sub ShowVarTypes(XdataType, XdataValue)
' show the arrays variable types
    Dim I As Long
    Dim arrayData
    For I = LBound(XdataType) To UBound(XdataType)
        If (XdataType(I) = 1010) Or (XdataType(I) = 1011) Or (XdataType(I) = 1012) Or (XdataType(I) = 1013) Then
            arrayData = XdataValue(I)
            Debug.Print I & ": " & VarType(arrayData(0)) & "," & VarType(arrayData(1)) & "," & VarType(arrayData(2))
        Else
            Debug.Print I & ": " & VarType(XdataValue(I))
        End If
    Next I

End Sub
