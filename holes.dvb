Attribute VB_Name = "Circles"
' Entry macro for the Hole Charting example by Bill Kramer and John Gibb
'
' Hole Chart uses a user defined set of circles to create an ordered
' hole chart sorted by diameter and X,Y location.  This chart is very
' useful for checking machined parts as well as creating CNC code for
' a drilling center.
'
' Hole Chart uses the Holes and Hole classes (custom objects).  The
' circle data is read from the drawing and inserted into the Holes
' collection object.  The Holes collection object only contains entries
' for Hole objects.
'
Public Sub Chart()
  HoleChart.Circles
  HoleChart.Show
End Sub

Attribute VB_Name = "Hole"
Attribute VB_Base = "0{FCFB3D2A-A0FA-1068-A738-08002B3371B5}"
Attribute VB_Creatable = True
Attribute VB_PredeclaredId = False
Attribute VB_Exposed = False
Attribute VB_TemplateDerived = False
Attribute VB_Customizable = False
' Class definition of object HOLE.
'
' Defines elements of a single hole.
' All properties are private.
'
' Public Functions:
'   Get_Label()   -- return label as string
'   Get_Dia() -- return diamter value as double
'   Get_Rad() -- return radius value as double
'   Get_Operation() -- return operation integer code
'   Get_Point() -- returns center point as variant
'   Get_X() -- returns X value as double
'   Get_Y() -- returns Y value as double
'   Get_Z() -- returns Z value as double
'
' Public Subroutines:
'   Put_Label(L as String) -- place string in label property
'   Set_Dia(R as Double) -- place double in diameter property
'   Set_Operation(I as Integer) -- place integer in operation property
'   Set_Rad(R as Double) -- place double in diameter property
'   Set_Point(P as Variant) -- place variant in X, Y, Z properties
'   Set_Default(I as Integer) -- places integer in default type property
'   Set_X(R as Double) -- places double in X property
'   Set_Y(R as Double) -- places double in Y property
'   Set_Z(R as Double) -- places double in Z property
'   Round(I as Integer) -- round all doubles to I digits
'   Load_Circle(EN as AcadEntity) -- places properties of circle into hole properties
'   Draw() -- draws the circle with centerlines and offsets for tap
'
Private Lbl As String  'Hole label
Private Dia As Double  'Diameter of hole
Private X As Double    'X ordinate of center
Private Y As Double    'Y ordinate of center
Private Z As Double    'Z ordinate of center
Private Typ As Integer 'Hole type code 0 = drill, 1 = tap
Private Default_Typ As Integer 'Default type
'--------------------------------------------------------------------
Const A90 = 1.5707963 'Angle value 90 degrees
Const A270 = 4.712389 'Angle value 270 degrees
Const A180 = 3.1415927 'Angle value 180 degrees
'--------------------------------------------------------------------
Public Function Get_X() As Double
  Get_X = X
End Function
Public Function Get_Y() As Double
  Get_Y = Y
End Function
Public Function Get_Z() As Double
  Get_Z = Z
End Function
Public Function Get_Label()
  Get_Label = Lbl
End Function
Public Function Get_Dia() As Double
  Get_Dia = Dia
End Function
Public Function Get_Rad() As Double
  Get_Rad = Dia / 2#
End Function
Public Function Get_Operation() As Integer
  Get_Operation = Typ
End Function
Public Function Get_point() As Variant
  Dim P As Variant
  Dim PA(2) As Double
  PA(0) = X
  PA(1) = Y
  PA(2) = Z
  P = PA
  Get_point = P
End Function
'---------------------------------------------------
Public Sub Set_X(P As Double)
  X = P
End Sub
Public Sub Set_Y(P As Double)
  Y = P
End Sub
Public Sub Set_Z(P As Double)
  Z = P
End Sub
Public Sub Set_Dia(R As Double)
  If R > 0# Then
    Dia = R
  End If
End Sub
Public Sub Set_Operation(Ioper As Integer)
  If (Ioper = 0) Or (Ioper = 1) Then
    Typ = Ioper
  End If
End Sub
Public Sub Set_Rad(R As Double)
  If R > 0# Then
    Dia = R * 2#
  End If
End Sub
Public Sub Put_Label(L As String)
  Lbl = L
End Sub
Public Sub Set_Default(Ioper As Integer)
  If (Ioper = 0) Or (Ioper = 1) Then
     Default_Typ = Ioper
  End If
End Sub
Public Sub Set_Point(P As Variant)
  X = P(0)
  Y = P(1)
  Z = P(2)
End Sub
Public Sub Round(Prec As Integer)
  Dim Rnder As Double
  Dim Mtplr As Double
  If Num < 0# Then
     Rnder = -0.5
    Else
     Rnder = 0.5
  End If
  Mtplr = 10# ^ Prec
  X = Fix((X * Mtplr) + Rnder) / Mtplr
  Y = Fix((Y * Mtplr) + Rnder) / Mtplr
  Z = Fix((Z * Mtplr) + Rnder) / Mtplr
  Dia = Fix((Dia * Mtplr) + Rnder) / Mtplr
End Sub
Public Sub Load_Circle(EN As AcadEntity)
  Dim P As Variant
  Dim EN2 As AcadCircle
  Set EN2 = EN
  P = EN2.Center
  Set_Point P
  Dia = EN2.Diameter
  Typ = Default_Typ
End Sub
Public Sub Draw()
  Dim A1 As AcadCircle
  Dim A2 As AcadCircle
  Dim L1 As AcadLine
  Dim L2 As AcadLine
  Dim P As Variant
  Dim P1 As Variant
  Dim P2 As Variant
  Dim R2 As Double
  Dim TS As Double
  Dim ALayer As AcadLayer
  On Error Resume Next
  Set ALayer = ThisDrawing.Layers.Item("CENTER")
  If Err.Number <> 0 Then
    Err.Clear
    Set ALayer = ThisDrawing.Layers.Add("CENTER")
    ALayer.Color = acBlue
  End If
  If Typ = 0 Then
    ReDim Objs(2) As AcadEntity
   Else
    ReDim Objs(3) As AcadEntity
  End If
  Dim JJ As Integer
  P = Get_point()
  JJ = 0
  Rad = Dia / 2#
  Set A1 = ThisDrawing.ModelSpace.AddCircle(P, Rad)
  Set Objs(JJ) = A1
  JJ = JJ + 1
  If Typ <> 0 Then
     Set ALayer = ThisDrawing.Layers.Item("TAP")
     If Err.Number <> 0 Then
        Err.Clear
        Set ALayer = ThisDrawing.Layers.Add("TAP")
        ALayer.Color = acGreen
     End If
     R2 = Rad - Rad / 10#
     Set A2 = ThisDrawing.ModelSpace.AddCircle(P, R2)
     A2.Layer = "TAP"
     Set Objs(JJ) = A2
     JJ = JJ + 1
  End If
  R2 = (Rad * 0.1) + Rad
  P1 = ThisDrawing.Utility.PolarPoint(P, A270, R2)
  P2 = ThisDrawing.Utility.PolarPoint(P, A90, R2)
  Set L1 = ThisDrawing.ModelSpace.AddLine(P1, P2)
  P1 = ThisDrawing.Utility.PolarPoint(P, A180, R2)
  P2 = ThisDrawing.Utility.PolarPoint(P, 0#, R2)
  Set L2 = ThisDrawing.ModelSpace.AddLine(P1, P2)
  L1.Layer = "CENTER"
  L2.Layer = "CENTER"
  If Lbl <> "" Then
    Dim Pts(0 To 8) As Double
    TS = ThisDrawing.GetVariable("TEXTSIZE")
    P1 = ThisDrawing.Utility.PolarPoint(P, A90 / 2#, Rad)
    P2 = ThisDrawing.Utility.PolarPoint(P1, A90 / 2#, TS * 2#)
    Pts(0) = P1(0): Pts(1) = P1(1): Pts(2) = 0#
    Pts(3) = P2(0): Pts(4) = P2(1): Pts(5) = 0#
    P1 = ThisDrawing.Utility.PolarPoint(P2, 0#, TS * 3#)
    Pts(6) = P1(0): Pts(7) = P1(1): Pts(8) = 0#
    Dim Txt As AcadMText
    Set Txt = ThisDrawing.ModelSpace.AddMText(P1, 10#, Lbl)
    Set L3 = ThisDrawing.ModelSpace.AddLeader(Pts, Txt, acLineWithArrow)
  End If
  Set Objs(JJ) = L1
  Set Objs(JJ + 1) = L2
  SS1.AddItems Objs
End Sub

Attribute VB_Name = "HoleChart"
Attribute VB_Base = "0{8BB692E2-1CB6-11D3-A16C-00C0D1080326}{8BB692D8-1CB6-11D3-A16C-00C0D1080326}"
Attribute VB_Creatable = False
Attribute VB_PredeclaredId = True
Attribute VB_Exposed = False
Attribute VB_TemplateDerived = False
Attribute VB_Customizable = False
' Support Routines and data for the HoleChart form.
'
Dim Circs As New Holes  'Collection of circles
Dim Prec As Integer 'Precision for real numbers
Dim I As Integer 'GPI - General Purpose Integer
Dim Ahole As Hole 'A single hole object
Public SS1 As AcadSelectionSet 'Used to collect circles
Private Sub UserForm_Activate()
  'This is the main entry point for the user form.
  Paint_The_List 'display collection data in list box control
End Sub
Private Sub CommandButton1_Click()
  'Program finished.
  End
End Sub
Private Sub CommandButton2_Click()
  'Update list information from edit fields
  '
  ' Retrieve the entry index we are changing.
  I = ListBox1.ListIndex
  '
  ' Get hole object data from collection and put it
  ' into the hole object for manipulation. In this case
  ' to establish the base value of the hole we are
  ' updating.
  Set Ahole = Circs.Holes.Item(I)
  '
  ' Pass data from the form edit boxes to the
  ' the custom hole object.
  Ahole.Put_Label Label.Value
  Ahole.Set_X Val(XVal.Value)
  Ahole.Set_Y Val(YVal.Value)
  Ahole.Set_Z Val(Depth.Value)
  Ahole.Set_Dia Val(Dia.Value)
  Ahole.Set_Operation Oper.ListIndex
  '
  ' Update the hole object in the collection.
  Circs.Update Ahole, I
  '
  ' Update the display on the screen.
  Update_List Ahole, I
End Sub
Private Sub CommandButton3_Click()
  'Apply precision to entries in edit boxes
  XVal.Value = Round(Val(XVal.Value), Prec)
  YVal.Value = Round(Val(YVal.Value), Prec)
  Dia.Value = Round(Val(Dia.Value), Prec)
  Depth.Value = Round(Val(Depth.Value), Prec)
End Sub
Private Sub CommandButton4_Click()
  'Redraw the circles with labels
  If SS1.Count > 0 Then
     SS1.Erase
  End If
  Circs.Draw_Holes  'method to draw all holes
End Sub
Private Sub CommandButton5_Click()
  'fill in the labels with numbers
  For I = 1 To Circs.Count
     Set Ahole = Circs.Item(I) 'get hole data
     If Ahole.Get_Label = "" Then 'if empty label
        Ahole.Put_Label Str$(I) 'convert index into string and use it
        Update_List Ahole, I 'update collection data
        ListBox1.ListIndex = I 'update list on screen
     End If
  Next I
End Sub
Private Sub CommandButton6_Click()
  'Round all numbers in the list to the precision desired
  Circs.Round Prec
  Paint_The_List
End Sub
Private Sub CommandButton7_Click()
 'Draws a chart on the current drawing that contains all the
 'data from the holes objects.
 Dim A90 As Double
 Dim A180 As Double  'Set up constant angles for polar
 Dim A270 As Double
 A180 = 3.1415927
 A90 = A180 / 2#
 A270 = A180 * 1.5
 HoleChart.hide  'Move dialog box to background
 '
 Dim PT As Variant
 On Error Resume Next
 PT = ThisDrawing.Utility.GetPoint(, "Locate upper left corner of chart: ")
 If Err.Number = 0 Then
   Dim TS As Double
   TS = ThisDrawing.GetVariable("TEXTSIZE")
   Dim RS As Double
   RS = TS * 3# 'row size is three times text size
   Dim CS As Double
   CS = TS * 10# 'column size is 10 times text size
   Dim P1 As Variant
   Dim P2 As Variant
   Dim P3 As Variant
   Dim P4 As Variant
   P1 = PT 'P1 is upper left corner
   P2 = ThisDrawing.Utility.PolarPoint(P1, 0#, CS * 6#) 'P2 is upper right corner
   ThisDrawing.ModelSpace.AddLine P1, P2 'draw top line
   '
   ' P4 is set to top of chart, P3 to bottom of chart.
   P3 = ThisDrawing.Utility.PolarPoint(P1, A270, RS * (Circs.Count + 1))
   P4 = P1
   For I = 1 To 7 'draw each line in chart.
     ThisDrawing.ModelSpace.AddLine P4, P3
     P4(0) = P4(0) + CS 'increment by column spacing value
     P3(0) = P3(0) + CS
   Next I
   '
   ' advance to first row
   P1 = ThisDrawing.Utility.PolarPoint(P1, A270, RS)
   '
   For I = 0 To ListBox1.ListCount - 1
     P2(1) = P1(1)
     ThisDrawing.ModelSpace.AddLine P1, P2 'Line at bottom of row
     P3(0) = P1(0) + TS * 0.5 'locate starting text point
     P3(1) = P1(1) + TS * 0.75
     ' Generate text objects for each column entry
     ThisDrawing.ModelSpace.AddText ListBox1.List(I, 0), P3, TS
     P4 = ThisDrawing.Utility.PolarPoint(P3, 0#, CS)
     ThisDrawing.ModelSpace.AddText ListBox1.List(I, 1), P4, TS
     P4 = ThisDrawing.Utility.PolarPoint(P4, 0#, CS)
     ThisDrawing.ModelSpace.AddText ListBox1.List(I, 2), P4, TS
     P4 = ThisDrawing.Utility.PolarPoint(P4, 0#, CS)
     ThisDrawing.ModelSpace.AddText ListBox1.List(I, 3), P4, TS
     P4 = ThisDrawing.Utility.PolarPoint(P4, 0#, CS)
     ThisDrawing.ModelSpace.AddText ListBox1.List(I, 4), P4, TS
     P4 = ThisDrawing.Utility.PolarPoint(P4, 0#, CS)
     ThisDrawing.ModelSpace.AddText ListBox1.List(I, 5), P4, TS
     P1(1) = P1(1) - RS
   Next I
 End If
 Err.Clear
 HoleChart.Show
End Sub
Private Function Round(Num As Double, Prec As Integer) As Double
  'round a number in Num to the precision in Prec
  Dim Rnder As Double
  Dim Mtplr As Double
  If Num < 0# Then
     Rnder = -0.5
    Else
     Rnder = 0.5
  End If
  Mtplr = 10# ^ Prec
  Num = (Num * Mtplr) + Rnder
  Num = Fix(Num) / Mtplr
  Round = Num
End Function
Private Sub ListBox1_Click()
  'move list selection to edit boxes
  I = ListBox1.ListIndex
  Set Ahole = Circs.Item(I)
  Label.Value = Ahole.Get_Label
  XVal.Value = Ahole.Get_X
  YVal.Value = Ahole.Get_Y
  Dia.Value = Ahole.Get_Dia
  Depth.Value = Ahole.Get_Z
  Oper.ListIndex = Ahole.Get_Operation
End Sub
Private Sub Precision_Change()
  'save new precision value from list selection
  Prec = Precision.ListIndex
End Sub
Private Sub Paint_The_List()
  'Displays the list of holes found
  'Build an array that will hold the list of circles
  ReDim LoadArray(Circs.Count, 6)
  '
  'First row in array will be labels.
  LoadArray(0, 0) = "Label"
  LoadArray(0, 1) = "X"
  LoadArray(0, 2) = "Y"
  LoadArray(0, 3) = "Diameter"
  LoadArray(0, 4) = "Depth"
  LoadArray(0, 5) = "Operation"
  '
  'Move info to array to store in list box
  For I = 1 To Circs.Count
    Set Ahole = Circs.Item(I)
    LoadArray(I, 0) = Ahole.Get_Label
    LoadArray(I, 1) = Ahole.Get_X
    LoadArray(I, 2) = Ahole.Get_Y
    LoadArray(I, 3) = Ahole.Get_Dia
    LoadArray(I, 4) = Ahole.Get_Z
    If Ahole.Get_Operation = 0 Then
      LoadArray(I, 5) = "Drill"
      Else
      LoadArray(I, 5) = "Tap"
    End If
  Next I
  ListBox1.List() = LoadArray
  '
  ' Load fixed lists on screen
  '
  Oper.AddItem "Drill", 0
  Oper.AddItem "Tap", 1
  '
  Precision.AddItem "0", 0
  Precision.AddItem "0.0", 1
  Precision.AddItem "0.00", 2
  Precision.AddItem "0.000", 3
  Precision.AddItem "0.0000", 4
  Precision.AddItem "0.00000", 5
  Prec = 3
  Precision.ListIndex = 3
End Sub
Private Sub Update_List(Ahole As Hole, I As Integer)
  'Move hole information to listbox display
  ListBox1.List(I, 0) = Ahole.Get_Label
  ListBox1.List(I, 1) = Ahole.Get_X
  ListBox1.List(I, 2) = Ahole.Get_Y
  ListBox1.List(I, 3) = Ahole.Get_Dia
  ListBox1.List(I, 4) = Ahole.Get_Z
  If Ahole.Get_Operation = 0 Then
    ListBox1.List(I, 5) = "Drill"
    Else
    ListBox1.List(I, 5) = "Tap"
  End If
End Sub
Public Sub Circles()
   Dim Obj As AcadEntity
   On Error Resume Next
   Set SS1 = ThisDrawing.SelectionSets.Item("SS1")
   If Err.Number <> 0 Then
     Set SS1 = ThisDrawing.SelectionSets.Add("SS1")
   End If
   Err.Clear
   SS1.Clear
   HoleChart.hide
   ThisDrawing.Utility.Prompt "Select circles for hole chart"
   SS1.SelectOnScreen
   Dim J As Integer
   J = 0
   'Set Circs = New Holes
   For I = 0 To SS1.Count - 1
     Set Obj = SS1.Item(I)
     If Obj.ObjectName = "AcDbCircle" Then
       Set Ahole = New Hole
       Ahole.Load_Circle Obj
       Circs.Add Ahole
       J = J + 1
     End If
   Next I
End Sub

Attribute VB_Name = "Holes"
Attribute VB_Base = "0{FCFB3D2A-A0FA-1068-A738-08002B3371B5}"
Attribute VB_Creatable = True
Attribute VB_PredeclaredId = False
Attribute VB_Exposed = False
Attribute VB_TemplateDerived = False
Attribute VB_Customizable = False
' Class Definition of Object HOLES
'
' Collection object handling for Hole object.
'
'  Subroutines:
'    Add -- add a new hole to the collection, inserted into collection at proper location.
'    Count -- number of elements in the collection
'    Item -- retrieve item by index number
'    Draw_Holes -- draws all the holes in the collection using the Hole.Draw method
'    Update -- replaces entry in collection by index number
'    Round -- rounds all doubles in collection by precision amount
'
Public Holes As New Collection
Public Sub Add(Ahole As Hole)
  Dim I As Integer
  Dim BHole As Hole
  I = 1
  While I <= Holes.Count
    Set BHole = Holes.Item(I)
    If BHole.Get_Dia < Ahole.Get_Dia Then
        I = I + 1 'Diameter is less, advance one
      Else
      If BHole.Get_Dia > Ahole.Get_Dia Then
          Holes.Add Ahole, , I 'Diameter greater, insert before
          I = Holes.Count + 10
        Else 'Diameter equal
        If BHole.Get_X < Ahole.Get_X Then
          I = I + 1 'X is less, advance one
        Else
        If BHole.Get_X = Ahole.Get_X Then
          If BHole.Get_Y < Ahole.Get_Y Then
            I = I + 1
           Else
            Holes.Add Ahole, , I
            I = Holes.Count + 10
          End If
          Else
            Holes.Add Ahole, , I
            I = Holes.Count + 10
        End If
        End If
      End If
    End If
  Wend
  If (Holes.Count + 10) <> I Then
    Holes.Add Ahole
  End If
End Sub
Public Function Count() As Integer
   Count = Holes.Count
End Function
Public Function Item(I As Integer) As Hole
   Set Item = Holes.Item(I)
End Function
Public Sub Draw_Holes()
 Dim Ahole As Hole
 If Holes.Count > 0 Then
   For I = 1 To Holes.Count
      Set Ahole = Holes.Item(I)
      Ahole.Draw
   Next I
 End If
End Sub
Public Sub Update(Ahole As Hole, I As Integer)
  Holes.Remove I
  If I <= Holes.Count Then
     Holes.Add Ahole, , I
     Else
     Holes.Add Ahole
  End If
End Sub
Public Sub Round(Prec As Integer)
  Dim Ahole As Hole
  Dim I As Integer
  For I = 1 To Holes.Count
    Set Ahole = Holes.Item(I)
    Ahole.Round Prec
    Update Ahole, I
  Next I
End Sub
