Attribute VB_Name = "Module1"
'  ad_CloseAllDwgs
'
'  This routine closes all currently open drawings and saves them or not
'     according to user input.
'  Demand load:  -vbarun;ad_CloseAllDwgs.dvb!ad_CloseAllDwgs;
'
'  version 1.00
'  7/22/2000
'  9/28/2000 - Updated Save method
'
'  Copyright©2000 ActiveDwg.com
'
'
Option Explicit

Public Sub ad_CloseAllDwgs()
'  This routine is provided for demonstration purposes only and must
'    not be used for critical applications without your verification
'    that this routine will perform as you intended.
'  This routine may be freely utilized for your own personal use so long
'    as the entire contents of this header remain intact.
'  This routine is provided "as-is" and no declaration, written or implied,
'    is made as to its reliability for any particular task. Any use of this
'    routine is solely at your own risk.

    Dim Drawing As AcadDocument
    Dim StrMsg As String
    Dim StrTitle As String
    Dim Response

'    On Error Resume Next
    If Documents.Count = 0 Then
        MsgBox "No drawings to close!"
        Exit Sub
    End If
    StrMsg = "Save all drawings before closing?"
    StrTitle = "Verify Close Mode"
    Response = MsgBox(StrMsg, vbYesNo, StrTitle)
    If Response = vbYes Then
        For Each Drawing In Documents
            Drawing.Save
            Drawing.Close
        Next
    Else
        For Each Drawing In Documents
            Drawing.Close (False)
        Next
    End If
End Sub
