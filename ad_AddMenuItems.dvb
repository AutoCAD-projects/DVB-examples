Attribute VB_Name = "Module1"
'
'  ad_AddMenuItems
'
'  This routine demonstrates adding a new menu item in the 'Edit' pull-down
'     menu and adding a new toolbar and button.
'  It was developed in AutoCAD 2000.
'
'  version 1.00
'  5/17/2001
'
'  Copyright©2001 ActiveDwg.com
'
'  This routine is provided for demonstration purposes only and must
'    not be used for critical applications without your verification
'    that this routine will perform as you intended.
'  This routine may be freely utilized for your own personal use so long
'    as the entire contents of this header remain intact.
'  This routine is provided "as-is" and no declaration, written or implied,
'    is made as to its reliability for any particular task. Any use of this
'    routine is solely at your own risk.
'
Option Explicit

Sub ad_AddMenuItems()
  Dim objMenu As AcadPopupMenu
  Dim newMenuItem As AcadPopupMenuItem
  Dim MenuMacro As String
  Dim objToolbar As AcadToolbar
  Dim objToolbarButton As AcadToolbarItem
  Dim ButtonName As String
  Dim objMenuGroup As AcadMenuGroup
  Dim MenuName As String
  Dim SmallBitmap As String
  Dim LargeBitmap As String
  On Error GoTo MENU_ERROR
    
'Create a menu item in the 'Edit' group
  Set objMenu = ThisDrawing.Application.MenuBar.Item("&Edit")
  MenuMacro = "Line "
  MenuName = "Acad"
  Set newMenuItem = objMenu.AddMenuItem(objMenu.Count + 1, "adMenu Item", MenuMacro)
 
'Create a toolbar and button
  ThisDrawing.Application.MenuGroups(MenuName).Toolbars.Add "MyToolBar"
  ButtonName = "MyButton"
  Set objToolbar = ThisDrawing.Application.MenuGroups(MenuName).Toolbars("MyToolBar")
  Set objToolbarButton = objToolbar.AddToolbarButton(1, "MyButton", "Draws a Line", MenuMacro)
 
'To add a bitmap to the new toolbar button, you need to have two icons available. One for
'  the small format is 16x16 pixels, and one for the large format is 32x32 pixels. They
'  should be available in AutoCAD's search path or you need to hard-wire the path.
'Also, be sure to uncomment these lines and the bitmap 'Dim' lines above.

'  SmallBitmap = "FrzLayer.bmp"
'  LargeBitmap = "Erase.bmp"
'  objToolbarButton.SetBitmaps SmallBitmap, LargeBitmap

'Save the menu file
'    Set objMenuGroup = ThisDrawing.Application.MenuGroups(MenuName)
'    objMenuGroup.Save acMenuFileSource
    
  Exit Sub

MENU_ERROR:
  MsgBox Err.Description

End Sub
