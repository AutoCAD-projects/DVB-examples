Attribute VB_Name = "basGlobal"
Option Explicit
Declare Function GetWindowsDirectory Lib "kernel32" Alias "GetWindowsDirectoryA" (ByVal lpBuffer As String, ByVal nSize As Long) As Long
Public Const gintMaxSize As Integer = 50
Public Const gconSEP_DIR As String = "\"

Public Sub IOEXAMPLE()
    Stop
    Dim strFilePath As String
    Dim lngResult, nSize As Long
    strFilePath = Space$(gintMaxSize)               ' make the string a set size
    nSize = gintMaxSize                             ' var to tell function the size
    lngResult = GetWindowsDirectory(strFilePath, nSize) ' get the Windows directory
    If lngResult > 0 Then                           ' Found if result above 0
        strFilePath = StripTerminator$(strFilePath) ' remove junk from end of string
        strFilePath = AddDirSep(strFilePath)        ' add a backslash if necessary
        ' Only proceed if file not already there
        If Len(Dir(strFilePath & "abcdef.$$$")) = 0 Then
            Dim dblFh As Double
            ' open for writing
            dblFh = FreeFile                        ' Get next available file handle
            Open strFilePath & "abcdef.$$$" For Output As dblFh
            Print #dblFh, "[Section Header]"        ' print a line
            Print #dblFh, "key=67890"               ' print a line
            Close dblFh                             ' close the file
            ' open for reading
            dblFh = FreeFile                        ' Get next available file handle
            Open strFilePath & "abcdef.$$$" For Input Access Read As dblFh
            Dim colFileLines As New Collection
            Dim strTextLine As String
            While Not EOF(dblFh)                    ' read until end of file
                Line Input #dblFh, strTextLine      ' read a line
                colFileLines.Add strTextLine        ' into a collection
            Wend
            Close dblFh                             ' close file for reading
            Dim lngCnt As Long
            Dim strMessage As String
            lngCnt = 0
            Do                                 ' build a message from the colection
                lngCnt = lngCnt + 1
                strMessage = strMessage & colFileLines.Item(lngCnt) & vbCrLf
            Loop Until lngCnt = colFileLines.Count
            MsgBox strMessage, , "File contents"    ' show the message
            Kill strFilePath & "abcdef.$$$"         ' remove the file
        End If
    End If
End Sub
Function StripTerminator(ByVal strString As String) As String
' returns the string with out the terminator or any characters following it
' or it returns the original string when no terminator present
    Dim intZeroPos As Integer

    intZeroPos = InStr(strString, Chr$(0))                  'get terminators position
    If intZeroPos > 0 Then
        StripTerminator = Left$(strString, intZeroPos - 1)  'get up to it
    Else
        StripTerminator = strString                         ' no, return the string
    End If
End Function
Public Function AddDirSep(strPathName As String) As String
' adds a backslash to the end of a directory string
' gstrSEP_DIR is a global constant
    If Right$(RTrim$(strPathName), Len(gconSEP_DIR)) <> gconSEP_DIR Then
        strPathName = RTrim$(strPathName) & gconSEP_DIR     ' add it when not on the end
    End If
    AddDirSep = strPathName
End Function
