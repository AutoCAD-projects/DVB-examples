Attribute VB_Name = "DevelopersGuide_Examples"
'      AutoCAD 2000
'
'      DevelopersGuide_Examples Code Module
'
'      Example code for all Methods and Properties
'      ActiveX Automation and VBA Samples.
'
'      Copyright (C) 1999 by Autodesk, Inc.
'
'      Permission to use, copy, modify, and distribute this software
'      for any purpose and without fee is hereby granted, provided
'      that the above copyright notice appears in all copies and
'      that both that copyright notice and the limited warranty and
'      restricted rights notice below appear in all supporting
'      documentation.
'
'      AUTODESK PROVIDES THIS PROGRAM "AS IS" AND WITH ALL FAULTS.
'      AUTODESK SPECIFICALLY DISCLAIMS ANY IMPLIED WARRANTY OF
'      MERCHANTABILITY OR FITNESS FOR A PARTICULAR USE.  AUTODESK, INC.
'      DOES NOT WARRANT THAT THE OPERATION OF THE PROGRAM WILL BE
'      UNINTERRUPTED OR ERROR FREE.
'
'      Use, duplication, or disclosure by the U.S. Government is subject to
'      restrictions set forth in FAR 52.227-19 (Commercial Computer
'      Software - Restricted Rights) and DFAR 252.227-7013(c)(1)(ii)
'      (Rights in Technical Data and Computer Software), as applicable.
'
Option Explicit
Public Sub Ch1_HelloWorld()
ThisDrawing.Application.Documents.Add

Dim insPoint(0 To 2) As Double 'Declare insertion point
Dim textHeight As Double       'Declare text height
Dim textStr As String          'Declare text string
Dim textObj As AcadText        'Declare text object

insPoint(0) = 2      'Set insertion point x coordinate
insPoint(1) = 4      'Set insertion point y coordinate
insPoint(2) = 0      'Set insertion point z coordinate

textHeight = 1                  'Set text height to 1.0
textStr = "Hello World!"        'Set the text string

'Create the Text object
Set textObj = ThisDrawing.ModelSpace.AddText _
          (textStr, insPoint, textHeight)
ThisDrawing.SaveAs ("Hello.dwg")
End Sub
Sub Ch2_IterateLayer()
    ' Iterate through the collection
    On Error Resume Next
    
    Dim I As Integer
    Dim msg As String
    msg = ""
    For I = 0 To ThisDrawing.Layers.count - 1
        msg = msg + ThisDrawing.Layers.Item(I).name + vbCrLf
    Next
    MsgBox msg
End Sub
Sub Ch2_FindLayerABC()
    ' Use the Item method to find a layer named "ABC"
    On Error Resume Next

    Dim ABCLayer As AcadLayer
    Set ABCLayer = ThisDrawing.Layers.Item("ABC")
    If Err <> 0 Then
        MsgBox "The layer 'ABC' does not exist."
    End If
End Sub
Sub Ch2_FindFirstEntity()
    ' This example returns the first entity in model space
    On Error Resume Next
    
    Dim entity As AcadEntity
    If ThisDrawing.ModelSpace.count <> 0 Then
        Set entity = ThisDrawing.ModelSpace.Item(0)
        MsgBox entity.ObjectName + _
            " is the first entity in model space."
    Else
        MsgBox "There are no objects in model space."
    End If
End Sub
Sub Ch2_CreateSplineUsingTypedArray()
    ' This example creates a spline object in model space
    ' using the CreateTypedArray method.
    Dim splineObj As AcadSpline
    Dim startTan As Variant
    Dim endTan As Variant
    Dim fitPoints As Variant
    Dim noOfPoints As Integer
    
    Dim utilObj As Object   ' late bind the Utility object
    Set utilObj = ThisDrawing.Utility
    
    ' Define the Spline Object
    utilObj.CreateTypedArray _
                startTan, vbDouble, 0.5, 0.5, 0
    utilObj.CreateTypedArray _
                endTan, vbDouble, 0.5, 0.5, 0
    utilObj.CreateTypedArray _
                fitPoints, vbDouble, 0, 0, 0, 5, 5, 0, 10, 0, 0
    noOfPoints = 3
    
    Set splineObj = ThisDrawing.ModelSpace.AddSpline _
                (fitPoints, startTan, endTan)
    
    ' Zoom in on the newly created spline
    ZoomAll
    
End Sub
Sub Ch2_CalculateDistance()
    Dim point1 As Variant
    Dim point2 As Variant
    
    ' Get the points from the user
    point1 = ThisDrawing.Utility.GetPoint _
                (, vbCrLf & "First point: ")
    point2 = ThisDrawing.Utility.GetPoint _
                (point1, vbCrLf & "Second point: ")
    
    ' Calculate the distance between point1 and point2
    Dim x As Double, y As Double, z As Double
    Dim dist As Double
    x = point1(0) - point2(0)
    y = point1(1) - point2(1)
    z = point1(2) - point2(2)
    dist = Sqr((Sqr((x ^ 2) + (y ^ 2)) ^ 2) + (z ^ 2))
    
    'Display the resulting distance
    MsgBox "The distance between the points is: " _
                  & dist, , "Calculate Distance"
End Sub
Sub Ch2_ConnectToAcad()
    Dim ACADApp As AcadApplication
    On Error Resume Next
    
    Set ACADApp = GetObject(, "AutoCAD.Application")
    If Err Then
        Err.Clear
        Set ACADApp = CreateObject("AutoCAD.Application")
        If Err Then
            MsgBox Err.Description
            Exit Sub
        End If
    End If
    MsgBox "Now running " + ACADApp.name + _
           " version " + ACADApp.version
End Sub
Sub Ch2_AddLineVBA()
    ' This example adds a line
    ' in model space
    Dim lineObj As AcadLine
    Dim startPoint(0 To 2) As Double
    Dim endPoint(0 To 2) As Double
    
    ' Define the start and end
    ' points for the line
    startPoint(0) = 1
    startPoint(1) = 1
    startPoint(2) = 0
    endPoint(0) = 5
    endPoint(1) = 5
    endPoint(2) = 0
    
    ' Create the line in model space
    Set lineObj = ThisDrawing. _
        ModelSpace.AddLine _
        (startPoint, endPoint)
        
    ' Zoom in on the newly created line
    ZoomAll
End Sub
Sub Ch2_AddLineVB()
    On Error Resume Next
    
    ' Connect to the AutoCAD application
    Dim ACADApp As AcadApplication
    Set ACADApp = GetObject _
                  (, "AutoCAD.Application")
    If Err Then
        Err.Clear
        Set ACADApp = CreateObject _
                  ("AutoCAD.Application")
        If Err Then
            MsgBox Err.Description
            Exit Sub
        End If
    End If
    
    ' Connect to the AutoCAD drawing
    Dim acadDoc As AcadDocument
    Set acadDoc = ACADApp.ActiveDocument
    
    ' Establish the endpoints of the line
    Dim lineObj As AcadLine
    Dim startPoint(0 To 2) As Double
    Dim endPoint(0 To 2) As Double
    startPoint(0) = 1
    startPoint(1) = 1
    startPoint(2) = 0
    endPoint(0) = 5
    endPoint(1) = 5
    endPoint(2) = 0
    ' Create a Line object in model space
    Set lineObj = acadDoc.ModelSpace.AddLine _
                         (startPoint, endPoint)
    ZoomAll
End Sub
Sub Ch3_OpenDrawing()
    Dim dwgName As String
    dwgName = "c:\Program Files\acad2000\sample\campus.dwg"
    If Dir(dwgName) <> "" Then
        ThisDrawing.Application.Documents.Open dwgName
    Else
        MsgBox "File " & dwgName & " does not exist."
    End If
End Sub
Sub Ch3_NewDrawing()
    Dim docObj As AcadDocument
    Set docObj = ThisDrawing.Application.Documents.Add
End Sub
Sub Ch3_SaveActiveDrawing()
    ' Save the active drawing under the current name
    ThisDrawing.Save
    
    ' Save the active drawing under a new name
    ThisDrawing.SaveAs "MyDrawing.dwg"
End Sub
Sub Ch3_TestIfSaved()
    If Not (ThisDrawing.Saved) Then
        If MsgBox("Do you wish to save this drawing?", _
                   vbYesNo) = vbYes Then
            ThisDrawing.Save
        End If
    End If
End Sub
Sub Ch3_PositionApplicationWindow()
    ThisDrawing.Application.WindowTop = 0
    ThisDrawing.Application.WindowLeft = 0
    ThisDrawing.Application.width = 400
    ThisDrawing.Application.height = 400
End Sub
Sub Ch3_CurrentWindowState()
    Dim CurrWindowState As Integer
    Dim msg As String
    CurrWindowState = ThisDrawing.Application.WindowState
    msg = Choose(CurrWindowState, "normal", _
                 "minimized", "maximized")
    
    MsgBox "The application window is " + msg
End Sub

Sub Ch3_ZoomWindow()
    ' ZoomWindow
    MsgBox "Perform a ZoomWindow with:" & vbCrLf & _
           "1.3, 7.8, 0" & vbCrLf & _
           "13.7, -2.6, 0", , "ZoomWindow"
           
    Dim point1(0 To 2) As Double
    Dim point2(0 To 2) As Double
    point1(0) = 1.3: point1(1) = 7.8: point1(2) = 0
    point2(0) = 13.7: point2(1) = -2.6: point2(2) = 0
    ThisDrawing.Application.ZoomWindow point1, point2
    ' ZoomPickWindow
    MsgBox "Perform a ZoomPickWindow", , "ZoomPickWindow"
    
    ThisDrawing.Application.ZoomPickWindow
End Sub
Sub Ch3_ZoomScaled()
    MsgBox "Perform a ZoomScaled using:" & vbCrLf & _
           "Scale Type: acZoomScaledRelative" & vbCrLf & _
           "Scale Factor: 2", , "ZoomScaled"
           
    Dim scalefactor As Double
    Dim scaletype As Integer
    
    scalefactor = 2
    scaletype = acZoomScaledRelative
    
    ThisDrawing.Application.ZoomScaled scalefactor, scaletype
End Sub
Sub Ch3_ZoomCenter()
    MsgBox "Perform a ZoomCenter using:" & vbCrLf & _
           "Center 3, 3, 0" & vbCrLf & _
           "Magnification: 10", , "ZoomCenter"
           
    Dim center(0 To 2) As Double
    Dim magnification As Double
    
    center(0) = 3: center(1) = 3: center(2) = 0
    magnification = 10
    
    ThisDrawing.Application.ZoomCenter center, magnification
End Sub
Sub Ch3_ZoomAll()
' ZoomAll
    MsgBox "Perform a ZoomAll", , "ZoomAll"
    ThisDrawing.Application.ZoomAll
    
' ZoomExtents
    MsgBox "Perform a ZoomExtents", , "ZoomExtents"
    ThisDrawing.Application.ZoomExtents
End Sub
Sub Ch3_AddView()
    ' Add a named view to the views collection
    Dim viewObj As AcadView
    Set viewObj = ThisDrawing.Views.Add("View1")
End Sub
Sub Ch3_IteratingViewportWindows()
    ' Create a new viewport and make it active
    Dim vportObj As AcadViewport
    Set vportObj = ThisDrawing.Viewports.Add("TEST_VIEWPORT")
    ThisDrawing.ActiveViewport = vportObj
    
    ' Split vport into 4 windows
    vportObj.Split acViewport4
    
    ' Iterate through the viewports,
    ' highlighting each viewport and displaying
    ' the upper right and lower left corners
    ' for each.
    Dim vport As AcadViewport
    Dim LLCorner As Variant
    Dim URCorner As Variant
    For Each vport In ThisDrawing.Viewports
        ThisDrawing.ActiveViewport = vport
        LLCorner = vport.LowerLeftCorner
        URCorner = vport.UpperRightCorner
        MsgBox "Viewport: " & vport.name & " is now active." & _
                vbCrLf & "Lower left corner: " & _
                LLCorner(0) & ", " & LLCorner(1) & vbCrLf & _
                "Upper right corner: " & _
                URCorner(0) & ", " & URCorner(1)
    Next vport
End Sub
Sub Ch3_UpdateDisplay()
    Dim circleObj As AcadCircle
    Dim center(0 To 2) As Double
    Dim radius As Double
    center(0) = 1: center(1) = 1: center(2) = 0
    radius = 1
    
    ' Create the circle and then color it red
    Set circleObj = ThisDrawing.ModelSpace.AddCircle(center, radius)
    circleObj.Color = acRed
    
    ' Update the circle
    circleObj.Update
End Sub
Sub Ch3_ResetActiveViewport()
    ' Toggle the setting of the grid display
    ' for the active viewport
    ThisDrawing.ActiveViewport.GridOn = _
              Not (ThisDrawing.ActiveViewport.GridOn)
    
    ' Reset the active viewport
    ThisDrawing.ActiveViewport = ThisDrawing.ActiveViewport
End Sub
Sub Ch3_ChangeSnapBasePoint()
    ' Turn on the grid for the active viewport
    ThisDrawing.ActiveViewport.GridOn = True
    
    ' Change the snap base point to 1, 1
    Dim newBasePoint(0 To 1) As Double
    newBasePoint(0) = 1: newBasePoint(1) = 1
    ThisDrawing.ActiveViewport.SnapBasePoint = newBasePoint
    
    ' Change the snap rotation angle to 30 degrees (0.575 radians)
    Dim rotationAngle As Double
    rotationAngle = 0.575
    ThisDrawing.ActiveViewport.SnapRotationAngle = rotationAngle
    
    ' reset the viewport
    ThisDrawing.ActiveViewport = ThisDrawing.ActiveViewport
End Sub
Sub Ch3_AddXLine()
    Dim xlineObj As AcadXline
    Dim basePoint(0 To 2) As Double
    Dim directionVec(0 To 2) As Double
    
    ' Define the xline
    basePoint(0) = 2#: basePoint(1) = 2#: basePoint(2) = 0#
    directionVec(0) = 1#: directionVec(1) = 1#: directionVec(2) = 0#
    
    ' Create the xline in model space
    Set xlineObj = ThisDrawing.ModelSpace.AddXline _
                   (basePoint, directionVec)
    ThisDrawing.Application.ZoomAll
End Sub
Sub Ch3_EditRay()
    Dim rayObj As AcadRay
    Dim basePoint(0 To 2) As Double
    Dim SecondPoint(0 To 2) As Double
    
    ' Define the ray
    basePoint(0) = 3#: basePoint(1) = 3#: basePoint(2) = 0#
    SecondPoint(0) = 4#: SecondPoint(1) = 4#: SecondPoint(2) = 0#
    
    ' Creates a Ray object in model space
    Set rayObj = ThisDrawing.ModelSpace.AddRay _
                 (basePoint, SecondPoint)
    ThisDrawing.Application.ZoomAll
    
    ' Find the current status of the Ray
    MsgBox "The base point of the ray is: " & _
            rayObj.basePoint(0) & ", " & _
            rayObj.basePoint(1) & ", " & _
            rayObj.basePoint(2) & vbCrLf & _
            "The directional vector for the ray is: " & _
           rayObj.DirectionVector(0) & ", " & _
           rayObj.DirectionVector(1) & ", " & _
           rayObj.DirectionVector(2), , "Edit Ray"
           
    ' Change the directional vector for the ray
    Dim newVector(0 To 2) As Double
    newVector(0) = -1
    newVector(1) = 1
    newVector(2) = 0
    rayObj.DirectionVector = newVector
    ThisDrawing.Regen False
    MsgBox "The base point of the ray is: " & _
            rayObj.basePoint(0) & ", " & _
            rayObj.basePoint(1) & ", " & _
            rayObj.basePoint(2) & vbCrLf & _
            "The directional vector for the ray is: " & _
           rayObj.DirectionVector(0) & ", " & _
           rayObj.DirectionVector(1) & ", " & _
           rayObj.DirectionVector(2), , "Edit Ray"
End Sub
Sub Ch3_GetDistanceBetweenTwoPoints()
    Dim returnDist As Double
        
    ' Return the value entered by user. A prompt is provided.
    returnDist = ThisDrawing.Utility.GetDistance _
                 (, "Pick two points.")
    MsgBox "The distance between the two points is: " & returnDist
End Sub
Sub Ch3_CalculateDefinedArea()
    Dim p1 As Variant
    Dim p2 As Variant
    Dim p3 As Variant
    Dim p4 As Variant
    Dim p5 As Variant
    
    ' Get the points from the user
    p1 = ThisDrawing.Utility.GetPoint(, vbCrLf & "First point: ")
    p2 = ThisDrawing.Utility.GetPoint(p1, vbCrLf & "Second point: ")
    p3 = ThisDrawing.Utility.GetPoint(p2, vbCrLf & "Third point: ")
    p4 = ThisDrawing.Utility.GetPoint(p3, vbCrLf & "Fourth point: ")
    p5 = ThisDrawing.Utility.GetPoint(p4, vbCrLf & "Fifth point: ")
    
    ' Create the 2D polyline from the points
    Dim polyObj As AcadLWPolyline
    Dim vertices(0 To 9) As Double
    vertices(0) = p1(0): vertices(1) = p1(1)
    vertices(2) = p2(0): vertices(3) = p2(1)
    vertices(4) = p3(0): vertices(5) = p3(1)
    vertices(6) = p4(0): vertices(7) = p4(1)
    vertices(8) = p5(0): vertices(9) = p5(1)
    Set polyObj = ThisDrawing.ModelSpace.AddLightWeightPolyline _
                  (vertices)
    polyObj.Closed = True
    ThisDrawing.Application.ZoomAll
    
    ' Display the area for the polyline
    MsgBox "The area defined the by points is " & _
            polyObj.Area, , "Calculate Defined Area"
End Sub
Sub Ch3_GetStringFromUser()
    Dim retVal As String
    retVal = ThisDrawing.Utility.GetString _
             (1, vbCrLf & "Enter your name: ")
    MsgBox "The name entered was: " & retVal
End Sub
Sub Ch3_GetPointsFromUser()
    Dim startPnt As Variant
    Dim endPnt As Variant
    Dim prompt1 As String
    Dim prompt2 As String
    
    prompt1 = vbCrLf & "Enter the start point of the line: "
    prompt2 = vbCrLf & "Enter the end point of the line: "
    
    ' Get the first point without entering a base point
    startPnt = ThisDrawing.Utility.GetPoint(, prompt1)
    
    ' Use the point entered above as the base point
    endPnt = ThisDrawing.Utility.GetPoint(startPnt, prompt2)
    
    ' Create a line using the two points entered
    ThisDrawing.ModelSpace.AddLine startPnt, endPnt
    ThisDrawing.Application.ZoomAll
End Sub
Sub Ch3_KeyWord()
    Dim keyWord As String
    ThisDrawing.Utility.InitializeUserInput 1, "Line Circle Arc"
    keyWord = ThisDrawing.Utility.GetKeyword _
              (vbCrLf & "Enter an option (Line/Circle/Arc): ")
    MsgBox keyWord, , "GetKeyword Example"
End Sub
Sub Ch3_KeyWord2()
    Dim keyWord As String
    ThisDrawing.Utility.InitializeUserInput 0, "Line Circle Arc"
    keyWord = ThisDrawing.Utility.GetKeyword _
              (vbCrLf & "Enter an option (Line/Circle/<Arc>): ")
    If keyWord = "" Then keyWord = "Arc"
    MsgBox keyWord, , "GetKeyword Example"
End Sub
Sub Ch3_UserInput()
    ' The first parameter of InitializeUserInput (6)
    ' restricts input to positive and non-negative
    ' values. The second parameter is the list of
    ' valid keywords.
    ThisDrawing.Utility.InitializeUserInput 6, "Big Small Regular"
    ' Set the prompt string variable
    Dim promptStr As String
    promptStr = vbCrLf & "Enter the size or (Big/Small/<Regular>):"
    ' Entering a keyword at the GetInteger prompt causes
    ' an error; therefore to allow your application to
    ' continue and check for the error description you
    ' must set the error handler to resume on error.
    On Error Resume Next
    
    ' Get the value entered by the user
    Dim returnInteger As Integer
    returnInteger = ThisDrawing.Utility.GetInteger(promptStr)
    ' Check for an error. If the error description matches the
    ' one shown below, then use GetInput to get the returned
    ' string; otherwise, use the value of returnInteger.
    If Err.Description = "User input is a keyword" Then
        Dim returnString As String
        returnString = ThisDrawing.Utility.GetInput()
        Err.Clear
    Else
        If returnInteger = 0 Then         'If user pressed ENTER
            returnString = "Regular"      'Set to default
        Else                              'Otherwise,
            returnString = returnInteger  'Use the value entered
        End If
    End If
    ' Display the result
    MsgBox returnString, , "InitializeUserInput Example"
End Sub
Sub Ch3_SendACommandToAutoCAD()
   ThisDrawing.SendCommand "_Circle 2,2,0 4 "
   ThisDrawing.SendCommand "_zoom a "
End Sub
Sub Ch3_ImportingAndExporting()

    ' Create the circle for visual representation
    Dim circleObj As AcadCircle
    Dim centerPt(0 To 2) As Double
    Dim radius As Double
    centerPt(0) = 2: centerPt(1) = 2: centerPt(2) = 0
    radius = 1
    Set circleObj = ThisDrawing.ModelSpace.AddCircle _
                    (centerPt, radius)
    ThisDrawing.Application.ZoomAll
    
    ' Create an empty selection set
    Dim sset As AcadSelectionSet
    Set sset = ThisDrawing.SelectionSets.Add("NEWSSET")
    ' Export the current drawing to the file specified above.
    Dim exportFile As String
    exportFile = "C:\AutoCAD\DXFExprt"
    ThisDrawing.Export exportFile, "DXF", sset
    
    ' Open a new drawing
    ThisDrawing.Application.Documents.Add "acad.dwt"
    
    ' Define the import
    Dim importFile As String
    Dim InsertPoint(0 To 2) As Double
    Dim scalefactor As Double
    importFile = "C:\AutoCAD\DXFExprt.dxf"
    InsertPoint(0) = 0: InsertPoint(1) = 0: InsertPoint(2) = 0
    scalefactor = 2#
    
    ' Import the file
    ThisDrawing.Import importFile, InsertPoint, scalefactor
    ThisDrawing.Application.ZoomAll
    
End Sub
Sub Ch4_AddLightWeightPolyline()
    Dim plineObj As AcadLWPolyline
    Dim points(0 To 5) As Double
    
    ' Define the 2D polyline points
    points(0) = 2: points(1) = 4
    points(2) = 4: points(3) = 2
    points(4) = 6: points(5) = 4
    
    ' Create a light weight Polyline object in model space
    Set plineObj = ThisDrawing.ModelSpace. _
                   AddLightWeightPolyline(points)
    ThisDrawing.Application.ZoomAll
End Sub
Sub Ch4_CreateSpline()
    ' This example creates a spline object in model space.
    ' Declare the variables needed
    Dim splineObj As AcadSpline
    Dim noOfPoints As Integer
    Dim startTan(0 To 2) As Double
    Dim endTan(0 To 2) As Double
    Dim fitPoints(0 To 8) As Double
    
    ' Define the variables
    noOfPoints = 3
    startTan(0) = 0.5: startTan(1) = 0.5: startTan(2) = 0
    endTan(0) = 0.5: endTan(1) = 0.5: endTan(2) = 0
    fitPoints(0) = 1: fitPoints(1) = 1: fitPoints(2) = 0
    fitPoints(3) = 5: fitPoints(4) = 5: fitPoints(5) = 0
    fitPoints(6) = 10: fitPoints(7) = 0: fitPoints(8) = 0
    
    ' Create the spline
    Set splineObj = ThisDrawing.ModelSpace.AddSpline _
                        (fitPoints, startTan, endTan)
    ZoomAll
End Sub
Sub Ch4_CreatePoint()
    Dim pointObj As AcadPoint
    Dim location(0 To 2) As Double
    
    ' Define the location of the point
    location(0) = 5#: location(1) = 5#: location(2) = 0#
    
    ' Create the point
    Set pointObj = ThisDrawing.ModelSpace.AddPoint(location)
    ThisDrawing.SetVariable "PDMODE", 34
    ThisDrawing.SetVariable "PDSIZE", 1
    ZoomAll
End Sub
Sub Ch4_CreateSolid()
    Dim solidObj As AcadSolid
    Dim point1(0 To 2) As Double
    Dim point2(0 To 2) As Double
    Dim point3(0 To 2) As Double
    Dim point4(0 To 2) As Double
    
    ' Define the solid
    point1(0) = 0#: point1(1) = 0#: point1(2) = 0#
    point2(0) = 5#: point2(1) = 0#: point2(2) = 0#
    point3(0) = 5#: point3(1) = 8#: point3(2) = 0#
    point4(0) = 0#: point4(1) = 8#: point4(2) = 0#
    ' Create the solid object in model space
    Set solidObj = ThisDrawing.ModelSpace.AddSolid _
                   (point1, point2, point3, point4)
    ZoomAll
End Sub
Sub Ch4_CreateRegion()
    ' Define an array to hold the
    ' boundaries of the region.
    Dim curves(0 To 0) As AcadCircle
    
    ' Create a circle to become a
    ' boundary for the region.
    Dim center(0 To 2) As Double
    Dim radius As Double
    center(0) = 2
    center(1) = 2
    center(2) = 0
    radius = 5#
    Set curves(0) = ThisDrawing.ModelSpace.AddCircle _
                    (center, radius)
                    
    ' Create the region
    Dim regionObj As Variant
    regionObj = ThisDrawing.ModelSpace.AddRegion(curves)
    
    ZoomAll
End Sub
Sub Ch4_CreateCompositeRegions()
    ' Create two circles, one representing a room,
    ' the other a pillar in the center of the room
    Dim RoomObjects(0 To 1) As AcadCircle
    Dim center(0 To 2) As Double
    Dim radius As Double
    center(0) = 4
    center(1) = 4
    center(2) = 0
    radius = 2#
    Set RoomObjects(0) = ThisDrawing.ModelSpace. _
                         AddCircle(center, radius)
    radius = 1#
    Set RoomObjects(1) = ThisDrawing.ModelSpace. _
                         AddCircle(center, radius)
    
    ' Create a region from the two circles
    Dim regions As Variant
    regions = ThisDrawing.ModelSpace.AddRegion(RoomObjects)
    
    ' Copy the regions into the region variables for ease of use
    Dim RoundRoomObj As AcadRegion
    Dim PillarObj As AcadRegion
    
    If regions(0).Area > regions(1).Area Then
        ' The first region is the room
        Set RoundRoomObj = regions(0)
        Set PillarObj = regions(1)
    Else
        ' The first region is the pillar
        Set PillarObj = regions(0)
        Set RoundRoomObj = regions(1)
    End If
    
    ' Color the room object red and the pillar object cyan
    RoundRoomObj.Color = acRed
    PillarObj.Color = acCyan
    ZoomAll
    
    ' Subtract the pillar space from the floor space to
    ' get a region that represents the total carpet area.
    RoundRoomObj.Boolean acSubtraction, PillarObj
    
    ' Use the Area property to determine the total carpet area
    MsgBox "The carpet area is: " & RoundRoomObj.Area
End Sub
Sub Ch4_CreateHatch()
    Dim hatchObj As AcadHatch
    Dim patternName As String
    Dim PatternType As Long
    Dim bAssociativity As Boolean
    
    ' Define the hatch
    patternName = "ANSI31"
    PatternType = 0
    bAssociativity = True
    
    ' Create the associative Hatch object
    Set hatchObj = ThisDrawing.ModelSpace.AddHatch _
                   (PatternType, patternName, bAssociativity)
    
    ' Create the outer boundary for the hatch. (a circle)
    Dim outerLoop(0 To 0) As AcadEntity
    Dim center(0 To 2) As Double
    Dim radius As Double
    center(0) = 3: center(1) = 3: center(2) = 0
    radius = 1
    Set outerLoop(0) = ThisDrawing.ModelSpace. _
                       AddCircle(center, radius)
    
    ' Append the outerboundary to the hatch
    ' object, and display the hatch
    hatchObj.AppendOuterLoop (outerLoop)
    hatchObj.Evaluate
    ThisDrawing.Regen True
    
End Sub
Sub Ch4_RenamingLayer()
    ' Create a layer
    Dim layerObj As AcadLayer
    Set layerObj = ThisDrawing.Layers.Add("NewLayer")
    
    ' Change the name of the layer
    layerObj.name = "MyLayer"
    
End Sub
Sub Ch4_CreateSelectionSet()
    Dim selectionSet1 As AcadSelectionSet
    Set selectionSet1 = ThisDrawing.SelectionSets. _
                        Add("NewSelectionSet")
End Sub
Sub Ch4_AddToASelectionSet()
    ' Create a new selection set
    Dim sset As AcadSelectionSet
    Set sset = ThisDrawing.SelectionSets.Add("SS1")
    
    ' Prompt the user to select objects
    ' and add them to the selection set.
    ' To finish selecting, press ENTER.
    sset.SelectOnScreen
    
    ' Iterate through the selection set
    ' and color each object blue
    Dim entry As AcadEntity
    For Each entry In sset
        entry.Color = acBlue
        entry.Update
    Next entry
End Sub
Sub Ch4_OffsetPolyline()
    ' Create the polyline
    Dim plineObj As AcadLWPolyline
    Dim points(0 To 11) As Double
    points(0) = 1: points(1) = 1
    points(2) = 1: points(3) = 2
    points(4) = 2: points(5) = 2
    points(6) = 3: points(7) = 2
    points(8) = 4: points(9) = 4
    points(10) = 4: points(11) = 1
    Set plineObj = ThisDrawing.ModelSpace. _
                   AddLightWeightPolyline(points)
    plineObj.Closed = True
    ZoomAll
                
    ' Offset the polyline
    Dim offsetObj As Variant
    offsetObj = plineObj.offset(0.25)
    offsetObj(0).Color = acRed
    
    ZoomAll
End Sub
Sub Ch4_MirrorPolyline()
    ' Create the polyline
    Dim plineObj As AcadLWPolyline
    Dim points(0 To 11) As Double
    points(0) = 1: points(1) = 1
    points(2) = 1: points(3) = 2
    points(4) = 2: points(5) = 2
    points(6) = 3: points(7) = 2
    points(8) = 4: points(9) = 4
    points(10) = 4: points(11) = 1
    Set plineObj = ThisDrawing.ModelSpace. _
               AddLightWeightPolyline(points)
    plineObj.Closed = True
    ZoomAll
    
    ' Define the mirror axis
    Dim point1(0 To 2) As Double
    Dim point2(0 To 2) As Double
    point1(0) = 0: point1(1) = 4.25: point1(2) = 0
    point2(0) = 4: point2(1) = 4.25: point2(2) = 0
        
    ' Mirror the polyline
    Dim mirrorObj As AcadLWPolyline
    Set mirrorObj = plineObj.Mirror(point1, point2)
    mirrorObj.Color = acRed
    
    ZoomAll
End Sub
Sub Ch4_ArrayingACircle()
    ' Create the circle
    Dim circleObj As AcadCircle
    Dim center(0 To 2) As Double
    Dim radius As Double
    center(0) = 2#: center(1) = 2#: center(2) = 0#
    radius = 1
    Set circleObj = ThisDrawing.ModelSpace. _
                    AddCircle(center, radius)
    ZoomAll
    
    ' Define the polar array
    Dim noOfObjects As Integer
    Dim angleToFill As Double
    Dim basePnt(0 To 2) As Double
    noOfObjects = 4
    angleToFill = 3.14          ' 180 degrees
    basePnt(0) = 4#: basePnt(1) = 4#: basePnt(2) = 0#
    
    ' The following example will create 4 copies
    ' of an object by rotating and copying it about
    ' the point (3,3,0).
    Dim retObj As Variant
    retObj = circleObj.ArrayPolar _
             (noOfObjects, angleToFill, basePnt)
    
    ZoomAll
End Sub
Sub Ch4_ArrayRectangularExample()
    ' Create the circle
    Dim circleObj As AcadCircle
    Dim center(0 To 2) As Double
    Dim radius As Double
    center(0) = 2#: center(1) = 2#: center(2) = 0#
    radius = 0.5
    Set circleObj = ThisDrawing.ModelSpace. _
                           AddCircle(center, radius)
    ZoomAll
    
    ' Define the rectangular array
    Dim numberOfRows As Long
    Dim numberOfColumns As Long
    Dim numberOfLevels As Long
    Dim distanceBwtnRows As Double
    Dim distanceBwtnColumns As Double
    Dim distanceBwtnLevels As Double
    numberOfRows = 5
    numberOfColumns = 5
    numberOfLevels = 2
    distanceBwtnRows = 1
    distanceBwtnColumns = 1
    distanceBwtnLevels = 1
    
    ' Create the array of objects
    Dim retObj As Variant
    retObj = circleObj.ArrayRectangular _
        (numberOfRows, numberOfColumns, numberOfLevels, _
        distanceBwtnRows, distanceBwtnColumns, distanceBwtnLevels)
    
    ZoomAll
End Sub
Sub Ch4_MoveCircle()
    ' Create the circle
    Dim circleObj As AcadCircle
    Dim center(0 To 2) As Double
    Dim radius As Double
    center(0) = 2#: center(1) = 2#: center(2) = 0#
    radius = 0.5
    Set circleObj = ThisDrawing.ModelSpace. _
                    AddCircle(center, radius)
    ZoomAll
    
    ' Define the points that make up the move vector.
    ' The move vector will move the circle 2 units
    ' along the x axis.
    Dim point1(0 To 2) As Double
    Dim point2(0 To 2) As Double
    point1(0) = 0: point1(1) = 0: point1(2) = 0
    point2(0) = 2: point2(1) = 0: point2(2) = 0
    
    ' Move the circle
    circleObj.Move point1, point2
    circleObj.Update
End Sub
Sub Ch4_RotatePolyline()
    ' Create the polyline
    Dim plineObj As AcadLWPolyline
    Dim points(0 To 11) As Double
    points(0) = 1: points(1) = 2
    points(2) = 1: points(3) = 3
    points(4) = 2: points(5) = 3
    points(6) = 3: points(7) = 3
    points(8) = 4: points(9) = 4
    points(10) = 4: points(11) = 2
    Set plineObj = ThisDrawing.ModelSpace. _
                   AddLightWeightPolyline(points)
    plineObj.Closed = True
    ZoomAll
    
    ' Define the rotation of 45 degrees about a
    ' base point of (4, 4.25, 0)
    Dim basePoint(0 To 2) As Double
    Dim rotationAngle As Double
    basePoint(0) = 4: basePoint(1) = 4.25: basePoint(2) = 0
    rotationAngle = 0.7853981   ' 45 degrees
    
    ' Rotate the polyline
    plineObj.Rotate basePoint, rotationAngle
    plineObj.Update
End Sub
Sub Ch4_DeletePolyline()
    ' Create the polyline
    Dim lwpolyObj As AcadLWPolyline
    Dim vertices(0 To 5) As Double
    vertices(0) = 2: vertices(1) = 4
    vertices(2) = 4: vertices(3) = 2
    vertices(4) = 6: vertices(5) = 4
    Set lwpolyObj = ThisDrawing.ModelSpace. _
                 AddLightWeightPolyline(vertices)
    ZoomAll
    
' Erase the polyline
    lwpolyObj.Delete
    ThisDrawing.Regen acActiveViewport
End Sub
Sub Ch4_ScalePolyline()
    ' Create the polyline
    Dim plineObj As AcadLWPolyline
    Dim points(0 To 11) As Double
    points(0) = 1: points(1) = 2
    points(2) = 1: points(3) = 3
    points(4) = 2: points(5) = 3
    points(6) = 3: points(7) = 3
    points(8) = 4: points(9) = 4
    points(10) = 4: points(11) = 2
    Set plineObj = ThisDrawing.ModelSpace. _
                      AddLightWeightPolyline(points)
    plineObj.Closed = True
    ZoomAll
            
    ' Define the scale
    Dim basePoint(0 To 2) As Double
    Dim scalefactor As Double
    basePoint(0) = 4: basePoint(1) = 4.25: basePoint(2) = 0
    scalefactor = 0.5
    
    ' Scale the polyline
    plineObj.ScaleEntity basePoint, scalefactor
    plineObj.Update
End Sub
Sub Ch4_TransformBy()
    ' Create a line
    Dim lineObj As AcadLine
    Dim startPt(0 To 2) As Double
    Dim endPt(0 To 2) As Double
    startPt(0) = 2
    startPt(1) = 1
    startPt(2) = 0
    endPt(0) = 5
    endPt(1) = 1
    endPt(2) = 0
    Set lineObj = ThisDrawing.ModelSpace. _
                AddLine(startPt, endPt)
    ZoomAll
    
    ' Initialize the transMat variable with a
    ' transformation matrix that will rotate
    ' an object by 90 degrees about the point(0,0,0)
    Dim transMat(0 To 3, 0 To 3) As Double
    transMat(0, 0) = 0#: transMat(0, 1) = -1#
    transMat(0, 2) = 0#: transMat(0, 3) = 0#
    transMat(1, 0) = 1#: transMat(1, 1) = 0#
    transMat(1, 2) = 0#: transMat(1, 3) = 0#
    transMat(2, 0) = 0#: transMat(2, 1) = 0#
    transMat(2, 2) = 1#: transMat(2, 3) = 0#
    transMat(3, 0) = 0#: transMat(3, 1) = 0#
    transMat(3, 2) = 0#: transMat(3, 3) = 1#
    
    ' Transform the line using the defined transformation matrix
    lineObj.TransformBy transMat
    lineObj.Update
End Sub
Sub Ch4_LengthenLine()
    ' Define and create the line
    Dim lineObj As AcadLine
    Dim startPoint(0 To 2) As Double
    Dim endPoint(0 To 2)  As Double
    startPoint(0) = 0
    startPoint(1) = 0
    startPoint(2) = 0
    endPoint(0) = 1
    endPoint(1) = 1
    endPoint(2) = 1
    Set lineObj = ThisDrawing.ModelSpace. _
                  AddLine(startPoint, endPoint)
    lineObj.Update
    
    ' Lengthen the line by changing the
    ' endpoint to 4, 4, 4
    endPoint(0) = 4
    endPoint(1) = 4
    endPoint(2) = 4
    lineObj.endPoint = endPoint
    lineObj.Update
End Sub
Sub Ch4_ExplodePolyline()
    Dim plineObj As AcadLWPolyline
    Dim points(0 To 11) As Double
    
    ' Define the 2D polyline points
    points(0) = 1: points(1) = 1
    points(2) = 1: points(3) = 2
    points(4) = 2: points(5) = 2
    points(6) = 3: points(7) = 2
    points(8) = 4: points(9) = 4
    points(10) = 4: points(11) = 1
        
    ' Create a light weight Polyline object
    Set plineObj = ThisDrawing.ModelSpace. _
                  AddLightWeightPolyline(points)
    
    ' Set the bulge on one segment to vary the
    ' type of objects in the polyline
    plineObj.SetBulge 3, -0.5
    plineObj.Update
    
    ' Explode the polyline
    Dim explodedObjects As Variant
    explodedObjects = plineObj.Explode
    
    ' Loop through the exploded objects
    ' and displays a message box with
    ' the type of each object
    Dim I As Integer
    For I = 0 To UBound(explodedObjects)
        explodedObjects(I).Color = acRed
        explodedObjects(I).Update
        MsgBox "Exploded Object " & I & ": " & _
                    explodedObjects(I).ObjectName
        explodedObjects(I).Color = acByLayer
        explodedObjects(I).Update
    Next
End Sub
Sub Ch4_EditPolyline()
    Dim plineObj As AcadLWPolyline
    Dim points(0 To 9) As Double
    
    ' Define the 2D polyline points
    points(0) = 1: points(1) = 1
    points(2) = 1: points(3) = 2
    points(4) = 2: points(5) = 2
    points(6) = 3: points(7) = 2
    points(8) = 4: points(9) = 4
        
    ' Create a light weight Polyline object
    Set plineObj = ThisDrawing.ModelSpace. _
                   AddLightWeightPolyline(points)
                   
    ' Add a bulge to segment 3
    plineObj.SetBulge 3, -0.5
    
    ' Define the new vertex
    Dim newVertex(0 To 1) As Double
    newVertex(0) = 4: newVertex(1) = 1
    
    ' Add the vertex to the polyline
    plineObj.AddVertex 5, newVertex
    
    ' Set the width of the new segment
    plineObj.SetWidth 4, 0.1, 0.5
    
    ' Close the polyline
    plineObj.Closed = True
    plineObj.Update
End Sub
Sub Ch4_ChangeSplineControlPoint()
    ' Create the spline
    Dim splineObj As AcadSpline
    Dim noOfPoints As Integer
    Dim startTan(0 To 2) As Double
    Dim endTan(0 To 2) As Double
    Dim fitPoints(0 To 8) As Double
    
    noOfPoints = 3
    startTan(0) = 0.5: startTan(1) = 0.5: startTan(2) = 0
    endTan(0) = 0.5: endTan(1) = 0.5: endTan(2) = 0
    fitPoints(0) = 1: fitPoints(1) = 1: fitPoints(2) = 0
    fitPoints(3) = 5: fitPoints(4) = 5: fitPoints(5) = 0
    fitPoints(6) = 10: fitPoints(7) = 0: fitPoints(8) = 0
    Set splineObj = ThisDrawing.ModelSpace. _
                   AddSpline(fitPoints, startTan, endTan)
    splineObj.Update
    
    ' Change the coordinate of the first fit point
    Dim controlPoint(0 To 2) As Double
    controlPoint(0) = 0
    controlPoint(1) = 3
    controlPoint(2) = 0
    splineObj.SetControlPoint 0, controlPoint
    splineObj.Update
End Sub
Sub Ch4_AppendInnerLoopToHatch()
    Dim hatchObj As AcadHatch
    Dim patternName As String
    Dim PatternType As Long
    Dim bAssociativity As Boolean
    
    ' Define and create the hatch
    patternName = "ANSI31"
    PatternType = 0
    bAssociativity = True
    Set hatchObj = ThisDrawing.ModelSpace. _
        AddHatch(PatternType, patternName, bAssociativity)
    
    ' Create the outer loop for the hatch.
    Dim outerLoop(0 To 1) As AcadEntity
    Dim center(0 To 2) As Double
    Dim radius As Double
    Dim startAngle As Double
    Dim endAngle As Double
    center(0) = 5: center(1) = 3: center(2) = 0
    radius = 3
    startAngle = 0
    endAngle = 3.141592
    Set outerLoop(0) = ThisDrawing.ModelSpace. _
       AddArc(center, radius, startAngle, endAngle)
    Set outerLoop(1) = ThisDrawing.ModelSpace. _
       AddLine(outerLoop(0).startPoint, outerLoop(0).endPoint)
        
    ' Append the outer loop to the hatch object
    hatchObj.AppendOuterLoop (outerLoop)
    
    ' Create a circle as the inner loop for the hatch.
    Dim innerLoop(0) As AcadEntity
    center(0) = 5: center(1) = 4.5: center(2) = 0
    radius = 1
    Set innerLoop(0) = ThisDrawing.ModelSpace. _
                                 AddCircle(center, radius)
    
    ' Append the circle as an inner loop to the hatch
    hatchObj.AppendInnerLoop (innerLoop)
    
    ' Evaluate and display the hatch
    hatchObj.Evaluate
    ThisDrawing.Regen True
End Sub
Sub Ch4_ChangeHatchPatternSpace()
    Dim hatchObj As AcadHatch
    Dim patternName As String
    Dim PatternType As Long
    Dim bAssociativity As Boolean
    
    ' Define the hatch
    patternName = "ANSI31"
    PatternType = 0
    bAssociativity = True
    
    ' Create the associative Hatch object
    Set hatchObj = ThisDrawing.ModelSpace. _
        AddHatch(PatternType, patternName, bAssociativity)
    
    ' Create the outer loop for the hatch.
    Dim outerLoop(0 To 0) As AcadEntity
    Dim center(0 To 2) As Double
    Dim radius As Double
    center(0) = 5
    center(1) = 3
    center(2) = 0
    radius = 3
    Set outerLoop(0) = ThisDrawing.ModelSpace. _
                                AddCircle(center, radius)
    hatchObj.AppendOuterLoop (outerLoop)
    hatchObj.Evaluate
    
    ' Change the spacing of the hatch pattern by
    ' adding 2 to the current spacing
    hatchObj.patternSpace = hatchObj.patternSpace + 2
    hatchObj.Evaluate
    ThisDrawing.Regen True
End Sub
Sub Ch4_IteratingLayers()
    Dim layerNames As String
    Dim entry As AcadLayer
    layerNames = ""
    For Each entry In ThisDrawing.Layers
        layerNames = layerNames + entry.name + vbCrLf
    Next
    MsgBox "The layers in this drawing are: " + _
           vbCrLf + layerNames
End Sub
Sub Ch4_NewLayer()
    ' Create a circle
    Dim circleObj As AcadCircle
    Dim center(0 To 2) As Double
    Dim radius As Double
    center(0) = 2: center(1) = 2: center(2) = 0
    radius = 1
    Set circleObj = ThisDrawing.ModelSpace. _
                        AddCircle(center, radius)
                        
    ' Assign the circle the color "ByLayer" so
    ' that the circle will automatically pick
    ' up the color of the layer on which it resides
    circleObj.Color = acByLayer
    
    ' Create a new layer called "ABC"
    Dim layerObj As AcadLayer
    Set layerObj = ThisDrawing.Layers.Add("ABC")
    
    ' Assign the "ABC" layer the color red
    layerObj.Color = acRed
    
    ' Assign the circle to the "ABC" layer
    circleObj.Layer = "ABC"
    circleObj.Update
End Sub
Sub Ch4_LayerInvisble()
    ' Create a circle
    Dim circleObj As AcadCircle
    Dim center(0 To 2) As Double
    Dim radius As Double
    center(0) = 2: center(1) = 2: center(2) = 0
    radius = 1
    Set circleObj = ThisDrawing.ModelSpace. _
                        AddCircle(center, radius)
    circleObj.Color = acByLayer
    
    ' Create a new layer called "ABC"
    Dim layerObj As AcadLayer
    Set layerObj = ThisDrawing.Layers.Add("ABC")
    layerObj.Color = acRed
    
    ' Assign the circle to the "ABC" layer
    circleObj.Layer = "ABC"
    circleObj.Update
    
    ' Turn off layer "ABC"
    layerObj.LayerOn = False
    ThisDrawing.Regen acActiveViewport
End Sub
Sub Ch4_LayerFreeze()
    ' Create a new layer called "ABC"
    Dim layerObj As AcadLayer
    Set layerObj = ThisDrawing.Layers.Add("ABC")
    
    ' Freeze layer "ABC"
    layerObj.Freeze = True
End Sub
Sub Ch4_LayerLock()
    ' Create a new layer called "ABC"
    Dim layerObj As AcadLayer
    Set layerObj = ThisDrawing.Layers.Add("ABC")
    
    ' Lock layer "ABC"
    layerObj.Lock = True
End Sub
Sub Ch4_LoadLinetype()
    On Error GoTo ERRORHANDLER
    
    Dim linetypeName As String
    linetypeName = "CENTER"
    
    ' Load "CENTER" line type from acad.lin file
    ThisDrawing.Linetypes.Load linetypeName, "acad.lin"
    Exit Sub
    
ERRORHANDLER:
    MsgBox Err.Description
    
End Sub
Sub Ch4_ChangeLinetypeScale()
    Dim center(0 To 2) As Double
    Dim radius As Double
    Dim circleObj As AcadCircle
    ' Create a circle object in model space
    center(0) = 2
    center(1) = 2
    center(2) = 0
    radius = 4
    Set circleObj = ThisDrawing.ModelSpace. _
                AddCircle(center, radius)
    ' Set the linetype scale of a circle to .5
    circleObj.LinetypeScale = 0.5
    circleObj.Update
End Sub
Sub Ch4_MoveObjectNewLayer()
    ' Create a circle
    Dim circleObj As AcadCircle
    Dim center(0 To 2) As Double
    Dim radius As Double
    center(0) = 2: center(1) = 2: center(2) = 0
    radius = 1
    Set circleObj = ThisDrawing.ModelSpace. _
                        AddCircle(center, radius)
    
    ' Create a new layer called "ABC"
    Dim layerObj As AcadLayer
    Set layerObj = ThisDrawing.Layers.Add("ABC")
    
    ' Assign the circle to the "ABC" layer
    circleObj.Layer = "ABC"
    circleObj.Update
End Sub
Sub Ch4_ColorCircle()
    ' Create a circle
    Dim circleObj As AcadCircle
    Dim center(0 To 2) As Double
    Dim radius As Double
    center(0) = 2: center(1) = 2: center(2) = 0
    radius = 1
    Set circleObj = ThisDrawing.ModelSpace. _
                        AddCircle(center, radius)
    
    ' Color the circle red
    circleObj.Color = acRed
    circleObj.Update
End Sub
Sub Ch4_ChangeCircleLinetype()
    On Error Resume Next
    
    ' Create a circle
    Dim circleObj As AcadCircle
    Dim center(0 To 2) As Double
    Dim radius As Double
    center(0) = 2: center(1) = 2: center(2) = 0
    radius = 1
    Set circleObj = ThisDrawing.ModelSpace. _
                        AddCircle(center, radius)
    
    Dim linetypeName As String
    linetypeName = "CENTER"
    
    ' Load "CENTER" line type from acad.lin file
    ThisDrawing.Linetypes.Load linetypeName, "acad.lin"
    If Err.Description <> "" Then MsgBox Err.Description
    
    ' Assign the circle the linetype "CENTER"
    circleObj.Linetype = "CENTER"
    circleObj.Update
End Sub
Sub Ch4_CopyCircleObjects()
    ' This example creates two Circle objects and uses
    ' the CopyObjects method to make a copy of the circles.

    Dim ACADApp As AcadApplication
    Dim DOC1 As AcadDocument
    Dim circleObj1 As AcadCircle
    Dim circleObj2 As AcadCircle
    Dim circleObj1Copy As AcadCircle
    Dim circleObj2Copy As AcadCircle
    Dim centerPoint(0 To 2) As Double
    Dim radius1 As Double
    Dim radius2 As Double
    Dim radius1Copy As Double
    Dim radius2Copy As Double
    Dim objCollection(0 To 1) As Object
    Dim retObjects As Variant
    
    ' Define the Circle object
    centerPoint(0) = 0: centerPoint(1) = 0: centerPoint(2) = 0
    radius1 = 5#: radius2 = 7#
    radius1Copy = 1#: radius2Copy = 2#
    
    ' Get application object from system
    Set ACADApp = GetObject(, "AutoCAD.Application")
    
    ' Create a new drawing
    Set DOC1 = ACADApp.Documents.Add
    
    ' Add two circles to the drawing
    Set circleObj1 = DOC1.ModelSpace.AddCircle _
                     (centerPoint, radius1)
    Set circleObj2 = DOC1.ModelSpace.AddCircle _
                     (centerPoint, radius2)
    ZoomAll
    
    ' Put the objects to be copied into a form
    ' compatible with CopyObjects
    Set objCollection(0) = circleObj1
    Set objCollection(1) = circleObj2
    
    ' Copy object and get back a collection of
    ' the new objects (copies)
    retObjects = DOC1.CopyObjects(objCollection)
    
    ' Get newly created object and apply
    ' new properties to the copies
    Set circleObj1Copy = retObjects(0)
    Set circleObj2Copy = retObjects(1)
    
    circleObj1Copy.radius = radius1Copy
    circleObj1Copy.Color = acRed
    circleObj2Copy.radius = radius2Copy
    circleObj2Copy.Color = acRed
        
    ZoomAll
End Sub
Sub Ch4_UpdateTextFont()
    Dim typeFace As String
    Dim Bold As Boolean
    Dim Italic As Boolean
    Dim charSet As Long
    Dim PitchandFamily As Long
    
    ' Get the current settings to fill in the
    ' default values for the SetFont method
    ThisDrawing.ActiveTextStyle.GetFont typeFace, _
                 Bold, Italic, charSet, PitchandFamily
      
    ' Change the typeface for the font
    typeFace = "PlayBill"
    ThisDrawing.ActiveTextStyle.SetFont typeFace, _
                Bold, Italic, charSet, PitchandFamily
    ThisDrawing.Regen acActiveViewport
End Sub
Sub Ch4_ChangeFontFiles()
    ThisDrawing.ActiveTextStyle.BigFontFile = _
                     "C:/AutoCAD/Fonts/bigfont.shx"
    ThisDrawing.ActiveTextStyle.fontFile = _
                     "C:/AutoCAD/Fonts/italic.shx"
End Sub
Sub Ch4_ChangeTextHeight()
    Dim textObj As AcadText
    Dim textString As String
    Dim insertionPoint(0 To 2) As Double
    Dim height As Double
    
    ' Define the text object
    textString = "Hello, World."
    insertionPoint(0) = 3
    insertionPoint(1) = 3
    insertionPoint(2) = 0
    height = 0.5
    
    ' Create the text object in model space
    Set textObj = ThisDrawing.ModelSpace. _
                 AddText(textString, insertionPoint, height)
    
    ' Change the value of the Height to 1
    textObj.height = 1
    textObj.Update
End Sub
Sub Ch4_ObliqueText()
    Dim textObj As AcadText
    Dim textString As String
    Dim insertionPoint(0 To 2) As Double
    Dim height As Double
    
    ' Define the text object
    textString = "Hello, World."
    insertionPoint(0) = 3
    insertionPoint(1) = 3
    insertionPoint(2) = 0
    height = 0.5
    
    ' Create the text object in model space
    Set textObj = ThisDrawing.ModelSpace. _
               AddText(textString, insertionPoint, height)
    
    ' Change the value of the ObliqueAngle
    ' to 45 degrees (.707 radians)
    textObj.ObliqueAngle = 0.707
    textObj.Update
End Sub
Sub Ch4_ChangingTextGenerationFlag()
    Dim textObj As AcadText
    Dim textString As String
    Dim insertionPoint(0 To 2) As Double
    Dim height As Double
    
    ' Create the text object
    textString = "Hello, World."
    insertionPoint(0) = 3
    insertionPoint(1) = 3
    insertionPoint(2) = 0
    height = 0.5
    Set textObj = ThisDrawing.ModelSpace. _
                AddText(textString, insertionPoint, height)
    
    ' Change the value of the TextGenerationFlag
    textObj.TextGenerationFlag = acTextFlagBackward
    textObj.Update
End Sub
Sub Ch4_CreateText()
    Dim textObj As AcadText
    Dim textString As String
    Dim insertionPoint(0 To 2) As Double
    Dim height As Double
    
    ' Create the text object
    textString = "Hello, World."
    insertionPoint(0) = 2
    insertionPoint(1) = 2
    insertionPoint(2) = 0
    height = 0.5
    Set textObj = ThisDrawing.ModelSpace. _
                AddText(textString, insertionPoint, height)
    textObj.Update
End Sub
Sub Ch4_TextAlignment()
    Dim textObj As AcadText
    Dim textString As String
    Dim insertionPoint(0 To 2) As Double
    Dim height As Double
    
    ' Define the new Text object
    textString = "Hello, World."
    insertionPoint(0) = 3
    insertionPoint(1) = 3
    insertionPoint(2) = 0
    height = 0.5
    
    ' Create the Text object in model space
    Set textObj = ThisDrawing.ModelSpace. _
                    AddText(textString, insertionPoint, height)
    
    ' Create a point over the text alignment point,
    ' so we can better visualize the alignment process
    Dim pointObj As AcadPoint
    Dim alignmentPoint(0 To 2) As Double
    alignmentPoint(0) = 3
    alignmentPoint(1) = 3
    alignmentPoint(2) = 0
    Set pointObj = ThisDrawing.ModelSpace. _
                    AddPoint(alignmentPoint)
    pointObj.Color = acRed
    
    ' Set the point style to crosshair
    ThisDrawing.SetVariable "PDMODE", 2
         
   ' Align the text to the Left
    textObj.Alignment = acAlignmentLeft
    ThisDrawing.Regen acActiveViewport
    MsgBox "The Text object is now aligned left"
    
    ' Align the text to the Center
    textObj.Alignment = acAlignmentCenter
    
    ' Align the text to the point (necessary for
    ' all but left aligned text.)
    textObj.TextAlignmentPoint = alignmentPoint
    
    ThisDrawing.Regen acActiveViewport
    MsgBox "The Text object is now centered"
    
    ' Align the text to the Right
    textObj.Alignment = acAlignmentRight
    ThisDrawing.Regen acActiveViewport
    MsgBox "The Text object is now aligned right"
    
End Sub
Sub Ch4_CreateMText()
    Dim MTextObj As AcadMText
    Dim InsertPoint(0 To 2) As Double
    Dim width As Double
    Dim textString As String
    
    InsertPoint(0) = 2
    InsertPoint(1) = 2
    InsertPoint(2) = 0
    width = 4
    textString = "This is a text string for the mtext object."
    
    ' Create a text Object in model space
    Set MTextObj = ThisDrawing.ModelSpace. _
               AddMText(InsertPoint, width, textString)
    ZoomAll
End Sub

Sub Ch4_FormatMText()
    Dim MTextObj As AcadMText
    Dim InsertPoint(0 To 2) As Double
    Dim width As Double
    Dim textString As String
    
    InsertPoint(0) = 2
    InsertPoint(1) = 2
    InsertPoint(2) = 0
    width = 4
    
    ' Define the ASCII characters for the control characters
    Dim OB As Long  ' Open Bracket  {
    Dim CB As Long  ' Close Bracket }
    Dim BS As Long  ' Back Slash    \
    Dim FS As Long  ' Forward Slash /
    Dim SC As Long  ' Semicolon     ;
    OB = Asc("{")
    CB = Asc("}")
    BS = Asc("\")
    FS = Asc("/")
    SC = Asc(";")
    
    ' Assign the text string the following line of control
    ' characters and text characters:
    ' {{\H1.5x; Big text}\A2; over text\A1;/\A0; under text}
    
    textString = Chr(OB) + Chr(OB) + Chr(BS) + "H1.5x" _
    + Chr(SC) + "Big text" + Chr(CB) + Chr(BS) + "A2" _
    + Chr(SC) + "over text" + Chr(BS) + "A1" + Chr(SC) _
    + Chr(FS) + Chr(BS) + "A0" + Chr(SC) + "under text" _
    + Chr(CB)
    
    ' Create a text Object in model space
    Set MTextObj = ThisDrawing.ModelSpace. _
               AddMText(InsertPoint, width, textString)
    ZoomAll
End Sub
Sub Ch5_CreateRadialDimension()
    Dim dimObj As AcadDimRadial
    Dim center(0 To 2) As Double
    Dim chordPoint(0 To 2) As Double
    Dim leaderLen As Integer
    
    ' Define the dimension
    center(0) = 0
    center(1) = 0
    center(2) = 0
    chordPoint(0) = 5
    chordPoint(1) = 5
    chordPoint(2) = 0
    leaderLen = 5
    
    ' Create the radial dimension in model space
    Set dimObj = ThisDrawing.ModelSpace. _
           AddDimRadial(center, chordPoint, leaderLen)
    ZoomAll
End Sub
Sub Ch5_CreateAngularDimension()
    Dim dimObj As AcadDimAngular
    Dim angVert(0 To 2) As Double
    Dim FirstPoint(0 To 2) As Double
    Dim SecondPoint(0 To 2) As Double
    Dim TextPoint(0 To 2) As Double
    
    ' Define the dimension
    angVert(0) = 0
    angVert(1) = 5
    angVert(2) = 0
    FirstPoint(0) = 1
    FirstPoint(1) = 7
    FirstPoint(2) = 0
    SecondPoint(0) = 1
    SecondPoint(1) = 3
    SecondPoint(2) = 0
    TextPoint(0) = 3
    TextPoint(1) = 5
    TextPoint(2) = 0
    
    ' Create the angular dimension in model space
    Set dimObj = ThisDrawing.ModelSpace. _
     AddDimAngular(angVert, FirstPoint, SecondPoint, TextPoint)
    ZoomAll
End Sub
Sub Ch5_CreatingOrdinateDimension()
    Dim dimObj As AcadDimOrdinate
    Dim definingPoint(0 To 2) As Double
    Dim leaderEndPoint(0 To 2) As Double
    Dim useXAxis As Long
    
    ' Define the dimension
    definingPoint(0) = 5
    definingPoint(1) = 5
    definingPoint(2) = 0
    leaderEndPoint(0) = 10
    leaderEndPoint(1) = 5
    leaderEndPoint(2) = 0
    useXAxis = 5
    
    ' Create an ordinate dimension in model space
    Set dimObj = ThisDrawing.ModelSpace. _
               AddDimOrdinate(definingPoint, _
               leaderEndPoint, useXAxis)
    ZoomAll
End Sub
Sub Ch5_OverrideDimensionText()
    Dim dimObj As AcadDimAligned
    Dim point1(0 To 2) As Double
    Dim point2(0 To 2) As Double
    Dim location(0 To 2) As Double
    
    ' Define the dimension
    point1(0) = 5#: point1(1) = 3#: point1(2) = 0#
    point2(0) = 10#: point2(1) = 3#: point2(2) = 0#
    location(0) = 7.5: location(1) = 5#: location(2) = 0#
    
    ' Create an aligned dimension object in model space
    Set dimObj = ThisDrawing.ModelSpace. _
                   AddDimAligned(point1, point2, location)
    
    ' Change the text string for the dimension
    dimObj.TextOverride = "The value is <>"
    dimObj.Update
End Sub
Sub Ch5_AddTextSuffix()
    Dim dimObj As AcadDimAligned
    Dim point1(0 To 2) As Double
    Dim point2(0 To 2) As Double
    Dim location(0 To 2) As Double
    Dim suffix As String
    
    ' Define the dimension
    point1(0) = 0: point1(1) = 5: point1(2) = 0
    point2(0) = 5: point2(1) = 5: point2(2) = 0
    location(0) = 5: location(1) = 7: location(2) = 0
    
    ' Create an aligned dimension object in model space
    Set dimObj = ThisDrawing.ModelSpace. _
                 AddDimAligned(point1, point2, location)
    
    ThisDrawing.Application.ZoomAll
    ' Allow the user to change the text suffix for the dimension
    suffix = InputBox("Enter a new text suffix for the dimension" _
                      , "Set Dimension Suffix", ":SUFFIX")
    
    ' Apply the change to the dimension
    dimObj.TextSuffix = suffix
    ThisDrawing.Regen acAllViewports
End Sub
Sub Ch5_CreateLeader()
    Dim leaderObj As AcadLeader
    Dim points(0 To 8) As Double
    Dim leaderType As Integer
    Dim annotationObject As AcadObject
    
    points(0) = 0: points(1) = 0: points(2) = 0
    points(3) = 4: points(4) = 4: points(5) = 0
    points(6) = 4: points(7) = 5: points(8) = 0
    leaderType = acLineWithArrow
    Set annotationObject = Nothing
        
    ' Create the leader object in model space
    Set leaderObj = ThisDrawing.ModelSpace. _
          AddLeader(points, annotationObject, leaderType)
    ZoomAll
End Sub
Sub Ch5_AddAnnotation()
    Dim leaderObj As AcadLeader
    Dim MTextObj As AcadMText
    Dim points(0 To 8) As Double
    Dim insertionPoint(0 To 2) As Double
    Dim width As Double
    Dim leaderType As Integer
    Dim annotationObject As Object
    Dim textString As String, msg As String
    
    ' Create the MText object in model space
    textString = "Hello, World."
    insertionPoint(0) = 5
    insertionPoint(1) = 5
    insertionPoint(2) = 0
    width = 2
    Set MTextObj = ThisDrawing.ModelSpace. _
               AddMText(insertionPoint, width, textString)
    
    ' Data for Leader
    points(0) = 0: points(1) = 0: points(2) = 0
    points(3) = 4: points(4) = 4: points(5) = 0
    points(6) = 4: points(7) = 5: points(8) = 0
    leaderType = acLineWithArrow
       
    ' Create the Leader object in model space and associate
    ' the MText object with the leader
    Set annotationObject = MTextObj
    Set leaderObj = ThisDrawing.ModelSpace. _
            AddLeader(points, annotationObject, leaderType)
    ZoomAll
End Sub
Sub Ch5_CreateTolerance()
    Dim toleranceObj As AcadTolerance
    Dim textString As String
    Dim insertionPoint(0 To 2) As Double
    Dim direction(0 To 2) As Double
    
    ' Define the tolerance object
    textString = "Here is the Feature Control Frame"
    insertionPoint(0) = 5
    insertionPoint(1) = 5
    insertionPoint(2) = 0
    direction(0) = 1
    direction(1) = 1
    direction(2) = 0
    ' Create the tolerance object in model space
    Set toleranceObj = ThisDrawing.ModelSpace. _
        AddTolerance(textString, insertionPoint, direction)
    ZoomAll
End Sub
Sub Ch5_CopyDimStyles()
    ' This example creates three new dimension styles.
    ' Before running this example you must create a new
    ' drawing. Then create a linear dimension in the new drawing.
    ' Using the OPM, change the color of the dimension line to yellow.
    ' Change the DIMCLRD system variable to 5 (blue).
    Dim newStyle1 As AcadDimStyle
    Dim newStyle2 As AcadDimStyle
    Dim newStyle3 As AcadDimStyle
    
    Set newStyle1 = ThisDrawing.DimStyles.Add _
                    ("Style 1 copied from a dim")
    Call newStyle1.CopyFrom(ThisDrawing.ModelSpace(0))
    
    Set newStyle2 = ThisDrawing.DimStyles.Add _
                    ("Style 2 copied from Style 1")
    Call newStyle2.CopyFrom(ThisDrawing.DimStyles.Item _
                    ("Style 1 copied from a dim"))
                    
    Set newStyle2 = ThisDrawing.DimStyles.Add _
                    ("Style 3 copied from the running drawing values")
    Call newStyle2.CopyFrom(ThisDrawing)
End Sub

Sub Ch6_InsertMenu()
    ' Define a variable for the current menu group
    Dim currMenuGroup As acadMenuGroup
    Set currMenuGroup = ThisDrawing.Application. _
                                    MenuGroups.Item(0)
    
    ' Create a new menu
    Dim newMenu As AcadPopupMenu
    Set newMenu = currMenuGroup.Menus.Add("TestMenu")
    
    ' Declare the variables for the menu item
    Dim newMenuItem As AcadPopupMenuItem
    Dim openMacro As String
    
    ' Assign the macro string the VB equivalent of
    ' "ESC ESC _open " and create the menu item
    openMacro = Chr(3) + Chr(3) + Chr(95) + "open" + Chr(32)
    Set newMenuItem = newMenu.AddMenuItem(newMenu.count + 1, _
        "Open", openMacro)
    
    ' Display the menu on the menu bar
    currMenuGroup.Menus.InsertMenuInMenuBar "TestMenu", ""
End Sub
Sub Ch6_MoveMenu()
    ' Define a variable to hold the menu to be moved
    Dim moveMenu As AcadPopupMenu
    Dim MyMenuBar As AcadMenuBar
    Set MyMenuBar = ThisDrawing.Application.MenuBar
    
    ' Set moveMenu equal to the first menu displayed
    ' on the menu bar
    Set moveMenu = MyMenuBar.Item(0)
    
    ' Remove the first menu from the menu bar
    MyMenuBar.Item(0).RemoveFromMenuBar
    
    ' Add the menu back into the menu bar
    ' in the last position on the bar
    moveMenu.InsertInMenuBar (MyMenuBar.count)
End Sub
Sub Ch6_CreateMenu()
    Dim currMenuGroup As acadMenuGroup
    Set currMenuGroup = ThisDrawing.Application.MenuGroups.Item(0)
    
    ' Create the new menu
    Dim newMenu As AcadPopupMenu
    Set newMenu = currMenuGroup.Menus.Add("TestMenu")
End Sub
Sub Ch6_AddAMenuItem()
    Dim currMenuGroup As acadMenuGroup
    Set currMenuGroup = ThisDrawing.Application.MenuGroups.Item(0)
    
    ' Create the new menu
    Dim newMenu As AcadPopupMenu
    Set newMenu = currMenuGroup.Menus.Add("TestMenu")
    
    ' Add a menu item to the new menu
    Dim newMenuItem As AcadPopupMenuItem
    Dim openMacro As String
    ' Assign the macro the VBA equivalent of "ESC ESC _open "
    openMacro = Chr(3) + Chr(3) + Chr(95) + "open" + Chr(32)
    
    Set newMenuItem = newMenu.AddMenuItem _
                       (newMenu.count + 1, "Open", openMacro)
    
    ' Display the menu on the menu bar
    newMenu.InsertInMenuBar _
                 (ThisDrawing.Application.MenuBar.count + 1)
End Sub

Sub Ch6_AddASubMenu()
    Dim currMenuGroup As acadMenuGroup
    Set currMenuGroup = ThisDrawing.Application.MenuGroups.Item(0)
    
    ' Create the new menu
    Dim newMenu As AcadPopupMenu
    Set newMenu = currMenuGroup.Menus.Add("TestMenu")
    
    ' Add the submenu
    Dim FileSubMenu As AcadPopupMenu
    Set FileSubMenu = newMenu.AddSubMenu("", "OpenFile")
       
    ' Add a menu item to the sub menu
    Dim newMenuItem As AcadPopupMenuItem
    Dim openMacro As String
    ' Assign the macro the VB equivalent of "ESC ESC _open "
    openMacro = Chr(3) + Chr(3) + Chr(95) + "open" + Chr(32)
    
    Set newMenuItem = FileSubMenu.AddMenuItem _
                          (newMenu.count + 1, "Open", openMacro)
    
    ' Display the menu on the menu bar
    newMenu.InsertInMenuBar _
                   (ThisDrawing.Application.MenuBar.count + 1)
End Sub
Sub Ch6_DeleteMenuItem()
    Dim LastMenu As AcadPopupMenu
    Set LastMenu = ThisDrawing.Application.MenuBar. _
                Item(ThisDrawing.Application.MenuBar.count - 1)
           
    ' Add a menu item
    Dim newMenuItem As AcadPopupMenuItem
    Dim openMacro As String
    ' Assign the macro the VB equivalent of "ESC ESC _open "
    openMacro = Chr(3) + Chr(3) + Chr(95) + "open" + Chr(32)
    
    Set newMenuItem = LastMenu.AddMenuItem _
                          (LastMenu.count + 1, "Open", openMacro)
                          
    ' Remove the menu item from the menu
    newMenuItem.Delete
End Sub
Sub Ch6_DisableMenuItem()
    Dim currMenuGroup As acadMenuGroup
    Set currMenuGroup = ThisDrawing.Application.MenuGroups.Item(0)
    
    ' Create the new menu
    Dim newMenu As AcadPopupMenu
    Set newMenu = currMenuGroup.Menus.Add("TestMenu")
    
    ' Add two menu items and a menu separator to the new menu
    Dim MenuEnable As AcadPopupMenuItem
    Dim MenuDisable As AcadPopupMenuItem
    Dim MenuSeparator As AcadPopupMenuItem
    Dim openMacro As String
    
    ' Assign the macro the VB equivalent of "ESC ESC _open "
    openMacro = Chr(3) + Chr(3) + Chr(95) + "open" + Chr(32)
    
    Set MenuEnable = newMenu.AddMenuItem _
                (newMenu.count + 1, "OpenEnabled", openMacro)
    Set MenuSeparator = newMenu.AddSeparator("")
    Set MenuDisable = newMenu.AddMenuItem _
                (newMenu.count + 1, "OpenDisabled", openMacro)
    
    ' Disable the second menu item
    MenuDisable.Enable = False
    
    ' Display the menu on the menu bar
    newMenu.InsertInMenuBar _
                (ThisDrawing.Application.MenuBar.count + 1)
End Sub
Sub Ch6_CreateToolbar()
    Dim currMenuGroup As acadMenuGroup
    Set currMenuGroup = ThisDrawing.Application.MenuGroups.Item(0)
    
    ' Create the new toolbar
    Dim newToolBar As AcadToolbar
    Set newToolBar = currMenuGroup.Toolbars.Add("TestToolbar")
End Sub
Sub Ch6_AddButton()
    Dim currMenuGroup As acadMenuGroup
    Set currMenuGroup = ThisDrawing.Application.MenuGroups.Item(0)
    
    ' Create the new toolbar
    Dim newToolBar As AcadToolbar
    Set newToolBar = currMenuGroup.Toolbars.Add("TestToolbar")
    
    ' Add a button to the new toolbar
    Dim newButton As AcadToolbarItem
    Dim openMacro As String
    
    ' Assign the macro the VB equivalent of "ESC ESC _open "
    openMacro = Chr(3) + Chr(3) + Chr(95) + "open" + Chr(32)
    Set newButton = newToolBar.AddToolbarButton _
                   ("", "NewButton", "Open a file.", openMacro)
End Sub
Sub Ch6_GetButtonImages()
    Dim button As AcadToolbarItem
    Dim Toolbar0 As AcadToolbar
    Dim MenuGroup0 As acadMenuGroup
    Dim SmallButtonName As String
    Dim LargeButtonName As String
    Dim msg As String
    Dim ButtonType As String
    
    ' Get the first toolbar in the first menu group
    Set MenuGroup0 = ThisDrawing.Application. _
                                 MenuGroups.Item(0)
    Set Toolbar0 = MenuGroup0.Toolbars.Item(0)
    
    ' Clear the string variables
    SmallButtonName = ""
    LargeButtonName = ""
    
    ' Create a header for the message box and
    ' display the toolbar to be queried
    msg = "Toolbar: " + Toolbar0.name + vbCrLf
    Toolbar0.Visible = True
    
    ' Iterate through the toolbar and collect data
    ' for each button in the toolbar. If the toolbar is
    ' a normal button or a flyout, collect the small
    ' and large button names for the button.
    For Each button In Toolbar0
        ButtonType = Choose(button.Type + 1, "Button", _
                        "Separator", "Control", "Flyout")
        msg = msg & ButtonType & ":   "
        If button.Type = acToolbarButton Or _
                       button.Type = acToolbarFlyout Then
            button.GetBitmaps SmallButtonName, _
                              LargeButtonName
            msg = msg + SmallButtonName + ", " _
                      + LargeButtonName
        End If
        msg = msg + vbCrLf
    Next button
    
    ' Display the results
    MsgBox msg
End Sub
Sub Ch6_AddFlyoutButton()
    Dim currMenuGroup As acadMenuGroup
    Set currMenuGroup = ThisDrawing.Application. _
                                 MenuGroups.Item(0)
    
    ' Create the first toolbar
    Dim FirstToolbar As AcadToolbar
    Set FirstToolbar = currMenuGroup.Toolbars. _
                                Add("FirstToolbar")
    
    ' Add a flyout button to the first menu on the menu bar
    Dim FlyoutButton As AcadToolbarItem
    Set FlyoutButton = FirstToolbar.AddToolbarButton _
            ("", "Flyout", "Demonstrates a flyout button", _
             "OPEN", True)
    
    ' Create the second toolbar. This will be attached to
    ' the first toolbar via the flyout button.
    Dim SecondToolbar As AcadToolbar
    Set SecondToolbar = currMenuGroup.Toolbars. _
            Add("SecondToolbar")
    
    ' Add a button to the next toolbar
    Dim newButton As AcadToolbarItem
    Dim openMacro As String
    
    ' Assign the macro the VB equivalent of "ESC ESC _open "
    openMacro = Chr(3) + Chr(3) + Chr(95) + "open" + Chr(32)
    Set newButton = SecondToolbar.AddToolbarButton _
            ("", "NewButton", "Open a file.", openMacro)
                   
    ' Attach the second toolbar to the flyout
    ' button on the first toolbar
    FlyoutButton.AttachToolbarToFlyout currMenuGroup.name, _
            SecondToolbar.name
    
    ' Display the first toolbar, hide the second toolbar
    FirstToolbar.Visible = True
    SecondToolbar.Visible = False
End Sub
Sub Ch6_DockToolbar()
    Dim currMenuGroup As acadMenuGroup
    Set currMenuGroup = ThisDrawing.Application. _
                                        MenuGroups.Item(0)
    
    ' Create the new toolbar
    Dim newToolBar As AcadToolbar
    Set newToolBar = currMenuGroup.Toolbars. _
                                       Add("TestToolbar")
    
    ' Add three buttons to the new toolbar.
    ' All three buttons will have the same macro attached.
    Dim newButton1 As AcadToolbarItem
    Dim newButton2 As AcadToolbarItem
    Dim newButton3 As AcadToolbarItem
    Dim openMacro As String
    
    ' Assign the macro the VB equivalent of "ESC ESC _open "
    openMacro = Chr(3) + Chr(3) + Chr(95) + "open" + Chr(32)
    
    Set newButton1 = newToolBar.AddToolbarButton _
                   ("", "NewButton1", "Open a file.", openMacro)
    Set newButton2 = newToolBar.AddToolbarButton _
                   ("", "NewButton2", "Open a file.", openMacro)
    Set newButton3 = newToolBar.AddToolbarButton _
                   ("", "NewButton3", "Open a file.", openMacro)
    
    ' Display the toolbar
    newToolBar.Visible = True
    
    ' Dock the toolbar to the left of the screen.
    newToolBar.Dock acToolbarDockLeft
End Sub
Sub Ch6_AddHelp()
    Dim currMenuGroup As acadMenuGroup
    Set currMenuGroup = ThisDrawing.Application.MenuGroups.Item(0)
    
    ' Create the new menu
    Dim newMenu As AcadPopupMenu
    Set newMenu = currMenuGroup.Menus.Add _
                              ("Te" + Chr(Asc("&")) + "stMenu")
    
    ' Add a menu item to the new menu
    Dim newMenuItem As AcadPopupMenuItem
    Dim openMacro As String
    ' Assign the macro the VBA equivalent of "ESC ESC _open "
    openMacro = Chr(3) + Chr(3) + Chr(95) + "open" + Chr(32)
    
    
    ' Create the menu item
    Set newMenuItem = newMenu.AddMenuItem _
                       (newMenu.count + 1, Chr(Asc("&")) _
                        + "Open", openMacro)
                        
    ' Add the status line help to the menu item
     newMenuItem.HelpString = "Opens an AutoCAD drawing file."
   
    ' Display the menu on the menu bar
    newMenu.InsertInMenuBar _
                 (ThisDrawing.Application.MenuBar.count + 1)
End Sub
Sub Ch6_AddMenuItemToshortcutMenu()
    Dim currMenuGroup As acadMenuGroup
    Set currMenuGroup = ThisDrawing.Application.MenuGroups.Item(0)
    
    ' Find the shortcut menu and assign it to the
    ' shortcutMenu variable
    Dim scMenu As AcadPopupMenu
    Dim entry As AcadPopupMenu
    For Each entry In currMenuGroup.Menus
        If entry.ShortcutMenu = True Then
            Set scMenu = entry
        End If
    Next entry
        
    ' Add a menu item to the shortcut menu
    Dim newMenuItem As AcadPopupMenuItem
    Dim openMacro As String
    ' Assign the macro the VBA equivalent of "ESC ESC _open "
    openMacro = Chr(3) + Chr(3) + Chr(95) + "open" + Chr(32)
    
    Set newMenuItem = scMenu.AddMenuItem _
                                    ("", Chr(Asc("&")) _
                                     + "OpenDWG", openMacro)
End Sub

Sub Ch8_Polyline_2D_3D()
    Dim pline2DObj As AcadLWPolyline
    Dim pline3DObj As AcadPolyline
    
    Dim points2D(0 To 5) As Double
    Dim points3D(0 To 8) As Double
        
    ' Define three 2D polyline points
   points2D(0) = 1: points2D(1) = 1
   points2D(2) = 1: points2D(3) = 2
   points2D(4) = 2: points2D(5) = 2
    
    ' Define three 3D polyline points
   points3D(0) = 1: points3D(1) = 1: points3D(2) = 0
   points3D(3) = 2: points3D(4) = 1: points3D(5) = 0
   points3D(6) = 2: points3D(7) = 2: points3D(8) = 0
   
    ' Create the 2D light weight Polyline
    Set pline2DObj = ThisDrawing.ModelSpace. _
                             AddLightWeightPolyline(points2D)
    pline2DObj.Color = acRed
    pline2DObj.Update
    
    ' Create the 3D polyline
    Set pline3DObj = ThisDrawing.ModelSpace. _
                             AddPolyline(points3D)
    pline3DObj.Color = acBlue
    pline3DObj.Update
    
    ' Query the coordinates of the polylines
    Dim get2Dpts As Variant
    Dim get3Dpts As Variant
    
    get2Dpts = pline2DObj.Coordinates
    get3Dpts = pline3DObj.Coordinates
    
    ' Display the coordinates
    
    MsgBox ("2D polyline (red): " & vbCrLf & _
            get2Dpts(0) & ", " & get2Dpts(1) & vbCrLf & _
            get2Dpts(2) & ", " & get2Dpts(3) & vbCrLf & _
            get2Dpts(4) & ", " & get2Dpts(5))
            
    MsgBox ("3D polyline (blue): " & vbCrLf & _
            get3Dpts(0) & ", " & get3Dpts(1) & ", " & _
            get3Dpts(2) & vbCrLf & _
            get3Dpts(3) & ", " & get3Dpts(4) & ", " & _
            get3Dpts(5) & vbCrLf & _
            get3Dpts(6) & ", " & get3Dpts(7) & ", " & _
            get3Dpts(8))
End Sub
Sub Ch8_NewUCS()
    ' Define the variables we will need
    Dim ucsObj As AcadUCS
    Dim origin(0 To 2) As Double
    Dim xAxisPnt(0 To 2) As Double
    Dim yAxisPnt(0 To 2) As Double
    ' Define the UCS points
    origin(0) = 4: origin(1) = 5: origin(2) = 3
    xAxisPnt(0) = 5: xAxisPnt(1) = 5: xAxisPnt(2) = 3
    yAxisPnt(0) = 4: yAxisPnt(1) = 6: yAxisPnt(2) = 3
    
    ' Add the UCS to the
    ' UserCoordinatesSystems collection
    Set ucsObj = ThisDrawing.UserCoordinateSystems. _
             Add(origin, xAxisPnt, yAxisPnt, "New_UCS")
    ' Display the UCS icon
    ThisDrawing.ActiveViewport.UCSIconAtOrigin = True
    ThisDrawing.ActiveViewport.UCSIconOn = True
    
    ' Make the new UCS the active UCS
    ThisDrawing.ActiveUCS = ucsObj
    MsgBox "The current UCS is : " & ThisDrawing.ActiveUCS.name _
            & vbCrLf & " Pick a point in the drawing."
        
    ' Find the WCS and UCS coordinate of a point
    Dim WCSPnt As Variant
    Dim UCSPnt As Variant
    
    WCSPnt = ThisDrawing.Utility.GetPoint(, "Enter a point: ")
    UCSPnt = ThisDrawing.Utility.TranslateCoordinates _
             (WCSPnt, acWorld, acUCS, False)
    
    MsgBox "The WCS coordinates are: " & WCSPnt(0) & ", " _
             & WCSPnt(1) & ", " & WCSPnt(2) & vbCrLf & _
             "The UCS coordinates are: " & UCSPnt(0) & ", " _
             & UCSPnt(1) & ", " & UCSPnt(2)
End Sub
Sub Ch8_Create3DMesh()
    Dim meshObj As AcadPolygonMesh
    Dim mSize, nSize, count As Integer
    Dim points(0 To 47) As Double
    
    ' create the matrix of points
    points(0) = 0: points(1) = 0: points(2) = 0
    points(3) = 2: points(4) = 0: points(5) = 1
    points(6) = 4: points(7) = 0: points(8) = 0
    points(9) = 6: points(10) = 0: points(11) = 1
    points(12) = 0: points(13) = 2: points(14) = 0
    points(15) = 2: points(16) = 2: points(17) = 1
    points(18) = 4: points(19) = 2: points(20) = 0
    points(21) = 6: points(22) = 2: points(23) = 1
    points(24) = 0: points(25) = 4: points(26) = 0
    points(27) = 2: points(28) = 4: points(29) = 1
    points(30) = 4: points(31) = 4: points(32) = 0
    points(33) = 6: points(34) = 4: points(35) = 0
    points(36) = 0: points(37) = 6: points(38) = 0
    points(39) = 2: points(40) = 6: points(41) = 1
    points(42) = 4: points(43) = 6: points(44) = 0
    points(45) = 6: points(46) = 6: points(47) = 0
    
    mSize = 4: nSize = 4
    
    ' creates a 3Dmesh in model space
    Set meshObj = ThisDrawing.ModelSpace. _
                        Add3DMesh(mSize, nSize, points)
    
    ' Change the viewing direction of the viewport
    ' to better see the cylinder
    Dim NewDirection(0 To 2) As Double
    NewDirection(0) = -1
    NewDirection(1) = -1
    NewDirection(2) = 1
    ThisDrawing.ActiveViewport.direction = NewDirection
    ThisDrawing.ActiveViewport = ThisDrawing.ActiveViewport
    ZoomAll
End Sub
Sub Ch8_CreatePolyfaceMesh()
    'Define the mesh vertices
    Dim vertex(0 To 17) As Double
    vertex(0) = 4: vertex(1) = 7: vertex(2) = 0
    vertex(3) = 5: vertex(4) = 7: vertex(5) = 0
    vertex(6) = 6: vertex(7) = 7: vertex(8) = 0
    vertex(9) = 4: vertex(10) = 6: vertex(11) = 0
    vertex(12) = 5: vertex(13) = 6: vertex(14) = 0
    vertex(15) = 6: vertex(16) = 6: vertex(17) = 1
    
    ' Define the face list
    Dim FaceList(0 To 7) As Integer
    FaceList(0) = 1
    FaceList(1) = 2
    FaceList(2) = 5
    FaceList(3) = 4
    FaceList(4) = 2
    FaceList(5) = 3
    FaceList(6) = 6
    FaceList(7) = 5
    ' Create the polyface mesh
    Dim polyfaceMeshObj As AcadPolyfaceMesh
    Set polyfaceMeshObj = ModelSpace.AddPolyfaceMesh _
                                  (vertex, FaceList)
    
    ' Change the viewing direction of the viewport to
    ' better see the polyface mesh
    Dim NewDirection(0 To 2) As Double
    NewDirection(0) = -1
    NewDirection(1) = -1
    NewDirection(2) = 1
    ThisDrawing.ActiveViewport.direction = NewDirection
    ThisDrawing.ActiveViewport = ThisDrawing.ActiveViewport
    ZoomAll
End Sub
Sub Ch8_CreateWedge()
    Dim wedgeObj As Acad3DSolid
    Dim center(0 To 2) As Double
    Dim length As Double
    Dim width As Double
    Dim height As Double
    
    ' Define the wedge
    center(0) = 5#: center(1) = 5#: center(2) = 0
    length = 10#: width = 15#: height = 20#
    
    ' Create the wedge in model space
    Set wedgeObj = ThisDrawing.ModelSpace. _
                   AddWedge(center, length, width, height)
    
    ' Change the viewing direction of the viewport
    Dim NewDirection(0 To 2) As Double
    NewDirection(0) = -1
    NewDirection(1) = -1
    NewDirection(2) = 1
    ThisDrawing.ActiveViewport.direction = NewDirection
    ThisDrawing.ActiveViewport = ThisDrawing.ActiveViewport
    ZoomAll
End Sub
Sub Ch8_Rotate_3DBox()
    Dim boxObj As Acad3DSolid
    Dim length As Double
    Dim width As Double
    Dim height As Double
    Dim center(0 To 2) As Double
    
    ' Define the box
    center(0) = 5: center(1) = 5: center(2) = 0
    length = 5
    width = 7
    height = 10
    
    ' Create the box object in model space
    Set boxObj = ThisDrawing.ModelSpace. _
                AddBox(center, length, width, height)
    
    ' Define the rotation axis with two points
    Dim rotatePt1(0 To 2) As Double
    Dim rotatePt2(0 To 2) As Double
    Dim rotateAngle As Double
    rotatePt1(0) = -3: rotatePt1(1) = 4: rotatePt1(2) = 0
    rotatePt2(0) = -3: rotatePt2(1) = -4: rotatePt2(2) = 0
    rotateAngle = 30
    rotateAngle = rotateAngle * 3.141592 / 180#
    ' Rotate the box
    boxObj.Rotate3D rotatePt1, rotatePt2, rotateAngle
    ZoomAll
End Sub
Sub Ch8_CreateRectangularArray()
    ' Create the circle
    Dim circleObj As AcadCircle
    Dim center(0 To 2) As Double
    Dim radius As Double
    center(0) = 2: center(1) = 2: center(2) = 0
    radius = 0.5
    Set circleObj = ThisDrawing.ModelSpace. _
                              AddCircle(center, radius)
    
    ' Define the rectangular array
    Dim numberOfRows As Long
    Dim numberOfColumns As Long
    Dim numberOfLevels As Long
    Dim distanceBwtnRows As Double
    Dim distanceBwtnColumns As Double
    Dim distanceBwtnLevels As Double
    numberOfRows = 4
    numberOfColumns = 4
    numberOfLevels = 3
    distanceBwtnRows = 1
    distanceBwtnColumns = 1
    distanceBwtnLevels = 4
    
    ' Create the array of objects
    Dim retObj As Variant
    retObj = circleObj.ArrayRectangular _
        (numberOfRows, numberOfColumns, _
         numberOfLevels, distanceBwtnRows, _
         distanceBwtnColumns, distanceBwtnLevels)
    ZoomAll
End Sub
Sub Ch8_MirrorABox3D()
    ' Create the box object
    Dim boxObj As Acad3DSolid
    Dim length As Double
    Dim width As Double
    Dim height As Double
    Dim center(0 To 2) As Double
    center(0) = 5#: center(1) = 5#: center(2) = 0
    length = 5#: width = 7: height = 10#
    
    ' Create the box (3DSolid) object in model space
    Set boxObj = ThisDrawing.ModelSpace. _
                AddBox(center, length, width, height)
    
    ' Define the mirroring plane with three points
    Dim mirrorPt1(0 To 2) As Double
    Dim mirrorPt2(0 To 2) As Double
    Dim mirrorPt3(0 To 2) As Double
    
    mirrorPt1(0) = 1.25: mirrorPt1(1) = 0: mirrorPt1(2) = 0
    mirrorPt2(0) = 1.25: mirrorPt2(1) = 2: mirrorPt2(2) = 0
    mirrorPt3(0) = 1.25: mirrorPt3(1) = 2: mirrorPt3(2) = 2
    
    ' Mirror the box
    Dim mirrorBoxObj As Acad3DSolid
    Set mirrorBoxObj = boxObj.Mirror3D _
                (mirrorPt1, mirrorPt2, mirrorPt3)
    mirrorBoxObj.Color = acRed
    ZoomAll
End Sub
Sub Ch8_FindInterferenceBetweenSolids()
    ' Define the box
    Dim boxObj As Acad3DSolid
    Dim length As Double
    Dim width As Double
    Dim height As Double
    Dim center(0 To 2) As Double
    center(0) = 5: center(1) = 5: center(2) = 0
    length = 5
    width = 7
    height = 10
    
    ' Create the box object in model space
    ' and color it white
    Set boxObj = ThisDrawing.ModelSpace. _
                AddBox(center, length, width, height)
    boxObj.Color = acWhite
    
    ' Define the cylinder
    Dim cylinderObj As Acad3DSolid
    Dim cylinderRadius As Double
    Dim cylinderHeight As Double
    center(0) = 0: center(1) = 0: center(2) = 0
    cylinderRadius = 5
    cylinderHeight = 20
    
    ' Create the Cylinder and
    ' color it cyan
    Set cylinderObj = ThisDrawing.ModelSpace.AddCylinder _
                   (center, cylinderRadius, cylinderHeight)
    cylinderObj.Color = acCyan
    
    ' Find the interference between the two solids
    ' and create a new solid from it. Color the
    ' new solid red.
    Dim solidObj As Acad3DSolid
    Set solidObj = boxObj.CheckInterference(cylinderObj, True)
    solidObj.Color = acRed
    ZoomAll
End Sub
Sub Ch8_SliceABox()
    ' Create the box object
    Dim boxObj As Acad3DSolid
    Dim length As Double
    Dim width As Double
    Dim height As Double
    Dim center(0 To 2) As Double
    center(0) = 5#: center(1) = 5#: center(2) = 0
    length = 5#: width = 7: height = 10#
    
    ' Create the box (3DSolid) object in model space
    Set boxObj = ThisDrawing.ModelSpace. _
                AddBox(center, length, width, height)
    boxObj.Color = acWhite
    
    ' Define the secion plane with three points
    Dim slicePt1(0 To 2) As Double
    Dim slicePt2(0 To 2) As Double
    Dim slicePt3(0 To 2) As Double
    
    slicePt1(0) = 1.5: slicePt1(1) = 7.5: slicePt1(2) = 0
    slicePt2(0) = 1.5: slicePt2(1) = 7.5: slicePt2(2) = 10
    slicePt3(0) = 8.5: slicePt3(1) = 2.5: slicePt3(2) = 10
    
    ' slice the box and color the new solid red
    Dim sliceObj As Acad3DSolid
    Set sliceObj = boxObj.SliceSolid _
                    (slicePt1, slicePt2, slicePt3, True)
    sliceObj.Color = acRed
    ZoomAll
End Sub
Sub Ch8_TranslateCoordinates()
    ' Create a polyline in model space.
    Dim plineObj As AcadPolyline
    Dim points(0 To 14) As Double
    
    ' Define the 2D polyline points
    points(0) = 1: points(1) = 1: points(2) = 0
    points(3) = 1: points(4) = 2: points(5) = 0
    points(6) = 2: points(7) = 2: points(8) = 0
    points(9) = 3: points(10) = 2: points(11) = 0
    points(12) = 4: points(13) = 4: points(14) = 0
        
    ' Create a light weight Polyline object in model space
    Set plineObj = ThisDrawing.ModelSpace.AddPolyline(points)
    
    ' Find the X and Y coordinates of the
    ' first vertex of the polyline
    Dim firstVertex As Variant
    firstVertex = plineObj.Coordinate(0)
    
    ' Find the Z coordinate for the polyline
    ' using the elevation property
    firstVertex(2) = plineObj.Elevation
    
    ' Change the normal for the pline so that the
    ' differences between the coordinate systems
    ' is obvious.
    Dim plineNormal(0 To 2) As Double
    plineNormal(0) = 0#
    plineNormal(1) = 1#
    plineNormal(2) = 2#
    plineObj.Normal = plineNormal
    
    ' Translate the OCS coordinate into WCS
    Dim coordinateWCS As Variant
    coordinateWCS = ThisDrawing.Utility.TranslateCoordinates _
          (firstVertex, acOCS, acWorld, False, plineNormal)
    
    ' Display the coordinates of the point
    MsgBox "The first vertex has the following coordinates:" _
           & vbCrLf & "OCS: " & firstVertex(0) & ", " & _
           firstVertex(1) & ", " & firstVertex(2) & vbCrLf & _
           "WCS: " & coordinateWCS(0) & ", " & _
           coordinateWCS(1) & ", " & coordinateWCS(2)
End Sub

Sub Ch9_SwitchToPaperSpace()
   ' Set the active space to paper space
    ThisDrawing.ActiveSpace = acPaperSpace
    
   ' Create the paperspace viewport
    Dim newVport As AcadPViewport
    Dim center(0 To 2) As Double
    center(0) = 3.25
    center(1) = 3
    center(2) = 0
    Set newVport = ThisDrawing.PaperSpace. _
                              AddPViewport(center, 6, 5)
    
   ' Change the view direction for the viewport
    Dim viewDir(0 To 2) As Double
    viewDir(0) = 1
    viewDir(1) = 1
    viewDir(2) = 1
    newVport.direction = viewDir
    
   ' Enable the viewport
    newVport.DISPLAY True
    
   ' Switch to model space
    ThisDrawing.mspace = True
    
   ' Set newVport current
   ' (not always necessary but a good idea)
    ThisDrawing.ActivePViewport = newVport
                                           
   ' Zoom Extents in model space
    ZoomExtents
    
   ' Turn model space editing off
    ThisDrawing.mspace = False
    
    ' ZoomExtents in paperspace
    ZoomExtents
End Sub
Sub Ch9_FourPViewports()
    Dim topVport, frontVport As AcadPViewport
    Dim rightVport, isoVport As AcadPViewport
    Dim pt(0 To 2) As Double
    Dim viewDir(0 To 2) As Double
    ThisDrawing.ActiveSpace = acPaperSpace
    ThisDrawing.mspace = True
'-------------------------------------------
' Take the existing PViewport and make it the topVport
'-------------------------------------------
    pt(0) = 2.5: pt(1) = 5.5: pt(2) = 0
    Set topVport = ThisDrawing.ActivePViewport
    'No need to set Direction for top view
    topVport.center = pt
    topVport.width = 2.5
    topVport.height = 2.5
    topVport.DISPLAY True
    ThisDrawing.mspace = True
    ThisDrawing.ActivePViewport = topVport
    ZoomExtents
    ZoomScaled 0.5, acZoomScaledRelativePSpace
'-------------------------------------------
'Create and setup frontVport
'-----------------------------------------
    pt(0) = 2.5: pt(1) = 2.5: pt(2) = 0
    Set frontVport = ThisDrawing.PaperSpace. _
            AddPViewport(pt, 2.5, 2.5)
    viewDir(0) = 0: viewDir(1) = 1: viewDir(2) = 0
    frontVport.direction = viewDir
    frontVport.DISPLAY acOn
    ThisDrawing.mspace = True
    ThisDrawing.ActivePViewport = frontVport
    ZoomExtents
    ZoomScaled 0.5, acZoomScaledRelativePSpace
'-------------------------------------------
'Create and setup rightVport
'-----------------------------------------
    pt(0) = 5.5: pt(1) = 5.5: pt(2) = 0
    Set rightVport = ThisDrawing.PaperSpace. _
            AddPViewport(pt, 2.5, 2.5)
    viewDir(0) = 1: viewDir(1) = 0: viewDir(2) = 0
    rightVport.direction = viewDir
    rightVport.DISPLAY acOn
    ThisDrawing.mspace = True
    ThisDrawing.ActivePViewport = rightVport
    ZoomExtents
    ZoomScaled 0.5, acZoomScaledRelativePSpace
'-------------------------------------------
'Create and set up isoVport
'-------------------------------------------
    pt(0) = 5.5: pt(1) = 2.5: pt(2) = 0
    Set isoVport = ThisDrawing.PaperSpace. _
                             AddPViewport(pt, 2.5, 2.5)
    viewDir(0) = 1: viewDir(1) = 1: viewDir(2) = 1
    isoVport.direction = viewDir
    isoVport.DISPLAY acOn
    ThisDrawing.mspace = True
    ThisDrawing.ActivePViewport = isoVport
    ZoomExtents
    ZoomScaled 0.5, acZoomScaledRelativePSpace
'-------------------------------------------
'Finish: Perform a regen in all viewports
'-------------------------------------------
    ThisDrawing.Regen True
End Sub
Sub Ch9_PrintModelSpace()
    ' Verify that the active space is model space
    If ThisDrawing.ActiveSpace = acPaperSpace Then
        ThisDrawing.mspace = True
        ThisDrawing.ActiveSpace = acModelSpace
    End If
    
    ' Set the extents and scale of the plot area
    ThisDrawing.ModelSpace.Layout.PlotType = acExtents
    ThisDrawing.ModelSpace.Layout. _
                          StandardScale = acScaleToFit
    
    ' Set the number of copies to one
    ThisDrawing.Plot.NumberOfCopies = 1
    
    ' Initiate the plot
    ThisDrawing.Plot.PlotToDevice
End Sub
Sub Ch9_PrintPaperSpace()
    ' Establish the paper space layouts to be plotted
    Dim strLayouts(0 To 1) As String
    Dim varLayouts As Variant
    strLayouts(0) = "Layout1"
    strLayouts(1) = "Layout2"
    varLayouts = strLayouts
    ThisDrawing.Plot.SetLayoutsToPlot varLayouts
    
    ' Set the number of copies to one
    ThisDrawing.Plot.NumberOfCopies = 1
        
    ' Initiate the plot
    ThisDrawing.Plot.PlotToDevice
End Sub
Sub Ch10_AttachingARaster()
    Dim insertionPoint(0 To 2) As Double
    Dim scalefactor As Double
    Dim rotationAngle As Double
    Dim imageName As String
    Dim rasterObj As AcadRasterImage
    imageName = "C:/Acad2000/sample/watch.jpg"
    insertionPoint(0) = 5
    insertionPoint(1) = 5
    insertionPoint(2) = 0
    scalefactor = 2
    rotationAngle = 0
    
    On Error GoTo ERRORHANDLER
    ' Attach the raster image in model space
    Set rasterObj = ThisDrawing.ModelSpace.AddRaster _
                  (imageName, insertionPoint, _
                   scalefactor, rotationAngle)
    ZoomAll
    Exit Sub
ERRORHANDLER:
    MsgBox Err.Description
End Sub
Sub Ch10_ClippingRasterBoundary()
    Dim insertionPoint(0 To 2) As Double
    Dim scalefactor As Double
    Dim rotationAngle As Double
    Dim imageName As String
    Dim rasterObj As AcadRasterImage
    
    imageName = "C:\AutoCAD\sample\downtown.jpg"
    insertionPoint(0) = 5
    insertionPoint(1) = 5
    insertionPoint(2) = 0
    scalefactor = 2
    rotationAngle = 0
    
    On Error GoTo ERRORHANDLER
    ' Creates a raster image in model space
    Set rasterObj = ThisDrawing.ModelSpace.AddRaster _
                    (imageName, insertionPoint, _
                     scalefactor, rotationAngle)
    ZoomAll
    
    ' Establish the clip boundary with an array of points
    Dim clipPoints(0 To 9) As Double
    clipPoints(0) = 6: clipPoints(1) = 6.75
    clipPoints(2) = 7: clipPoints(3) = 6
    clipPoints(4) = 6: clipPoints(5) = 5
    clipPoints(6) = 5: clipPoints(7) = 6
    clipPoints(8) = 6: clipPoints(9) = 6.75
    
    ' Clip the image
    rasterObj.ClipBoundary clipPoints
    
    ' Enable the display of the clip
    rasterObj.ClippingEnabled = True
    ThisDrawing.Regen acActiveViewport
    Exit Sub
    
ERRORHANDLER:
    MsgBox Err.Description
End Sub
Sub Ch10_InsertingABlock()
    ' Define the block
    Dim blockObj As AcadBlock
    Dim insertionPnt(0 To 2) As Double
    insertionPnt(0) = 0
    insertionPnt(1) = 0
    insertionPnt(2) = 0
    Set blockObj = ThisDrawing.Blocks.Add _
                     (insertionPnt, "CircleBlock")
    
    ' Add a circle to the block
    Dim circleObj As AcadCircle
    Dim center(0 To 2) As Double
    Dim radius As Double
    center(0) = 0
    center(1) = 0
    center(2) = 0
    radius = 1
    Set circleObj = blockObj.AddCircle(center, radius)
   
    ' Insert the block
    Dim blockRefObj As AcadBlockReference
    insertionPnt(0) = 2
    insertionPnt(1) = 2
    insertionPnt(2) = 0
    Set blockRefObj = ThisDrawing.ModelSpace.InsertBlock _
               (insertionPnt, "CircleBlock", 1#, 1#, 1#, 0)
    ZoomAll
    MsgBox "The circle belongs to " & blockRefObj.ObjectName
End Sub
Sub Ch10_ExplodingABlock()
    ' Define the block
    Dim blockObj As AcadBlock
    Dim insertionPnt(0 To 2) As Double
    insertionPnt(0) = 0
    insertionPnt(1) = 0
    insertionPnt(2) = 0
    Set blockObj = ThisDrawing.Blocks.Add _
                     (insertionPnt, "CircleBlock")
    
    ' Add a circle to the block
    Dim circleObj As AcadCircle
    Dim center(0 To 2) As Double
    Dim radius As Double
    center(0) = 0
    center(1) = 0
    center(2) = 0
    radius = 1
    Set circleObj = blockObj.AddCircle(center, radius)
   
    ' Insert the block
    Dim blockRefObj As AcadBlockReference
    insertionPnt(0) = 2
    insertionPnt(1) = 2
    insertionPnt(2) = 0
    Set blockRefObj = ThisDrawing.ModelSpace.InsertBlock _
               (insertionPnt, "CircleBlock", 1#, 1#, 1#, 0)
    ZoomAll
    MsgBox "The circle belongs to " & blockRefObj.ObjectName
    
    ' Explode the block reference
    Dim explodedObjects As Variant
    explodedObjects = blockRefObj.Explode
    
    ' Loop through the exploded objects
    Dim I As Integer
    For I = 0 To UBound(explodedObjects)
        explodedObjects(I).Color = acRed
        explodedObjects(I).Update
        MsgBox "Exploded Object " & I & ": " _
                            & explodedObjects(I).ObjectName
        explodedObjects(I).Color = acByLayer
        explodedObjects(I).Update
    Next
End Sub
Sub Ch10_RedefiningABlock()
    ' Define the block
    Dim blockObj As AcadBlock
    Dim insertionPnt(0 To 2) As Double
    insertionPnt(0) = 0
    insertionPnt(1) = 0
    insertionPnt(2) = 0
    Set blockObj = ThisDrawing.Blocks.Add _
                     (insertionPnt, "CircleBlock")
    
    ' Add a circle to the block
    Dim circleObj As AcadCircle
    Dim center(0 To 2) As Double
    Dim radius As Double
    center(0) = 0
    center(1) = 0
    center(2) = 0
    radius = 1
    Set circleObj = blockObj.AddCircle(center, radius)
   
    ' Insert the block
    Dim blockRefObj As AcadBlockReference
    insertionPnt(0) = 2
    insertionPnt(1) = 2
    insertionPnt(2) = 0
    Set blockRefObj = ThisDrawing.ModelSpace.InsertBlock _
               (insertionPnt, "CircleBlock", 1#, 1#, 1#, 0)
    ZoomAll
    
    ' Redefine the circle in the block,
    ' and update the block reference
    circleObj.radius = 3
    blockRefObj.Update
End Sub
Sub Ch10_CreatingAnAttribute()
    ' Define the block
    Dim blockObj As AcadBlock
    Dim insertionPnt(0 To 2) As Double
    insertionPnt(0) = 0
    insertionPnt(1) = 0
    insertionPnt(2) = 0
    Set blockObj = ThisDrawing.Blocks.Add _
                     (insertionPnt, "BlockWithAttribute")
    
    ' Add an attribute to the block
    Dim attributeObj As AcadAttribute
    Dim height As Double
    Dim mode As Long
    Dim prompt As String
    Dim insertionPoint(0 To 2) As Double
    Dim tag As String
    Dim value As String
    height = 1
    mode = acAttributeModeVerify
    prompt = "New Prompt"
    insertionPoint(0) = 5
    insertionPoint(1) = 5
    insertionPoint(2) = 0
    tag = "New Tag"
    value = "New Value"
    Set attributeObj = blockObj.AddAttribute(height, mode, _
                          prompt, insertionPoint, tag, value)
    ' Insert the block, creating a block reference
    ' and an attribute reference
    Dim blockRefObj As AcadBlockReference
    insertionPnt(0) = 2
    insertionPnt(1) = 2
    insertionPnt(2) = 0
    Set blockRefObj = ThisDrawing.ModelSpace.InsertBlock _
               (insertionPnt, "BlockWithAttribute", 1#, 1#, 1#, 0)
End Sub
Sub Ch10_RedefiningAnAttribute()
    ' Define the block
    Dim blockObj As AcadBlock
    Dim insertionPnt(0 To 2) As Double
    insertionPnt(0) = 0
    insertionPnt(1) = 0
    insertionPnt(2) = 0
    Set blockObj = ThisDrawing.Blocks.Add _
                     (insertionPnt, "BlockWithAttribute")
    
    ' Add an attribute to the block
    Dim attributeObj As AcadAttribute
    Dim height As Double
    Dim mode As Long
    Dim prompt As String
    Dim insertionPoint(0 To 2) As Double
    Dim tag As String
    Dim value As String
    height = 1
    mode = acAttributeModeVerify
    prompt = "New Prompt"
    insertionPoint(0) = 5
    insertionPoint(1) = 5
    insertionPoint(2) = 0
    tag = "New Tag"
    value = "New Value"
    Set attributeObj = blockObj.AddAttribute(height, mode, _
                          prompt, insertionPoint, tag, value)
    ' Insert the block, creating a block reference
    ' and an attribute reference
    Dim blockRefObj As AcadBlockReference
    insertionPnt(0) = 2
    insertionPnt(1) = 2
    insertionPnt(2) = 0
    Set blockRefObj = ThisDrawing.ModelSpace.InsertBlock _
               (insertionPnt, "BlockWithAttribute", 1#, 1#, 1#, 0)
    
    ' Redefine the attribute text to display backwards.
    attributeObj.Backward = True
    attributeObj.Update
End Sub
Sub Ch10_GettingAttributes()
    ' Create the block
    Dim blockObj As AcadBlock
    Dim insertionPnt(0 To 2) As Double
    insertionPnt(0) = 0
    insertionPnt(1) = 0
    insertionPnt(2) = 0
    Set blockObj = ThisDrawing.Blocks.Add _
                          (insertionPnt, "TESTBLOCK")
    
    ' Define the attribute definition
    Dim attributeObj As AcadAttribute
    Dim height As Double
    Dim mode As Long
    Dim prompt As String
    Dim insertionPoint(0 To 2) As Double
    Dim tag As String
    Dim value As String
    height = 1#
    mode = acAttributeModeVerify
    prompt = "Attribute Prompt"
    insertionPoint(0) = 5
    insertionPoint(1) = 5
    insertionPoint(2) = 0
    tag = "Attribute Tag"
    value = "Attribute Value"
    
    ' Create the attribute definition object on the block
    Set attributeObj = blockObj.AddAttribute _
                        (height, mode, prompt, _
                        insertionPoint, tag, value)
    
   
    ' Insert the block
    Dim blockRefObj As AcadBlockReference
    insertionPnt(0) = 2
    insertionPnt(1) = 2
    insertionPnt(2) = 0
    Set blockRefObj = ThisDrawing.ModelSpace.InsertBlock _
                     (insertionPnt, "TESTBLOCK", 1, 1, 1, 0)
    ZoomAll
    
    ' Get the attributes for the block reference
    Dim varAttributes As Variant
    varAttributes = blockRefObj.GetAttributes
    
    ' Move the attribute tags and values into a
    ' string to be displayed in a Msgbox
    Dim strAttributes As String
    strAttributes = ""
    Dim I As Integer
    For I = LBound(varAttributes) To UBound(varAttributes)
        strAttributes = strAttributes + "  Tag: " + _
                    varAttributes(I).TagString + vbCrLf + _
                    "   Value: " + varAttributes(I).textString
    Next
    MsgBox "The attributes for blockReference " + _
                   blockRefObj.name & " are: " & vbCrLf _
                   & strAttributes
    
    ' Change the value of the attribute
    ' Note: There is no SetAttributes. Once you have the
    ' variant array, you have the objects.
    ' Changing them changes the objects in the drawing.
    varAttributes(0).textString = "NEW VALUE!"
    
    ' Get the attributes again
    Dim newvarAttributes As Variant
    newvarAttributes = blockRefObj.GetAttributes
    
    ' Again, display the tags and values
    strAttributes = ""
    For I = LBound(varAttributes) To UBound(varAttributes)
        strAttributes = strAttributes + "  Tag: " + _
                    newvarAttributes(I).TagString + vbCrLf + _
                    "   Value: " + newvarAttributes(I).textString
    Next
    MsgBox "The attributes for blockReference " & _
                  blockRefObj.name & " are: " & vbCrLf _
                  & strAttributes
End Sub
Sub Ch10_AttachingExternalReference()
    On Error GoTo ERRORHANDLER
    Dim InsertPoint(0 To 2) As Double
    Dim insertedBlock As AcadExternalReference
    Dim tempBlock As AcadBlock
    Dim msg As String, PathName As String
    
    ' Define external reference to be inserted
    InsertPoint(0) = 1
    InsertPoint(1) = 1
    InsertPoint(2) = 0
    PathName = "c:/acad2000/sample/City map.dwg"
    
    ' Display current Block information for this drawing
    GoSub ListBlocks
    
    ' Add the external reference to the drawing
    Set insertedBlock = ThisDrawing.ModelSpace. _
            AttachExternalReference(PathName, "XREF_IMAGE", _
            InsertPoint, 1, 1, 1, 0, False)
    ZoomAll
    
    ' Display new Block information for this drawing
    GoSub ListBlocks
    Exit Sub
ListBlocks:
    msg = vbCrLf    ' Reset message
    For Each tempBlock In ThisDrawing.Blocks
        msg = msg & tempBlock.name & vbCrLf
    Next
    MsgBox "The current blocks in this drawing are: " & msg
    Return
    
ERRORHANDLER:
    MsgBox Err.Description
End Sub
Sub Ch10_DetachingExternalReference()
    On Error GoTo ERRORHANDLER
                          
    ' Define external reference to be inserted
    Dim xrefHome As AcadBlock
    Dim xrefInserted As AcadExternalReference
    Dim insertionPnt(0 To 2) As Double
    Dim PathName As String
    insertionPnt(0) = 1
    insertionPnt(1) = 1
    insertionPnt(2) = 0
    PathName = "c:/AutoCAD/sample/City map.dwg"
    
    ' Add the external reference
    Set xrefInserted = ThisDrawing.ModelSpace. _
            AttachExternalReference(PathName, "XREF_IMAGE", _
            insertionPnt, 1, 1, 1, 0, False)
    ZoomAll
    MsgBox "The external reference is attached."
    
    ' Detach the external reference definition
    Dim name As String
    name = xrefInserted.name
    ThisDrawing.Blocks.Item(name).Detach
    MsgBox "The external reference is detached."
    Exit Sub
ERRORHANDLER:
    MsgBox Err.Description
End Sub
Sub Ch10_ReloadingExternalReference()
    On Error GoTo ERRORHANDLER
                          
    ' Define external reference to be inserted
    Dim xrefHome As AcadBlock
    Dim xrefInserted As AcadExternalReference
    Dim insertionPnt(0 To 2) As Double
    Dim PathName As String
    insertionPnt(0) = 1
    insertionPnt(1) = 1
    insertionPnt(2) = 0
    PathName = "c:/AutoCAD/sample/City map.dwg"
    
    ' Add the external reference to the block
    Set xrefInserted = ThisDrawing.ModelSpace. _
            AttachExternalReference(PathName, "XREF_IMAGE", _
            insertionPnt, 1, 1, 1, 0, False)
    ZoomAll
    MsgBox "The external reference is attached."
    
    ' Reload the external reference definition
    ThisDrawing.Blocks.Item(xrefInserted.name).Reload
    MsgBox "The external reference is reloaded."
    Exit Sub
ERRORHANDLER:
    MsgBox Err.Description
End Sub
Sub Ch10_UnloadingExternalReference()
    On Error GoTo ERRORHANDLER
                          
    ' Define external reference to be inserted
    Dim xrefHome As AcadBlock
    Dim xrefInserted As AcadExternalReference
    Dim insertionPnt(0 To 2) As Double
    Dim PathName As String
    insertionPnt(0) = 1
    insertionPnt(1) = 1
    insertionPnt(2) = 0
    PathName = "c:/AutoCAD/sample/City map.dwg"
    
    ' Add the external reference
    Set xrefInserted = ThisDrawing.ModelSpace. _
            AttachExternalReference(PathName, "XREF_IMAGE", _
            insertionPnt, 1, 1, 1, 0, False)
    ZoomAll
    MsgBox "The external reference is attached."
    
    ' Unload the external reference definition
    ThisDrawing.Blocks.Item(xrefInserted.name).Unload
    MsgBox "The external reference is unloaded."
    Exit Sub
ERRORHANDLER:
    MsgBox Err.Description
End Sub
Sub Ch10_BindingExternalReference()
    On Error GoTo ERRORHANDLER
                          
    ' Define external reference to be inserted
    Dim xrefHome As AcadBlock
    Dim xrefInserted As AcadExternalReference
    Dim insertionPnt(0 To 2) As Double
    Dim PathName As String
    insertionPnt(0) = 1
    insertionPnt(1) = 1
    insertionPnt(2) = 0
    PathName = "c:/AutoCAD/sample/City map.dwg"
    
    ' Add the external reference
    Set xrefInserted = ThisDrawing.ModelSpace. _
            AttachExternalReference(PathName, "XREF_IMAGE", _
            insertionPnt, 1, 1, 1, 0, False)
    ZoomAll
    MsgBox "The external reference is attached."
    
    ' Bind the external reference definition
    ThisDrawing.Blocks.Item(xrefInserted.name).Bind False
    MsgBox "The external reference is bound."
    Exit Sub
ERRORHANDLER:
    MsgBox Err.Description
End Sub
Sub Ch10_AttachXDataToSelectionSetObjects()
    ' Create the selection set
    Dim sset As Object
    Set sset = ThisDrawing.SelectionSets.Add("SS1")
    
    ' Prompt the user to select objects
    sset.SelectOnScreen
    
    ' Define the xdata
    Dim appName As String, xdataStr As String
    appName = "MY_APP"
    xdataStr = "This is some xdata"
    Dim xdataType(0 To 1) As Integer
    Dim xdata(0 To 1) As Variant
    
    ' Define the values for each array
    '1001 indicates the appName
    xdataType(0) = 1001
    xdata(0) = appName
    '1000 indicates a string value
    xdataType(1) = 1000
    xdata(1) = xdataStr
    
    ' Loop through all entities in the selection
    ' set and assign the xdata to each entity
    Dim ent As Object
    For Each ent In sset
        ent.SetXData xdataType, xdata
    Next ent
End Sub
Sub Ch10_ViewXData()
    ' Find the selection created in previous example
    Dim sset As Object
    Set sset = ThisDrawing.SelectionSets.Item("SS1")
    
    ' Define the xdata variables to hold xdata information
    Dim xdataType As Variant
    Dim xdata As Variant
    Dim xd As Variant
    
    'Define index counter
    Dim xdi As Integer
    xdi = 0
    
    ' Loop throught the objects in the selection set
    ' and retrieve the xdata for the object
    Dim msgstr As String
    Dim appName As String
    Dim ent As AcadEntity
    appName = "MY_APP"
    For Each ent In sset
        msgstr = ""
        xdi = 0
        
        ' Retrieve the appName xdata type and value
        ent.GetXData appName, xdataType, xdata
        
        ' If the xdataType variable is not initialized, there
        ' was no appName xdata to retrieve for that entity
        If VarType(xdataType) <> vbEmpty Then
            For Each xd In xdata
                msgstr = msgstr & vbCrLf & xdataType(xdi) _
                         & ": " & xd
                xdi = xdi + 1
            Next xd
        End If
        
        ' If the msgstr variable is NULL, there was no xdata
        If msgstr = "" Then msgstr = vbCrLf & "NONE"
        MsgBox appName & " xdata on " & ent.ObjectName & _
                                      ":" & vbCrLf & msgstr
    Next ent
End Sub
Sub Ch11_ColorEntities()
    Dim entry As Object
    On Error Resume Next
    For Each entry In ThisDrawing.ModelSpace
        entry.Color = acRed
    Next entry
End Sub
Sub Ch11_ColorEntities2()
    Dim entry As Object
    On Error GoTo MyErrorHandler
    For Each entry In ThisDrawing.ModelSpace
        entry.Color = acRed
    Next entry
    ' Important! Exit the subroutine before the error handler
    Exit Sub
MyErrorHandler:
    MsgBox entry.EntityName + " is on a locked layer." + _
                 " The handle is: " + entry.handle
    Resume Next
End Sub
Sub Ch12_Extract()
    Dim Excel As Excel.Application
    Dim ExcelSheet As Object
    Dim ExcelWorkbook As Object
    
    Dim RowNum As Integer
    Dim Header As Boolean
    Dim elem As AcadEntity
    Dim Array1 As Variant
    Dim count As Integer
    
    ' Launch Excel.
    Set Excel = New Excel.Application
    
    ' Create a new workbook and find the active sheet.
    Set ExcelWorkbook = Excel.Workbooks.Add
    Set ExcelSheet = Excel.ActiveSheet
    ExcelWorkbook.SaveAs "Attribute.xls"
    
    RowNum = 1
    Header = False
    ' Iterate through model space finding
    ' all block references.
    For Each elem In ThisDrawing.ModelSpace
        With elem
            ' When a block reference has been found,
            ' check it for attributes
            If StrComp(.EntityName, "AcDbBlockReference", 1) _
                = 0 Then
                If .HasAttributes Then
                    ' Get the attributes
                    Array1 = .GetAttributes
                    ' Copy the Tagstrings for the
                    ' Attributes into Excel
                    For count = LBound(Array1) To UBound(Array1)
                        If Header = False Then
                            If StrComp(Array1(count).EntityName, _
                                  "AcDbAttribute", 1) = 0 Then
                                ExcelSheet.Cells(RowNum, _
                                    count + 1).value = _
                                    Array1(count).TagString
                            End If
                        End If
                    Next count
                    RowNum = RowNum + 1
                    For count = LBound(Array1) To UBound(Array1)
                        ExcelSheet.Cells(RowNum, count + 1).value _
                                    = Array1(count).textString
                    Next count
                    Header = True
                End If
            End If
        End With
    Next elem
    Excel.Application.Quit
End Sub

Attribute VB_Name = "GPDialog"
Attribute VB_Base = "0{7D99210D-DD95-11D2-8EC1-0060B087348B}{7D992101-DD95-11D2-8EC1-0060B087348B}"
Attribute VB_Creatable = False
Attribute VB_PredeclaredId = True
Attribute VB_Exposed = False
Attribute VB_TemplateDerived = False
Attribute VB_Customizable = False

'      AutoCAD 2000
'
'      GPDialog Form Code Module
'
'      Example code for all Methods and Properties
'      ActiveX Automation and VBA Samples.
'
'      Copyright (C) 1999 by Autodesk, Inc.
'
'      Permission to use, copy, modify, and distribute this software
'      for any purpose and without fee is hereby granted, provided
'      that the above copyright notice appears in all copies and
'      that both that copyright notice and the limited warranty and
'      restricted rights notice below appear in all supporting
'      documentation.
'
'      AUTODESK PROVIDES THIS PROGRAM "AS IS" AND WITH ALL FAULTS.
'      AUTODESK SPECIFICALLY DISCLAIMS ANY IMPLIED WARRANTY OF
'      MERCHANTABILITY OR FITNESS FOR A PARTICULAR USE.  AUTODESK, INC.
'      DOES NOT WARRANT THAT THE OPERATION OF THE PROGRAM WILL BE
'      UNINTERRUPTED OR ERROR FREE.
'
'      Use, duplication, or disclosure by the U.S. Government is subject to
'      restrictions set forth in FAR 52.227-19 (Commercial Computer
'      Software - Restricted Rights) and DFAR 252.227-7013(c)(1)(ii)
'      (Rights in Technical Data and Computer Software), as applicable.
'
Option Explicit

Private Sub gp_poly_Click()
    gp_tsides.Enabled = True
    GPDialog_Tutorial.tshape = "Polygon"
End Sub
Private Sub gp_circ_Click()
    gp_tsides.Enabled = False
    GPDialog_Tutorial.tshape = "Circle"
End Sub
Private Sub accept_Click()
    If GPDialog_Tutorial.tshape = "Polygon" Then
        GPDialog_Tutorial.tsides = CInt(gp_tsides.text)
        If (GPDialog_Tutorial.tsides < 3#) Or _
                         (GPDialog_Tutorial.tsides > 1024#) Then
            MsgBox "Enter a value between 3 and " & _
                    "1024 for the number of sides."
            Exit Sub
        End If
    End If
    GPDialog_Tutorial.trad = CDbl(gp_trad.text)
    GPDialog_Tutorial.tspac = CDbl(gp_tspac.text)
    If GPDialog_Tutorial.trad < 0# Then
        MsgBox "Enter a positive value for the radius."
        Exit Sub
    End If
    If (GPDialog_Tutorial.tspac < 0#) Then
        MsgBox "Enter a positive value for the spacing."
        Exit Sub
    End If
    GPDialog.Hide
End Sub
Private Sub cancel_Click()
    Unload Me
    End
End Sub

Private Sub UserForm_Initialize()
    gp_circ.value = True
    gp_trad.text = ".2"
    gp_tspac.text = ".1"
    gp_tsides.text = "5"
    gp_tsides.Enabled = False
    GPDialog_Tutorial.tsides = 5
End Sub

Attribute VB_Name = "GPDialog_Tutorial"
'      AutoCAD 2000
'
'      GPDialog_Tutorial Code Module
'
'      Example code for all Methods and Properties
'      ActiveX Automation and VBA Samples.
'
'      Copyright (C) 1999 by Autodesk, Inc.
'
'      Permission to use, copy, modify, and distribute this software
'      for any purpose and without fee is hereby granted, provided
'      that the above copyright notice appears in all copies and
'      that both that copyright notice and the limited warranty and
'      restricted rights notice below appear in all supporting
'      documentation.
'
'      AUTODESK PROVIDES THIS PROGRAM "AS IS" AND WITH ALL FAULTS.
'      AUTODESK SPECIFICALLY DISCLAIMS ANY IMPLIED WARRANTY OF
'      MERCHANTABILITY OR FITNESS FOR A PARTICULAR USE.  AUTODESK, INC.
'      DOES NOT WARRANT THAT THE OPERATION OF THE PROGRAM WILL BE
'      UNINTERRUPTED OR ERROR FREE.
'
'      Use, duplication, or disclosure by the U.S. Government is subject to
'      restrictions set forth in FAR 52.227-19 (Commercial Computer
'      Software - Restricted Rights) and DFAR 252.227-7013(c)(1)(ii)
'      (Rights in Technical Data and Computer Software), as applicable.
'
Option Explicit


Const pi = 3.14159
' Variables used to store garden path parameters
Private sp(0 To 2) As Double
Private ep(0 To 2) As Double
Private hwidth As Double
Private pangle As Double
Private plength As Double
Private totalwidth As Double
Private angp90 As Double
Private angm90 As Double

Public trad As Double       ' Updated
Public tspac As Double      ' Updated
Public tsides As Integer    ' Add
Public tshape As String     ' Add


' Convert angle in degrees to radians
Function dtr(a As Double) As Double
    dtr = (a / 180) * pi
End Function
' Calculate distance between two points
Function distance(sp As Variant, ep As Variant) _
 As Double
    Dim x As Double
    Dim y As Double
    Dim z As Double
    x = sp(0) - ep(0)
    y = sp(1) - ep(1)
    z = sp(2) - ep(2)
    distance = Sqr((Sqr((x ^ 2) + (y ^ 2)) ^ 2) + (z ^ 2))
End Function
' Acquire information for garden path
Private Sub gpuser()
    Dim varRet As Variant
    
    varRet = ThisDrawing.Utility.GetPoint( _
     , "Start point of path: ")
    sp(0) = varRet(0)
    sp(1) = varRet(1)
    sp(2) = varRet(2)
    varRet = ThisDrawing.Utility.GetPoint( _
     , "Endpoint of path: ")
    ep(0) = varRet(0)
    ep(1) = varRet(1)
    ep(2) = varRet(2)
    hwidth = ThisDrawing.Utility. _
        GetDistance(sp, "Half width of path: ")
    Load GPDialog
    GPDialog.Show
    pangle = ThisDrawing.Utility.AngleFromXAxis( _
     sp, ep)
    totalwidth = 2 * hwidth
    plength = distance(sp, ep)
    angp90 = pangle + dtr(90)
    angm90 = pangle - dtr(90)
End Sub
' Draw outline of path
Private Sub drawout()
    Dim points(0 To 9) As Double
    Dim pline As AcadLWPolyline
    Dim varRet As Variant
    varRet = ThisDrawing.Utility.PolarPoint( _
        sp, angm90, hwidth)
    points(0) = varRet(0)
    points(1) = varRet(1)
    points(8) = varRet(0)
    points(9) = varRet(1)
    varRet = ThisDrawing.Utility.PolarPoint( _
        varRet, pangle, plength)
    points(2) = varRet(0)
    points(3) = varRet(1)
    varRet = ThisDrawing.Utility.PolarPoint( _
        varRet, angp90, totalwidth)
    points(4) = varRet(0)
    points(5) = varRet(1)
    varRet = ThisDrawing.Utility.PolarPoint( _
        varRet, pangle + dtr(180), plength)
    points(6) = varRet(0)
    points(7) = varRet(1)
    Set pline = ThisDrawing.ModelSpace. _
     AddLightWeightPolyline(points)
End Sub
' Place one row of tiles the given distance along path
' and possibly offset it
Private Sub drow(pd As Double, offset As Double)
    Dim pfirst(0 To 2) As Double
    Dim pctile(0 To 2) As Double
    Dim pltile(0 To 2) As Double
    Dim cir As AcadCircle
    Dim varRet As Variant
    varRet = ThisDrawing.Utility.PolarPoint( _
     sp, pangle, pd)
    pfirst(0) = varRet(0)
    pfirst(1) = varRet(1)
    pfirst(2) = varRet(2)
    varRet = ThisDrawing.Utility.PolarPoint( _
     pfirst, angp90, offset)
    pctile(0) = varRet(0)
    pctile(1) = varRet(1)
    pctile(2) = varRet(2)
    pltile(0) = pctile(0)
    pltile(1) = pctile(1)
    pltile(2) = pctile(2)
    Do While distance(pfirst, pltile) < (hwidth - trad)
        DrawShape (pltile)       ' Updated
        varRet = ThisDrawing.Utility.PolarPoint( _
         pltile, angp90, (tspac + trad + trad))
        pltile(0) = varRet(0)
        pltile(1) = varRet(1)
        pltile(2) = varRet(2)
    Loop
    varRet = ThisDrawing.Utility.PolarPoint( _
     pctile, angm90, tspac + trad + trad)
    pltile(0) = varRet(0)
    pltile(1) = varRet(1)
    pltile(2) = varRet(2)
    Do While distance(pfirst, pltile) < (hwidth - trad)
        DrawShape (pltile)       ' Updated
        varRet = ThisDrawing.Utility.PolarPoint( _
         pltile, angm90, (tspac + trad + trad))
        pltile(0) = varRet(0)
        pltile(1) = varRet(1)
        pltile(2) = varRet(2)
    Loop
End Sub
' Draw the rows of tiles
Private Sub drawtiles()
    Dim pdist As Double
    Dim offset As Double
    pdist = trad + tspac
    offset = 0
    Do While pdist <= (plength - trad)
        drow pdist, offset
        pdist = pdist + ((tspac + trad + trad) * Sin(dtr(60)))
        If offset = 0 Then
            offset = (tspac + trad + trad) * Cos(dtr(60))
        Else
            offset = 0
        End If
    Loop
End Sub
Sub GardenPath()
    Dim sblip As Variant
    Dim scmde As Variant
    gpuser
    sblip = ThisDrawing.GetVariable("blipmode")
    scmde = ThisDrawing.GetVariable("cmdecho")
    ThisDrawing.SetVariable "blipmode", 0
    ThisDrawing.SetVariable "cmdecho", 0
    drawout
    drawtiles
    ThisDrawing.SetVariable "blipmode", sblip
    ThisDrawing.SetVariable "cmdecho", scmde
End Sub
'Draw the tile with the designated shape
Sub DrawShape(pltile)
    Dim angleSegment As Double
    Dim currentAngle As Double
    Dim angleInRadians As Double
    Dim currentSide As Integer
    Dim varRet As Variant
    Dim aCircle As AcadCircle
    Dim aPolygon As AcadLWPolyline
    ReDim points(1 To tsides * 2) As Double
    'Branch based on the type of shape to draw
    Select Case tshape
    Case "Circle"
        Set aCircle = ThisDrawing.ModelSpace. _
                      AddCircle(pltile, trad)
    Case "Polygon"
        angleSegment = 360 / tsides
        currentAngle = 0
        For currentSide = 0 To (tsides - 1)
            angleInRadians = dtr(currentAngle)
            varRet = ThisDrawing.Utility.PolarPoint(pltile, _
                     angleInRadians, trad)
            points((currentSide * 2) + 1) = varRet(0)
            points((currentSide * 2) + 2) = varRet(1)
            currentAngle = currentAngle + angleSegment
        Next currentSide
        Set aPolygon = ThisDrawing.ModelSpace. _
                        AddLightWeightPolyline(points)
        aPolygon.Closed = True
    End Select
End Sub

Attribute VB_Name = "GardenPath_Tutorial"
'      AutoCAD 2000
'
'      GardenPath_Tutorial Code Module
'
'      Example code for all Methods and Properties
'      ActiveX Automation and VBA Samples.
'
'      Copyright (C) 1999 by Autodesk, Inc.
'
'      Permission to use, copy, modify, and distribute this software
'      for any purpose and without fee is hereby granted, provided
'      that the above copyright notice appears in all copies and
'      that both that copyright notice and the limited warranty and
'      restricted rights notice below appear in all supporting
'      documentation.
'
'      AUTODESK PROVIDES THIS PROGRAM "AS IS" AND WITH ALL FAULTS.
'      AUTODESK SPECIFICALLY DISCLAIMS ANY IMPLIED WARRANTY OF
'      MERCHANTABILITY OR FITNESS FOR A PARTICULAR USE.  AUTODESK, INC.
'      DOES NOT WARRANT THAT THE OPERATION OF THE PROGRAM WILL BE
'      UNINTERRUPTED OR ERROR FREE.
'
'      Use, duplication, or disclosure by the U.S. Government is subject to
'      restrictions set forth in FAR 52.227-19 (Commercial Computer
'      Software - Restricted Rights) and DFAR 252.227-7013(c)(1)(ii)
'      (Rights in Technical Data and Computer Software), as applicable.
'
Option Explicit

Const pi = 3.14159
' Variables used to store garden path parameters
Private sp(0 To 2) As Double
Private ep(0 To 2) As Double
Private hwidth As Double
Private trad As Double
Private tspac As Double
Private pangle As Double
Private plength As Double
Private totalwidth As Double
Private angp90 As Double
Private angm90 As Double

' Convert angle in degrees to radians
Function dtr(a As Double) As Double
    dtr = (a / 180) * pi
End Function
' Calculate distance between two points
Function distance(sp As Variant, ep As Variant) _
 As Double
    Dim x As Double
    Dim y As Double
    Dim z As Double
    x = sp(0) - ep(0)
    y = sp(1) - ep(1)
    z = sp(2) - ep(2)
    distance = Sqr((Sqr((x ^ 2) + (y ^ 2)) ^ 2) + (z ^ 2))
End Function
' Acquire information for garden path
Private Sub gpuser()
    Dim varRet As Variant
    
    varRet = ThisDrawing.Utility.GetPoint( _
     , "Start point of path: ")
    sp(0) = varRet(0)
    sp(1) = varRet(1)
    sp(2) = varRet(2)
    varRet = ThisDrawing.Utility.GetPoint( _
     , "Endpoint of path: ")
    ep(0) = varRet(0)
    ep(1) = varRet(1)
    ep(2) = varRet(2)
    hwidth = ThisDrawing.Utility. _
     GetDistance(sp, "Half width of path: ")
    trad = ThisDrawing.Utility. _
     GetDistance(sp, "Radius of tiles: ")
    tspac = ThisDrawing.Utility. _
     GetDistance(sp, "Spacing between tiles: ")
    pangle = ThisDrawing.Utility.AngleFromXAxis( _
     sp, ep)
    totalwidth = 2 * hwidth
    plength = distance(sp, ep)
    angp90 = pangle + dtr(90)
    angm90 = pangle - dtr(90)
End Sub
' Draw outline of path
Private Sub drawout()
    Dim points(0 To 9) As Double
    Dim pline As AcadLWPolyline
    Dim varRet As Variant
    varRet = ThisDrawing.Utility.PolarPoint( _
        sp, angm90, hwidth)
    points(0) = varRet(0)
    points(1) = varRet(1)
    points(8) = varRet(0)
    points(9) = varRet(1)
    varRet = ThisDrawing.Utility.PolarPoint( _
        varRet, pangle, plength)
    points(2) = varRet(0)
    points(3) = varRet(1)
    varRet = ThisDrawing.Utility.PolarPoint( _
        varRet, angp90, totalwidth)
    points(4) = varRet(0)
    points(5) = varRet(1)
    varRet = ThisDrawing.Utility.PolarPoint( _
        varRet, pangle + dtr(180), plength)
    points(6) = varRet(0)
    points(7) = varRet(1)
    Set pline = ThisDrawing.ModelSpace. _
     AddLightWeightPolyline(points)
End Sub
' Place one row of tiles the given distance along path
' and possibly offset it
Private Sub drow(pd As Double, offset As Double)
    Dim pfirst(0 To 2) As Double
    Dim pctile(0 To 2) As Double
    Dim pltile(0 To 2) As Double
    Dim cir As AcadCircle
    Dim varRet As Variant
    varRet = ThisDrawing.Utility.PolarPoint( _
     sp, pangle, pd)
    pfirst(0) = varRet(0)
    pfirst(1) = varRet(1)
    pfirst(2) = varRet(2)
    varRet = ThisDrawing.Utility.PolarPoint( _
     pfirst, angp90, offset)
    pctile(0) = varRet(0)
    pctile(1) = varRet(1)
    pctile(2) = varRet(2)
    pltile(0) = pctile(0)
    pltile(1) = pctile(1)
    pltile(2) = pctile(2)
    Do While distance(pfirst, pltile) < (hwidth - trad)
        Set cir = ThisDrawing.ModelSpace.AddCircle( _
         pltile, trad)
        varRet = ThisDrawing.Utility.PolarPoint( _
         pltile, angp90, (tspac + trad + trad))
        pltile(0) = varRet(0)
        pltile(1) = varRet(1)
        pltile(2) = varRet(2)
    Loop
    varRet = ThisDrawing.Utility.PolarPoint( _
     pctile, angm90, tspac + trad + trad)
    pltile(0) = varRet(0)
    pltile(1) = varRet(1)
    pltile(2) = varRet(2)
    Do While distance(pfirst, pltile) < (hwidth - trad)
        Set cir = ThisDrawing.ModelSpace.AddCircle( _
         pltile, trad)
        varRet = ThisDrawing.Utility.PolarPoint( _
         pltile, angm90, (tspac + trad + trad))
        pltile(0) = varRet(0)
        pltile(1) = varRet(1)
        pltile(2) = varRet(2)
    Loop
End Sub
' Draw the rows of tiles
Private Sub drawtiles()
    Dim pdist As Double
    Dim offset As Double
    pdist = trad + tspac
    offset = 0
    Do While pdist <= (plength - trad)
        drow pdist, offset
        pdist = pdist + ((tspac + trad + trad) * Sin(dtr(60)))
        If offset = 0 Then
            offset = (tspac + trad + trad) * Cos(dtr(60))
        Else
            offset = 0
        End If
    Loop
End Sub
Sub GardenPath()
    Dim sblip As Variant
    Dim scmde As Variant
    gpuser
    sblip = ThisDrawing.GetVariable("blipmode")
    scmde = ThisDrawing.GetVariable("cmdecho")
    ThisDrawing.SetVariable "blipmode", 0
    ThisDrawing.SetVariable "cmdecho", 0
    drawout
    drawtiles
    ThisDrawing.SetVariable "blipmode", sblip
    ThisDrawing.SetVariable "cmdecho", scmde
End Sub

Attribute VB_Name = "ReferenceGuide_Examples"
'      AutoCAD 2000
'
'      ReferenceGuide_Examples Code Module
'
'      Example code for all Methods and Properties
'      ActiveX Automation and VBA Samples.
'
'      Copyright (C) 1999 by Autodesk, Inc.
'
'      Permission to use, copy, modify, and distribute this software
'      for any purpose and without fee is hereby granted, provided
'      that the above copyright notice appears in all copies and
'      that both that copyright notice and the limited warranty and
'      restricted rights notice below appear in all supporting
'      documentation.
'
'      AUTODESK PROVIDES THIS PROGRAM "AS IS" AND WITH ALL FAULTS.
'      AUTODESK SPECIFICALLY DISCLAIMS ANY IMPLIED WARRANTY OF
'      MERCHANTABILITY OR FITNESS FOR A PARTICULAR USE.  AUTODESK, INC.
'      DOES NOT WARRANT THAT THE OPERATION OF THE PROGRAM WILL BE
'      UNINTERRUPTED OR ERROR FREE.
'
'      Use, duplication, or disclosure by the U.S. Government is subject to
'      restrictions set forth in FAR 52.227-19 (Commercial Computer
'      Software - Restricted Rights) and DFAR 252.227-7013(c)(1)(ii)
'      (Rights in Technical Data and Computer Software), as applicable.
'
Option Explicit
Sub Example_ArrowHeadType()
    ' This example creates a Leader object in model space with an associated Annotation
    ' and then alters the visible appearance (shape) of its arrow head
    ' using the ArrowHeadType property

    Dim leaderObj As AcadLeader, MTextObj As AcadMText
    Dim points(0 To 8) As Double, insertionPoint(0 To 2) As Double, iTextWidth As Double
    Dim leaderType As Integer
    Dim annotationObject As Object
    Dim textString As String
    
    ' Define the new MText object
    textString = "Hello, World."
    insertionPoint(0) = 5: insertionPoint(1) = 5: insertionPoint(2) = 0
    iTextWidth = 2
    
    ' Create the MText object in model space
    Set MTextObj = ThisDrawing.ModelSpace.AddMText(insertionPoint, iTextWidth, textString)
    
    ' Data for Leader
    points(0) = 0: points(1) = 0: points(2) = 0
    points(3) = 4: points(4) = 4: points(5) = 0
    points(6) = 4: points(7) = 5: points(8) = 0
    leaderType = acLineWithArrow
       
    ' Create the Leader object in model space and Associate new MText object
    ' with new Leader by making the MText object the annotation for the Leader
    Set annotationObject = MTextObj
    Set leaderObj = ThisDrawing.ModelSpace.AddLeader(points, annotationObject, leaderType)
    ThisDrawing.Application.ZoomAll

    ' Read and display current arrow head type
    MsgBox "The arrow head type for this object is: " & leaderObj.ArrowheadType

    ' Alter the arrow head type property for this object
    leaderObj.ArrowheadType = acArrowBoxBlank
    ThisDrawing.Application.ZoomAll
    
    ' Read and display current arrow head type
    MsgBox "The arrow head type for this object is now set to: " & leaderObj.ArrowheadType
End Sub
Sub Example_ArcLength()
    ' This example creates an Arc in model space and returns the length of the new Arc
    Dim arcObj As AcadArc
    Dim centerPoint(0 To 2)  As Double
    Dim radius As Double
    Dim startAngleInDegree As Double, endAngleInDegree As Double
    Dim startAngleInRadian As Double, endAngleInRadian As Double
    
    ' Define the Arc
    centerPoint(0) = 0: centerPoint(1) = 0: centerPoint(2) = 0
    radius = 5#
    startAngleInDegree = 10#: endAngleInDegree = 230#

    ' Convert the angles in degrees to angles in radians
    startAngleInRadian = startAngleInDegree * 3.141592 / 180#
    endAngleInRadian = endAngleInDegree * 3.141592 / 180#
    
    ' Create the arc object in model space
    Set arcObj = ThisDrawing.ModelSpace.AddArc(centerPoint, radius, startAngleInRadian, endAngleInRadian)
    ThisDrawing.Application.ZoomAll
    
    ' Return length of new arc
    MsgBox "The length of the new Arc is: " & arcObj.ArcLength
End Sub

Sub Example_TotalAngle()
    ' This example creates an Arc in model space and
    ' returns the total angle of the new Arc
    
    Dim arcObj As AcadArc
    Dim centerPoint(0 To 2) As Double
    Dim radius As Double
    Dim startAngleInDegree As Double, endAngleInDegree As Double
    Dim startAngleInRadian As Double, endAngleInRadian As Double
    
    ' Define the Arc
    centerPoint(0) = 0: centerPoint(1) = 0: centerPoint(2) = 0
    radius = 5#
    startAngleInDegree = 10#: endAngleInDegree = 230#

    ' Convert the angles in degrees to angles in radians
    startAngleInRadian = startAngleInDegree * 3.141592 / 180#
    endAngleInRadian = endAngleInDegree * 3.141592 / 180#
    
    ' Create the arc object in model space
    Set arcObj = ThisDrawing.ModelSpace.AddArc(centerPoint, radius, startAngleInRadian, endAngleInRadian)
    ThisDrawing.Application.ZoomAll
    
    ' Return length of new arc
    MsgBox "The total angle of the new Arc is: " & arcObj.TotalAngle
End Sub

Sub Example_HasExtensionDictionary()
    ' This example will iterate through each object in the current drawing and
    ' determine if that object has an associated Extension Dictionary
    
    Dim DrawingObject As AcadObject
    Dim ExtensionDictionaryResults As String
    
    ' Make sure this drawing contains objects before we continue
    If ThisDrawing.ModelSpace.count = 0 Then
        MsgBox "There are no objects in the current drawing."
        Exit Sub
    End If
    
    For Each DrawingObject In ThisDrawing.ModelSpace
        ' Determine if object contains Extension Dictionary
        Select Case DrawingObject.HasExtensionDictionary
            Case True
                ExtensionDictionaryResults = ExtensionDictionaryResults & DrawingObject.ObjectName & " has an associated Extension Dictionary" & vbCrLf
            Case False
                ExtensionDictionaryResults = ExtensionDictionaryResults & DrawingObject.ObjectName & " does not have an associated Extension Dictionary" & vbCrLf
        End Select
    Next
    
    MsgBox ExtensionDictionaryResults
End Sub

Sub Example_GetExtensionDictionary()
    ' This example creates a Circle object in model space and
    ' adds a new Extension Dictionary to the Circle object
    
    Dim EDictionary As AcadDictionary
    Dim circleObj As AcadCircle
    Dim centerPoint(0 To 2) As Double
    Dim radius As Double
    
    ' Define the Circle object
    centerPoint(0) = 0: centerPoint(1) = 0: centerPoint(2) = 0
    radius = 5#
    
    ' Create the Circle object in model space
    Set circleObj = ThisDrawing.ModelSpace.AddCircle(centerPoint, radius)

    ThisDrawing.Application.ZoomAll
    
    MsgBox "Circle object Extension Dictionary state before: " & circleObj.HasExtensionDictionary
    
    ' Create an Extension Dictionary for the new Circle
    Set EDictionary = circleObj.GetExtensionDictionary
    
    MsgBox "Circle object Extension Dictionary state after: " & circleObj.HasExtensionDictionary
End Sub

Sub Example_Circumference()
    ' This example creates a Circle object in model space and
    ' returns the circumference of the Circle
    
    Dim circleObj As AcadCircle
    Dim centerPoint(0 To 2) As Double
    Dim radius As Double
    
    ' Define the new Circle object
    centerPoint(0) = 0: centerPoint(1) = 0: centerPoint(2) = 0
    radius = 5#
    
    ' Create the Circle object in model space
    Set circleObj = ThisDrawing.ModelSpace.AddCircle(centerPoint, radius)

    ThisDrawing.Application.ZoomAll
    
    MsgBox "The circumference of the new Circle is: " & circleObj.Circumference
    
End Sub

Sub Example_Diameter()
    ' This example creates a Circle object in model space and
    ' returns the diameter of the new Circle
    
    Dim circleObj As AcadCircle
    Dim centerPoint(0 To 2) As Double
    Dim radius As Double
    
    ' Define the new Circle object
    centerPoint(0) = 0: centerPoint(1) = 0: centerPoint(2) = 0
    radius = 5#
    
    ' Create the Circle object in model space
    Set circleObj = ThisDrawing.ModelSpace.AddCircle(centerPoint, radius)

    ThisDrawing.Application.ZoomAll
    
    MsgBox "The diameter of the new Circle is: " & circleObj.Diameter
End Sub

Sub Example_Alignment()
   ' This example creates a text object in model space and
   ' demonstrates setting the alignment of the new text string
    
    Dim textObj As AcadText
    Dim textString As String
    Dim insertionPoint(0 To 2) As Double, alignmentPoint(0 To 2) As Double
    Dim height As Double
    Dim oldPDMODE As Integer
    Dim pointObj As AcadPoint
    
    ' Define the new Text object
    textString = "Hello, World."
    insertionPoint(0) = 3: insertionPoint(1) = 3: insertionPoint(2) = 0
    alignmentPoint(0) = 3: alignmentPoint(1) = 3: alignmentPoint(2) = 0
    height = 0.5
    
    ' Create the Text object in model space
    Set textObj = ThisDrawing.ModelSpace.AddText(textString, insertionPoint, height)
    
    oldPDMODE = ThisDrawing.GetVariable("PDMODE")   ' Record existing point style
    
    ' Create a crosshair over the text alignment point,
    ' so we can better visualize the alignment process
    Set pointObj = ThisDrawing.ModelSpace.AddPoint(alignmentPoint)
    pointObj.Color = acRed
    
    ThisDrawing.SetVariable "PDMODE", 2             ' Set point style to crosshair
        
    ThisDrawing.Application.ZoomAll
    
    ' Set the text alignment to a value other than acAlignmentLeft which is the default.
    ' This allows us to create a point which will act as an alignment reference point
    textObj.Alignment = acAlignmentRight
    
    ' Create the text alignment reference point and the text will automatically
    ' align to the right of this point, since we have already set the text
    ' alignment to acAlignmentRight
    textObj.TextAlignmentPoint = alignmentPoint
    ThisDrawing.Regen acActiveViewport
    MsgBox "The Text object is now aligned to the right of the alignment point"
    
    ' Center the text to the alignment point
    textObj.Alignment = acAlignmentCenter
    ThisDrawing.Regen acActiveViewport
    MsgBox "The Text object is now centered to the alignment point"
    
    ' Reset point style
    ThisDrawing.SetVariable "PDMODE", oldPDMODE
End Sub

Sub Example_UpsideDown()
   ' This example creates a text object in model space and
   ' uses the UpsideDown property to flip the text vertically
   
    Dim textObj As AcadText
    Dim textString As String
    Dim insertionPoint(0 To 2) As Double
    Dim height As Double
    
    ' Define the new Text object
    textString = "Hello, World."
    insertionPoint(0) = 3: insertionPoint(1) = 3: insertionPoint(2) = 0
    height = 0.5
    
    ' Create the Text object in model space
    Set textObj = ThisDrawing.ModelSpace.AddText(textString, insertionPoint, height)
    
    ThisDrawing.Application.ZoomAll
    
    MsgBox "The Text oject is now right side up"
    
    textObj.UpsideDown = True
    ThisDrawing.Regen acActiveViewport
    
    MsgBox "The Text object is now upside down"
End Sub

Sub Example_Angle()
   ' This example adds a line in model space and returns the angle of the new line
   
    Dim lineObj As AcadLine
    Dim startPoint(0 To 2) As Double, endPoint(0 To 2)  As Double
    
    ' Define the start and end points for the line
    startPoint(0) = 1: startPoint(1) = 1: startPoint(2) = 0
    endPoint(0) = 5: endPoint(1) = 5: endPoint(2) = 0
    
    ' Create the line in model space
    Set lineObj = ThisDrawing.ModelSpace.AddLine(startPoint, endPoint)

    ThisDrawing.Application.ZoomAll
    
    MsgBox "The angle of the new Line is: " & lineObj.angle
End Sub

Sub Example_Delta()
   ' This example adds a line in model space and returns the delta of the new line

    Dim lineObj As AcadLine
    Dim lineDelta As Variant
    Dim startPoint(0 To 2) As Double, endPoint(0 To 2) As Double
    
    ' Define the start and end points for the line
    startPoint(0) = 1: startPoint(1) = 1: startPoint(2) = 0
    endPoint(0) = 5: endPoint(1) = 5: endPoint(2) = 0
    
    ' Create the line in model space
    Set lineObj = ThisDrawing.ModelSpace.AddLine(startPoint, endPoint)

    ThisDrawing.Application.ZoomAll
    
    ' Display the delta of the new line
    lineDelta = lineObj.Delta
    MsgBox "The delta of the new Line is: " & vbCrLf & _
                                            "DeltaX:" & lineDelta(0) & vbCrLf & _
                                            "DeltaY:" & lineDelta(1) & vbCrLf & _
                                            "DeltaZ:" & lineDelta(2)
End Sub

Sub Example_Length()
   ' This example adds a line in model space and returns the length of the new line

    Dim lineObj As AcadLine
    Dim startPoint(0 To 2) As Double, endPoint(0 To 2)  As Double
    
    ' Define the start and end points for the line
    startPoint(0) = 1: startPoint(1) = 1: startPoint(2) = 0
    endPoint(0) = 5: endPoint(1) = 5: endPoint(2) = 0

    ' Create the line in model space
    Set lineObj = ThisDrawing.ModelSpace.AddLine(startPoint, endPoint)

    ThisDrawing.Application.ZoomAll
    
    MsgBox "The length of the new Line is: " & lineObj.length
End Sub

Sub Example_IsPeriodic()
   ' This example creates a Spline object in model space and
   ' determines if the Spline is periodic

    Dim splineObj As AcadSpline
    Dim startTan(0 To 2) As Double, endTan(0 To 2) As Double
    Dim fitPoints(0 To 8) As Double
    Dim UserMessage As String
    
    ' Define the Spline object
    startTan(0) = 0.5: startTan(1) = 0.5: startTan(2) = 0
    endTan(0) = 0.5: endTan(1) = 0.5: endTan(2) = 0
    fitPoints(0) = 0: fitPoints(1) = 0: fitPoints(2) = 0: fitPoints(3) = 5
    fitPoints(4) = 5: fitPoints(5) = 0: fitPoints(6) = 10: fitPoints(7) = 0: fitPoints(8) = 0
    
    ' Create new Spline object
    Set splineObj = ThisDrawing.ModelSpace.AddSpline(fitPoints, startTan, endTan)
    ThisDrawing.Application.ZoomAll
    
    ' Display whether or not new Spline is periodic
    UserMessage = IIf(splineObj.IsPeriodic, "is periodic", "is not periodic")
    
    MsgBox "The new Spline " & UserMessage
    
End Sub

Sub Example_IsPlanar()
   ' This example creates a Spline object in model space and
   ' determines if the Spline is planar

    Dim splineObj As AcadSpline
    Dim startTan(0 To 2) As Double, endTan(0 To 2) As Double
    Dim fitPoints(0 To 8) As Double
    Dim UserMessage As String

    ' Define the Spline object
    startTan(0) = 0.5: startTan(1) = 0.5: startTan(2) = 0
    endTan(0) = 0.5: endTan(1) = 0.5: endTan(2) = 0
    fitPoints(0) = 0: fitPoints(1) = 0: fitPoints(2) = 0: fitPoints(3) = 5
    fitPoints(4) = 5: fitPoints(5) = 0: fitPoints(6) = 10: fitPoints(7) = 0: fitPoints(8) = 0
    
    ' Create new Spline object
    Set splineObj = ThisDrawing.ModelSpace.AddSpline(fitPoints, startTan, endTan)
    ThisDrawing.Application.ZoomAll
    
    ' Display whether or not new Spline is periodic
    UserMessage = IIf(splineObj.IsPlanar, "is planar", "is not planar")
    
    MsgBox "The new Spline " & UserMessage

End Sub


Sub Example_Weights()
   ' This example creates a Spline object in model space and
   ' returns the weight vector for the new Spline

    Dim splineObj As AcadSpline
    Dim startTan(0 To 2) As Double, endTan(0 To 2) As Double
    Dim fitPoints(0 To 8) As Double
    Dim weightVector As Variant

    ' Define the Spline object
    startTan(0) = 0.5: startTan(1) = 0.5: startTan(2) = 0
    endTan(0) = 0.5: endTan(1) = 0.5: endTan(2) = 0
    fitPoints(0) = 0: fitPoints(1) = 0: fitPoints(2) = 0
    fitPoints(3) = 5:    fitPoints(4) = 5: fitPoints(5) = 0
    fitPoints(6) = 10: fitPoints(7) = 0: fitPoints(8) = 0
    
    ' Create new Spline object
    Set splineObj = ThisDrawing.ModelSpace.AddSpline(fitPoints, startTan, endTan)
        
    ' Add weights to the Spline
    splineObj.SetWeight 0, 1.5
    splineObj.SetWeight 1, 2
    splineObj.SetWeight 2, 4.5
    
    ThisDrawing.Application.ZoomAll
    
    ' Display the weight vector of the new Spline
    weightVector = splineObj.Weights
    MsgBox "The weight vector of the new Spline is: " & vbCrLf & _
                                            weightVector(0) & vbCrLf & _
                                            weightVector(1) & vbCrLf & _
                                            weightVector(2)
End Sub

Sub Example_SecondPoint()
    ' This example creates a ray object. It then finds the
    ' second point of the ray, changes the second point, and
    ' queries the new second point.
    
    Dim basePoint(0 To 2) As Double
    Dim directionVec(0 To 2) As Double
    Dim rayObj As AcadRay
    Dim currSecondPoint As Variant
    Dim msg As String
    Dim newSecondPoint(0 To 2) As Double
    
    ' Establish the base point and directional vector for the ray
    basePoint(0) = 3: basePoint(1) = 3: basePoint(2) = 0
    directionVec(0) = 1:    directionVec(1) = 1: directionVec(2) = 0
    
    ' Create a Ray object in model space
    Set rayObj = ThisDrawing.ModelSpace.AddRay(basePoint, directionVec)
    
    ThisDrawing.Regen True
    MsgBox "A new Ray has been added.", vbInformation
    
    ' Define a new second point
    newSecondPoint(0) = 4: newSecondPoint(1) = 2: newSecondPoint(2) = 0
    
    ' Update the ray using the new second point
    rayObj.SecondPoint = newSecondPoint
            
    ' Query the new second point for the Ray
    currSecondPoint = rayObj.SecondPoint
    msg = currSecondPoint(0) & vbCrLf & _
          currSecondPoint(1) & vbCrLf & _
          currSecondPoint(2)
    
    ThisDrawing.Regen True
    MsgBox "We've just changed the second point of the new Ray to: " & vbCrLf & msg, vbInformation

End Sub

Sub Example_NumberOfFaces()
    ' This example creates a PolyFaceMesh and displays the number of faces it contains
    
    Dim vertexList(0 To 17) As Double
    Dim FaceList(0 To 7) As Integer
    Dim NewPolyFaceMeshObj As AcadPolyfaceMesh
    Dim direction(0 To 2) As Double
    
    'Data for new PolyFaceMesh object
    vertexList(0) = 4: vertexList(1) = 7: vertexList(2) = 0
    vertexList(3) = 5: vertexList(4) = 7: vertexList(5) = 0
    vertexList(6) = 6: vertexList(7) = 7: vertexList(8) = 0
    vertexList(9) = 4: vertexList(10) = 6: vertexList(11) = 0
    vertexList(12) = 5: vertexList(13) = 6: vertexList(14) = 0
    vertexList(15) = 6: vertexList(16) = 6: vertexList(17) = 6
    
    FaceList(0) = 1:    FaceList(1) = 2:    FaceList(2) = 5
    FaceList(3) = 4:    FaceList(4) = 2:    FaceList(5) = 3
    FaceList(6) = 6:    FaceList(7) = 5

    ' Create new PolyFaceMesh object
    Set NewPolyFaceMeshObj = ModelSpace.AddPolyfaceMesh(vertexList, FaceList)
    NewPolyFaceMeshObj.Update

    ' Change the viewing direction of the viewport to
    ' better see the polyface mesh
    direction(0) = -1: direction(1) = -1: direction(2) = 1
    ThisDrawing.ActiveViewport.direction = direction
    ThisDrawing.ActiveViewport = ThisDrawing.ActiveViewport
    ThisDrawing.Application.ZoomAll
    
    ' Display number of faces in this PolyFaceMesh
    MsgBox "The new PolyFaceMesh contains " & NewPolyFaceMeshObj.NumberOfFaces & " faces."
End Sub

Sub Example_NumberOfVertices()
    ' This example creates a PolyFaceMesh and displays the number of vertices it contains
    
    Dim vertexList(0 To 17) As Double
    Dim FaceList(0 To 7) As Integer
    Dim NewPolyFaceMeshObj As AcadPolyfaceMesh
    Dim direction(0 To 2) As Double
    
    'Data for new PolyFaceMesh object
    vertexList(0) = 4: vertexList(1) = 7: vertexList(2) = 0
    vertexList(3) = 5: vertexList(4) = 7: vertexList(5) = 0
    vertexList(6) = 6: vertexList(7) = 7: vertexList(8) = 0
    vertexList(9) = 4: vertexList(10) = 6: vertexList(11) = 0
    vertexList(12) = 5: vertexList(13) = 6: vertexList(14) = 0
    vertexList(15) = 6: vertexList(16) = 6: vertexList(17) = 6
    
    FaceList(0) = 1:    FaceList(1) = 2:    FaceList(2) = 5
    FaceList(3) = 4:    FaceList(4) = 2:    FaceList(5) = 3
    FaceList(6) = 6:    FaceList(7) = 5

    ' Create new PolyFaceMesh object
    Set NewPolyFaceMeshObj = ModelSpace.AddPolyfaceMesh(vertexList, FaceList)
    NewPolyFaceMeshObj.Update

    ' Change the viewing direction of the viewport to
    ' better see the polyface mesh
    direction(0) = -1: direction(1) = -1: direction(2) = 1
    ThisDrawing.ActiveViewport.direction = direction
    ThisDrawing.ActiveViewport = ThisDrawing.ActiveViewport
    ThisDrawing.Application.ZoomAll
    
    ' Display number of vertices in this PolyFaceMesh
    MsgBox "The new PolyFaceMesh contains " & NewPolyFaceMeshObj.NumberOfVertices & " vertices."
End Sub

Sub Example_AddMLine()
   ' This example adds an Mline in model space

    Dim mLineObj As AcadMLine
    Dim vertexList(0 To 17) As Double
   
    ' Define data for new object
    vertexList(0) = 4: vertexList(1) = 7: vertexList(2) = 0
    vertexList(3) = 5: vertexList(4) = 7: vertexList(5) = 0
    vertexList(6) = 6: vertexList(7) = 7: vertexList(8) = 0
    vertexList(9) = 4: vertexList(10) = 6: vertexList(11) = 0
    vertexList(12) = 5: vertexList(13) = 6: vertexList(14) = 0
    vertexList(15) = 6: vertexList(16) = 6: vertexList(17) = 6

    ' Create the line in model space
    Set mLineObj = ThisDrawing.ModelSpace.AddMLine(vertexList)

    ThisDrawing.Application.ZoomAll
    
    MsgBox "A new MLine has been added to the drawing."
End Sub

Sub Example_MajorRadius()
  ' This example creates an Ellipse in model space and displays
  ' both the Major radius and the Minor radius of the new Ellipse
  
    Dim ellObj As AcadEllipse
    Dim majAxis(0 To 2) As Double, center(0 To 2) As Double
    Dim radRatio As Double
    
    ' Create an ellipse in model space
    center(0) = 5: center(1) = 5: center(2) = 0
    majAxis(0) = 10: majAxis(1) = 20: majAxis(2) = 0
    radRatio = 0.3
    Set ellObj = ThisDrawing.ModelSpace.AddEllipse(center, majAxis, radRatio)

    ThisDrawing.Application.ZoomAll
    
    ' Display radius information
    MsgBox "The major radius of the new Ellipse is: " & ellObj.majorRadius & vbCrLf & _
           "The minor radius of the new Ellipse is: " & ellObj.minorRadius
End Sub

Sub Example_MinorRadius()
  ' This example creates an Ellipse in model space and displays
  ' both the Major radius and the Minor radius of the new Ellipse
  
    Dim ellObj As AcadEllipse
    Dim majAxis(0 To 2) As Double, center(0 To 2) As Double
    Dim radRatio As Double
    
    ' Create an ellipse in model space
    center(0) = 5: center(1) = 5: center(2) = 0
    majAxis(0) = 10: majAxis(1) = 20: majAxis(2) = 0
    radRatio = 0.3
    Set ellObj = ThisDrawing.ModelSpace.AddEllipse(center, majAxis, radRatio)

    ThisDrawing.Application.ZoomAll
    
    ' Display radius information
    MsgBox "The major radius of the new Ellipse is: " & ellObj.majorRadius & vbCrLf & _
           "The minor radius of the new Ellipse is: " & ellObj.minorRadius
End Sub

Sub Example_VisibilityEdge1()
    ' This example creates a 3D Face in model space and allows the user to
    ' control the visibility of the edges
    
    Dim faceObj As Acad3DFace
    Dim point1(0 To 2) As Double, point2(0 To 2) As Double, _
        point3(0 To 2) As Double, point4(0 To 2) As Double
    Dim Edge1Msg As String, Edge2Msg As String, _
        Edge3Msg As String, Edge4Msg As String
    
    ' Define the four coordinates of the face
    point1(0) = 0: point1(1) = 0: point1(2) = 0
    point2(0) = 5: point2(1) = 0: point2(2) = 1
    point3(0) = 1: point3(1) = 10: point3(2) = 0
    point4(0) = 5: point4(1) = 5: point4(2) = 1
    
    ' Create the 3DFace object in model space
    Set faceObj = ThisDrawing.ModelSpace.Add3DFace(point1, point2, point3, point4)
    ThisDrawing.Application.ZoomAll
    
    ' Display information about the visibility of the edges for this object
DisplayEdgeInformation:
    Edge1Msg = IIf(faceObj.VisibilityEdge1, "Edge1 of the new 3DFace is visible", "Edge1 of the new 3DFace is not visible")
    Edge2Msg = IIf(faceObj.VisibilityEdge2, "Edge2 of the new 3DFace is visible", "Edge2 of the new 3DFace is not visible")
    Edge3Msg = IIf(faceObj.VisibilityEdge3, "Edge3 of the new 3DFace is visible", "Edge3 of the new 3DFace is not visible")
    Edge4Msg = IIf(faceObj.VisibilityEdge4, "Edge4 of the new 3DFace is visible", "Edge4 of the new 3DFace is not visible")
    
    MsgBox Edge1Msg & vbCrLf & _
           Edge2Msg & vbCrLf & _
           Edge3Msg & vbCrLf & _
           Edge4Msg
            
    ' Allow user to toggle the visibility of one of the edges
    Select Case InputBox("Which edge of the 3DFace would you like to toggle the visibility of?", "Toggle Edge Visibility", 1)
        Case "1": faceObj.VisibilityEdge1 = Not (faceObj.VisibilityEdge1)
        Case "2": faceObj.VisibilityEdge2 = Not (faceObj.VisibilityEdge2)
        Case "3": faceObj.VisibilityEdge3 = Not (faceObj.VisibilityEdge3)
        Case "4": faceObj.VisibilityEdge4 = Not (faceObj.VisibilityEdge4)
        Case "":  Exit Sub
        Case Else: MsgBox "You must enter the number of an edge (1-4)", vbInformation
    End Select
            
    ' Refresh view
    ThisDrawing.Regen acAllViewports
    
    ' Return to display information about the edges
    GoTo DisplayEdgeInformation
End Sub

Sub Example_VisibilityEdge2()
    ' This example creates a 3D Face in model space and allows the user to
    ' control the visibility of the edges
    
    Dim faceObj As Acad3DFace
    Dim point1(0 To 2) As Double, point2(0 To 2) As Double, _
        point3(0 To 2) As Double, point4(0 To 2) As Double
    Dim Edge1Msg As String, Edge2Msg As String, _
        Edge3Msg As String, Edge4Msg As String
    
    ' Define the four coordinates of the face
    point1(0) = 0: point1(1) = 0: point1(2) = 0
    point2(0) = 5: point2(1) = 0: point2(2) = 1
    point3(0) = 1: point3(1) = 10: point3(2) = 0
    point4(0) = 5: point4(1) = 5: point4(2) = 1
    
    ' Create the 3DFace object in model space
    Set faceObj = ThisDrawing.ModelSpace.Add3DFace(point1, point2, point3, point4)
    ThisDrawing.Application.ZoomAll
    
    ' Display information about the visibility of the edges for this object
DisplayEdgeInformation:
    Edge1Msg = IIf(faceObj.VisibilityEdge1, "Edge1 of the new 3DFace is visible", "Edge1 of the new 3DFace is not visible")
    Edge2Msg = IIf(faceObj.VisibilityEdge2, "Edge2 of the new 3DFace is visible", "Edge2 of the new 3DFace is not visible")
    Edge3Msg = IIf(faceObj.VisibilityEdge3, "Edge3 of the new 3DFace is visible", "Edge3 of the new 3DFace is not visible")
    Edge4Msg = IIf(faceObj.VisibilityEdge4, "Edge4 of the new 3DFace is visible", "Edge4 of the new 3DFace is not visible")
    
    MsgBox Edge1Msg & vbCrLf & _
           Edge2Msg & vbCrLf & _
           Edge3Msg & vbCrLf & _
           Edge4Msg
            
    ' Allow user to toggle the visibility of one of the edges
    Select Case InputBox("Which edge of the 3DFace would you like to toggle the visibility of?", "Toggle Edge Visibility", 1)
        Case "1": faceObj.VisibilityEdge1 = Not (faceObj.VisibilityEdge1)
        Case "2": faceObj.VisibilityEdge2 = Not (faceObj.VisibilityEdge2)
        Case "3": faceObj.VisibilityEdge3 = Not (faceObj.VisibilityEdge3)
        Case "4": faceObj.VisibilityEdge4 = Not (faceObj.VisibilityEdge4)
        Case "":  Exit Sub
        Case Else: MsgBox "You must enter the number of an edge (1-4)", vbInformation
    End Select
            
    ' Refresh view
    ThisDrawing.Regen acAllViewports
    
    ' Return to display information about the edges
    GoTo DisplayEdgeInformation

End Sub

Sub Example_VisibilityEdge3()
    ' This example creates a 3D Face in model space and allows the user to
    ' control the visibility of the edges
    
    Dim faceObj As Acad3DFace
    Dim point1(0 To 2) As Double, point2(0 To 2) As Double, _
        point3(0 To 2) As Double, point4(0 To 2) As Double
    Dim Edge1Msg As String, Edge2Msg As String, _
        Edge3Msg As String, Edge4Msg As String
    
    ' Define the four coordinates of the face
    point1(0) = 0: point1(1) = 0: point1(2) = 0
    point2(0) = 5: point2(1) = 0: point2(2) = 1
    point3(0) = 1: point3(1) = 10: point3(2) = 0
    point4(0) = 5: point4(1) = 5: point4(2) = 1
    
    ' Create the 3DFace object in model space
    Set faceObj = ThisDrawing.ModelSpace.Add3DFace(point1, point2, point3, point4)
    ThisDrawing.Application.ZoomAll
    
    ' Display information about the visibility of the edges for this object
DisplayEdgeInformation:
    Edge1Msg = IIf(faceObj.VisibilityEdge1, "Edge1 of the new 3DFace is visible", "Edge1 of the new 3DFace is not visible")
    Edge2Msg = IIf(faceObj.VisibilityEdge2, "Edge2 of the new 3DFace is visible", "Edge2 of the new 3DFace is not visible")
    Edge3Msg = IIf(faceObj.VisibilityEdge3, "Edge3 of the new 3DFace is visible", "Edge3 of the new 3DFace is not visible")
    Edge4Msg = IIf(faceObj.VisibilityEdge4, "Edge4 of the new 3DFace is visible", "Edge4 of the new 3DFace is not visible")
    
    MsgBox Edge1Msg & vbCrLf & _
           Edge2Msg & vbCrLf & _
           Edge3Msg & vbCrLf & _
           Edge4Msg
            
    ' Allow user to toggle the visibility of one of the edges
    Select Case InputBox("Which edge of the 3DFace would you like to toggle the visibility of?", "Toggle Edge Visibility", 1)
        Case "1": faceObj.VisibilityEdge1 = Not (faceObj.VisibilityEdge1)
        Case "2": faceObj.VisibilityEdge2 = Not (faceObj.VisibilityEdge2)
        Case "3": faceObj.VisibilityEdge3 = Not (faceObj.VisibilityEdge3)
        Case "4": faceObj.VisibilityEdge4 = Not (faceObj.VisibilityEdge4)
        Case "":  Exit Sub
        Case Else: MsgBox "You must enter the number of an edge (1-4)", vbInformation
    End Select
            
    ' Refresh view
    ThisDrawing.Regen acAllViewports
    
    ' Return to display information about the edges
    GoTo DisplayEdgeInformation

End Sub

Sub Example_VisibilityEdge4()
    ' This example creates a 3D Face in model space and allows the user to
    ' control the visibility of the edges
    
    Dim faceObj As Acad3DFace
    Dim point1(0 To 2) As Double, point2(0 To 2) As Double, _
        point3(0 To 2) As Double, point4(0 To 2) As Double
    Dim Edge1Msg As String, Edge2Msg As String, _
        Edge3Msg As String, Edge4Msg As String
    
    ' Define the four coordinates of the face
    point1(0) = 0: point1(1) = 0: point1(2) = 0
    point2(0) = 5: point2(1) = 0: point2(2) = 1
    point3(0) = 1: point3(1) = 10: point3(2) = 0
    point4(0) = 5: point4(1) = 5: point4(2) = 1
    
    ' Create the 3DFace object in model space
    Set faceObj = ThisDrawing.ModelSpace.Add3DFace(point1, point2, point3, point4)
    ThisDrawing.Application.ZoomAll
    
    ' Display information about the visibility of the edges for this object
DisplayEdgeInformation:
    Edge1Msg = IIf(faceObj.VisibilityEdge1, "Edge1 of the new 3DFace is visible", "Edge1 of the new 3DFace is not visible")
    Edge2Msg = IIf(faceObj.VisibilityEdge2, "Edge2 of the new 3DFace is visible", "Edge2 of the new 3DFace is not visible")
    Edge3Msg = IIf(faceObj.VisibilityEdge3, "Edge3 of the new 3DFace is visible", "Edge3 of the new 3DFace is not visible")
    Edge4Msg = IIf(faceObj.VisibilityEdge4, "Edge4 of the new 3DFace is visible", "Edge4 of the new 3DFace is not visible")
    
    MsgBox Edge1Msg & vbCrLf & _
           Edge2Msg & vbCrLf & _
           Edge3Msg & vbCrLf & _
           Edge4Msg
            
    ' Allow user to toggle the visibility of one of the edges
    Select Case InputBox("Which edge of the 3DFace would you like to toggle the visibility of?", "Toggle Edge Visibility", 1)
        Case "1": faceObj.VisibilityEdge1 = Not (faceObj.VisibilityEdge1)
        Case "2": faceObj.VisibilityEdge2 = Not (faceObj.VisibilityEdge2)
        Case "3": faceObj.VisibilityEdge3 = Not (faceObj.VisibilityEdge3)
        Case "4": faceObj.VisibilityEdge4 = Not (faceObj.VisibilityEdge4)
        Case "":  Exit Sub
        Case Else: MsgBox "You must enter the number of an edge (1-4)", vbInformation
    End Select
            
    ' Refresh view
    ThisDrawing.Regen acAllViewports
    
    ' Return to display information about the edges
    GoTo DisplayEdgeInformation

End Sub

Sub Example_AddMInsertBlock()
    ' This example creates a new Block in the current drawing, adds a
    ' Circle object to the new block, and uses the newly created block
    ' to create a rectangular array of block references using AddMInsertBlock
    
    Dim circleObj As AcadCircle
    Dim centerPoint(0 To 2) As Double, InsertPoint(0 To 2) As Double
    Dim radius As Double
    Dim newMBlock As AcadMInsertBlock
    Dim newBlock As AcadBlock
    
    ' Define the Circle object that will be inserted into the block
    centerPoint(0) = 0: centerPoint(1) = 0: centerPoint(2) = 0
    InsertPoint(0) = 1: InsertPoint(1) = 1: InsertPoint(2) = 0
    radius = 0.5
    
    ' Create a new block to hold the Circle object
    Set newBlock = ThisDrawing.Blocks.Add(centerPoint, "CBlock")
    
    ' Add the Circle object to the new block object
    Set circleObj = ThisDrawing.Blocks("CBlock").AddCircle(centerPoint, radius)
    
    ' Create a rectangular array of Circles using the new block containing the Circle
    ' and the AddMInsertBlock method
    Set newMBlock = ThisDrawing.ModelSpace.AddMInsertBlock(InsertPoint, "CBlock", 1, 1, 1, 1, 2, 2, 1, 1)
        
    ThisDrawing.Application.ZoomAll
    
    MsgBox "A rectangular array has been created from the original block."

End Sub

Sub Example_Columns()
    ' This example creates a new MInsertBlock in the current drawing and
    ' displays the column and row information for the new MInsertBlock
    
    Dim circleObj As AcadCircle
    Dim centerPoint(0 To 2) As Double, InsertPoint(0 To 2) As Double
    Dim radius As Double
    Dim newMBlock As AcadMInsertBlock
    Dim newBlock As AcadBlock
        
    ' Define the Circle object
    centerPoint(0) = 0: centerPoint(1) = 0: centerPoint(2) = 0
    InsertPoint(0) = 1: InsertPoint(1) = 1: InsertPoint(2) = 0
    radius = 0.5
    
    ' Create a new block to hold the Circle
    Set newBlock = ThisDrawing.Blocks.Add(centerPoint, "CBlock")
    
    ' Add the Circle object to the new block
    Set circleObj = ThisDrawing.Blocks("CBlock").AddCircle(centerPoint, radius)
    
    ' Create a rectangular array of Circles using the new block containing the Circle
    ' and the AddMInsertBlock method
    Set newMBlock = ThisDrawing.ModelSpace.AddMInsertBlock(InsertPoint, "CBlock", 1, 1, 1, 1, 2, 2, 1, 1)
        
    ThisDrawing.Application.ZoomAll
    
    ' Display information about the Columns and Rows defined by the MInsertBlock
    MsgBox "The new rectangular array is comprised of: " & vbCrLf & _
            newMBlock.Columns & " columns with a spacing of " & newMBlock.ColumnSpacing & " and" & vbCrLf & _
            newMBlock.Rows & " rows with a spacing of " & newMBlock.RowSpacing

End Sub

Sub Example_ColumnSpacing()
    ' This example creates a new MInsertBlock in the current drawing and
    ' displays the column and row information for the new MInsertBlock
    
    Dim circleObj As AcadCircle
    Dim centerPoint(0 To 2) As Double, InsertPoint(0 To 2) As Double
    Dim radius As Double
    Dim newMBlock As AcadMInsertBlock
    Dim newBlock As AcadBlock
    
    ' Define the Circle object
    centerPoint(0) = 0: centerPoint(1) = 0: centerPoint(2) = 0
    InsertPoint(0) = 1: InsertPoint(1) = 1: InsertPoint(2) = 0
    radius = 0.5
    
    ' Create a new block to hold the Circle
    Set newBlock = ThisDrawing.Blocks.Add(centerPoint, "CBlock")
    
    ' Add the Circle object to the new block
    Set circleObj = ThisDrawing.Blocks("CBlock").AddCircle(centerPoint, radius)
    
    ' Create a rectangular array of Circles using the new block containing the Circle
    ' and the AddMInsertBlock method
    Set newMBlock = ThisDrawing.ModelSpace.AddMInsertBlock(InsertPoint, "CBlock", 1, 1, 1, 1, 2, 2, 1, 1)
        
    ThisDrawing.Application.ZoomAll
    
    ' Display information about the Columns and Rows defined by the MInsertBlock
    MsgBox "The new rectangular array is comprised of: " & vbCrLf & _
            newMBlock.Columns & " columns with a spacing of " & newMBlock.ColumnSpacing & " and" & vbCrLf & _
            newMBlock.Rows & " rows with a spacing of " & newMBlock.RowSpacing

End Sub

Sub Example_Rows()
    ' This example creates a new MInsertBlock in the current drawing and
    ' displays the column and row information for the new MInsertBlock
    
    Dim circleObj As AcadCircle
    Dim centerPoint(0 To 2) As Double, InsertPoint(0 To 2) As Double
    Dim radius As Double
    Dim newMBlock As AcadMInsertBlock
    Dim newBlock As AcadBlock
    
    ' Define the Circle object
    centerPoint(0) = 0: centerPoint(1) = 0: centerPoint(2) = 0
    InsertPoint(0) = 1: InsertPoint(1) = 1: InsertPoint(2) = 0
    radius = 0.5
    
    ' Create a new block to hold the Circle
    Set newBlock = ThisDrawing.Blocks.Add(centerPoint, "CBlock")
    
    ' Add the Circle object to the new block
    Set circleObj = ThisDrawing.Blocks("CBlock").AddCircle(centerPoint, radius)
    
    ' Create a rectangular array of Circles using the new block containing the Circle
    ' and the AddMInsertBlock method
    Set newMBlock = ThisDrawing.ModelSpace.AddMInsertBlock(InsertPoint, "CBlock", 1, 1, 1, 1, 2, 2, 1, 1)
        
    ThisDrawing.Application.ZoomAll
    
    ' Display information about the Columns and Rows defined by the MInsertBlock
    MsgBox "The new rectangular array is comprised of: " & vbCrLf & _
            newMBlock.Columns & " columns with a spacing of " & newMBlock.ColumnSpacing & " and" & vbCrLf & _
            newMBlock.Rows & " rows with a spacing of " & newMBlock.RowSpacing

End Sub

Sub Example_RowSpacing()
    ' This example creates a new MInsertBlock in the current drawing and
    ' displays the column and row information for the new MInsertBlock
    
    Dim circleObj As AcadCircle
    Dim centerPoint(0 To 2) As Double, InsertPoint(0 To 2) As Double
    Dim radius As Double
    Dim newMBlock As AcadMInsertBlock
    Dim newBlock As AcadBlock
        
    ' Define the Circle object
    centerPoint(0) = 0: centerPoint(1) = 0: centerPoint(2) = 0
    InsertPoint(0) = 1: InsertPoint(1) = 1: InsertPoint(2) = 0
    radius = 0.5
    
    ' Create a new block to hold the Circle
    Set newBlock = ThisDrawing.Blocks.Add(centerPoint, "CBlock")
    
    ' Add the Circle object to the new block
    Set circleObj = ThisDrawing.Blocks("CBlock").AddCircle(centerPoint, radius)
    
    ' Create a rectangular array of Circles using the new block containing the Circle
    ' and the AddMInsertBlock method
    Set newMBlock = ThisDrawing.ModelSpace.AddMInsertBlock(InsertPoint, "CBlock", 1, 1, 1, 1, 2, 2, 1, 1)
        
    ThisDrawing.Application.ZoomAll
    
    ' Display information about the Columns and Rows defined by the MInsertBlock
    MsgBox "The new rectangular array is comprised of: " & vbCrLf & _
            newMBlock.Columns & " columns with a spacing of " & newMBlock.ColumnSpacing & " and" & vbCrLf & _
            newMBlock.Rows & " rows with a spacing of " & newMBlock.RowSpacing

End Sub

Sub Example_AltRoundDistance()
   ' This example creates an aligned dimension in model space and
   ' uses AltRoundDistance to set the alternate unit display
   ' of the dimension to rounded values

    Dim dimObj As AcadDimAligned
    Dim point1(0 To 2) As Double, point2(0 To 2) As Double
    Dim location(0 To 2) As Double
    
    ' Define the dimension
    point1(0) = 5: point1(1) = 5: point1(2) = 0
    point2(0) = 10.123: point2(1) = 5: point2(2) = 0
    location(0) = 5: location(1) = 7: location(2) = 0
    
    ' Create an aligned dimension object in model space
    Set dimObj = ThisDrawing.ModelSpace.AddDimAligned(point1, point2, location)
    
    ' Enable alternate unit display
    dimObj.AltUnits = True
    
    ThisDrawing.Application.ZoomAll
    
    MsgBox "Press any key to round the alternate dimension unit display to .5"
    
    ' Round the distance of the alternate dimension to 0.50 of a unit
    dimObj.AltRoundDistance = 0.5
    ThisDrawing.Regen acAllViewports
    
    MsgBox "Alternate dimension units have been rounded to: " & dimObj.AltRoundDistance
End Sub

Sub Example_AltSuppressLeadingZeros()
   ' This example creates an aligned dimension in model space and
   ' uses AltSuppressLeadingZeros to toggle the display of leading zeros
   ' in the alternate dimension display

    Dim dimObj As AcadDimAligned
    Dim point1(0 To 2) As Double, point2(0 To 2) As Double
    Dim location(0 To 2) As Double
    
    ' Define the dimension
    point1(0) = 5: point1(1) = 5: point1(2) = 0
    point2(0) = 5.01: point2(1) = 5: point2(2) = 0
    location(0) = 5: location(1) = 7: location(2) = 0
    
    ' Create an aligned dimension object in model space
    Set dimObj = ThisDrawing.ModelSpace.AddDimAligned(point1, point2, location)
    
    ' Enable alternate unit display
    dimObj.AltUnits = True
    
    ThisDrawing.Application.ZoomAll
    
Toggle:
    Select Case MsgBox("Press OK to toggle the display of leading zeros in the alternate dimension", vbOKCancel)
        Case vbOK
            ' Toggle the display of leading zeros for the alternate dimension value
            dimObj.AltSuppressLeadingZeros = Not (dimObj.AltSuppressLeadingZeros)
            ThisDrawing.Regen acAllViewports
        Case vbCancel
            Exit Sub
    End Select
    
    GoTo Toggle
End Sub

Sub Example_AltSuppressTrailingZeros()
   ' This example creates an aligned dimension in model space and
   ' uses AltSuppressTrailingZeros to toggle the display of trailing zeros
   ' in the alternate dimension display

    Dim dimObj As AcadDimAligned
    Dim point1(0 To 2) As Double, point2(0 To 2) As Double
    Dim location(0 To 2) As Double
    
    ' Define the dimension
    point1(0) = 5: point1(1) = 5: point1(2) = 0
    point2(0) = 7: point2(1) = 5: point2(2) = 0
    location(0) = 5: location(1) = 7: location(2) = 0
    
    ' Create an aligned dimension object in model space
    Set dimObj = ThisDrawing.ModelSpace.AddDimAligned(point1, point2, location)
    
    ' Enable alternate unit display
    dimObj.AltUnits = True
    
    ThisDrawing.Application.ZoomAll
    
Toggle:
    Select Case MsgBox("Press OK to toggle the display of trailing zeros in the alternate dimension", vbOKCancel)
        Case vbOK
            ' Toggle the display of trailing zeros for the alternate dimension value
            dimObj.AltSuppressTrailingZeros = Not (dimObj.AltSuppressTrailingZeros)
            ThisDrawing.Regen acAllViewports
        Case vbCancel
            Exit Sub
    End Select
    
    GoTo Toggle
End Sub

Sub Example_AltSuppressZeroInches()
   ' This example creates an aligned dimension in model space and
   ' uses AltSuppressZeroInches to suppress or view the display of
   ' zero inches in the alternate dimension display

    Dim dimObj As AcadDimAligned
    Dim point1(0 To 2) As Double, point2(0 To 2) As Double
    Dim location(0 To 2) As Double
    
    ' Define the dimension
    point1(0) = 0: point1(1) = 5: point1(2) = 0
    point2(0) = 12: point2(1) = 5: point2(2) = 0
    location(0) = 5: location(1) = 7: location(2) = 0
    
    ' Create an aligned dimension object in model space
    Set dimObj = ThisDrawing.ModelSpace.AddDimAligned(point1, point2, location)
    
    ' Enable alternate unit display
    dimObj.AltUnits = True
    
    ' Set the dimension display to a style that works with AltSuppressZeroInches
    dimObj.AltUnitsFormat = acDimLArchitectural
    dimObj.AltUnitsScale = 2    ' Set the alternate unit scale to be a multiple of 2
    
    ThisDrawing.Application.ZoomAll
    
Toggle:
    Select Case MsgBox("Press OK to suppress or view the display of zero inches in the alternate dimension", vbOKCancel)
        Case vbOK
            ' Toggle the display of zero inches for the alternate dimension value
            dimObj.AltSuppressZeroInches = Not (dimObj.AltSuppressZeroInches)
            ThisDrawing.Regen acAllViewports
        Case vbCancel
            Exit Sub
    End Select
    
    GoTo Toggle
End Sub

Sub Example_AltSuppressZeroFeet()
   ' This example creates an aligned dimension in model space and
   ' uses AltSuppressZeroFeet to suppress or view the display of
   ' zero feet in the alternate dimension display

    Dim dimObj As AcadDimAligned
    Dim point1(0 To 2) As Double, point2(0 To 2) As Double
    Dim location(0 To 2) As Double
    
    ' Define the dimension
    point1(0) = 0: point1(1) = 5: point1(2) = 0
    point2(0) = 5: point2(1) = 5: point2(2) = 0
    location(0) = 5: location(1) = 7: location(2) = 0
    
    ' Create an aligned dimension object in model space
    Set dimObj = ThisDrawing.ModelSpace.AddDimAligned(point1, point2, location)
    
    ' Enable alternate unit display
    dimObj.AltUnits = True
    
    ' Set the dimension display to a style that works with AltSuppressZeroFeet
    dimObj.AltUnitsFormat = acDimLArchitectural
    dimObj.AltUnitsScale = 2    ' Set the alternate unit scale to be a multiple of 2
    
    ThisDrawing.Application.ZoomAll
    
Toggle:
    Select Case MsgBox("Press OK to suppress or view the display of zero feet in the alternate dimension", vbOKCancel)
        Case vbOK
            ' Toggle the display of zero feet for the alternate dimension value
            dimObj.AltSuppressZeroFeet = Not (dimObj.AltSuppressZeroFeet)
            ThisDrawing.Regen acAllViewports
        Case vbCancel
            Exit Sub
    End Select
    
    GoTo Toggle
End Sub

Sub Example_AltTextPrefix()
   ' This example creates an aligned dimension in model space and
   ' uses AltTextPrefix to allow the user to change the text prefix for the
   ' alternate dimension

    Dim dimObj As AcadDimAligned
    Dim point1(0 To 2) As Double, point2(0 To 2) As Double
    Dim location(0 To 2) As Double
    Dim prefix As String
    
    ' Define the dimension
    point1(0) = 0: point1(1) = 5: point1(2) = 0
    point2(0) = 5: point2(1) = 5: point2(2) = 0
    location(0) = 5: location(1) = 7: location(2) = 0
    
    ' Create an aligned dimension object in model space
    Set dimObj = ThisDrawing.ModelSpace.AddDimAligned(point1, point2, location)
    
    ' Enable alternate unit display
    dimObj.AltUnits = True
    
    ThisDrawing.Application.ZoomAll

    ' Allow the user to change the text prefix for the alternate dimension
    prefix = InputBox("Enter a new text prefix for the alternate dimension", "Alternate Dimension Prefix", "PREFIX:")
    dimObj.AltTextPrefix = prefix   ' Commit changes to prefix
    
    ThisDrawing.Regen acAllViewports
    
    ' Read back and display the alternate dimension text prefix
    prefix = dimObj.AltTextPrefix
    If prefix <> "" Then
        MsgBox "The prefix of the alternate dimension has been changed to: " & prefix
    Else
        MsgBox "The prefix of the alternate dimension has been removed"
    End If
End Sub

Sub Example_AltTextSuffix()
   ' This example creates an aligned dimension in model space and
   ' uses AltTextSuffix to allow the user to change the text suffix for the
   ' alternate dimension

    Dim dimObj As AcadDimAligned
    Dim point1(0 To 2) As Double, point2(0 To 2) As Double
    Dim location(0 To 2) As Double
    Dim suffix As String
    
    ' Define the dimension
    point1(0) = 0: point1(1) = 5: point1(2) = 0
    point2(0) = 5: point2(1) = 5: point2(2) = 0
    location(0) = 5: location(1) = 7: location(2) = 0
    
    ' Create an aligned dimension object in model space
    Set dimObj = ThisDrawing.ModelSpace.AddDimAligned(point1, point2, location)
    
    ' Enable alternate unit display
    dimObj.AltUnits = True
    
    ThisDrawing.Application.ZoomAll

    ' Allow the user to change the text suffix for the alternate dimension
    suffix = InputBox("Enter a new text suffix for the alternate dimension", "Alternate Dimension Suffix", ":SUFFIX")
    dimObj.AltTextSuffix = suffix   ' Commit changes to suffix
    
    ThisDrawing.Regen acAllViewports
    
    ' Read back and display the alternate dimension text suffix
    suffix = dimObj.AltTextSuffix
    If suffix <> "" Then
        MsgBox "The suffix of the alternate dimension has been changed to: " & suffix
    Else
        MsgBox "The suffix of the alternate dimension has been removed"
    End If
End Sub

Sub Example_AltTolerancePrecision()
   ' This example creates an aligned dimension in model space and
   ' uses AltTolerancePrecision to allow the user to change the
   ' precision of the alternate dimension tolerance

    Dim dimObj As AcadDimAligned
    Dim point1(0 To 2) As Double, point2(0 To 2) As Double
    Dim location(0 To 2) As Double
    Dim oldTolerance As String, newTolerance As String
    
    ' Define the dimension
    point1(0) = 0: point1(1) = 5: point1(2) = 0
    point2(0) = 5.12345678: point2(1) = 5: point2(2) = 0
    location(0) = 5: location(1) = 7: location(2) = 0
    
    ' Create an aligned dimension object in model space
    Set dimObj = ThisDrawing.ModelSpace.AddDimAligned(point1, point2, location)
    
    ' Enable alternate unit display
    dimObj.AltUnits = True
    dimObj.ToleranceDisplay = acTolLimits
    
    ThisDrawing.Application.ZoomAll

    ' Store old tolerance value as default for input box
    oldTolerance = dimObj.AltTolerancePrecision
    
    ' Allow the user to change the precision for the alternate dimension tolerance
    newTolerance = InputBox("Enter a new tolerance precision for the alternate dimension.  The value must range from 0 to 8.", "Alternate Dimension Tolerance Precision", oldTolerance)
    
    Select Case newTolerance
        Case 0: newTolerance = acDimPrecisionZero
        Case 1: newTolerance = acDimPrecisionOne
        Case 2: newTolerance = acDimPrecisionTwo
        Case 3: newTolerance = acDimPrecisionThree
        Case 4: newTolerance = acDimPrecisionFour
        Case 5: newTolerance = acDimPrecisionFive
        Case 6: newTolerance = acDimPrecisionSix
        Case 7: newTolerance = acDimPrecisionSeven
        Case 8: newTolerance = acDimPrecisionEight
        Case Else
            MsgBox "The alternate tolerance precision has not been changed."
            Exit Sub
    End Select
    
    dimObj.AltTolerancePrecision = newTolerance   ' Commit changes to tolerance precision
    
    ThisDrawing.Regen acAllViewports
    
    ' Read back and display the alternate dimension tolerance precision
    newTolerance = dimObj.AltTolerancePrecision
    MsgBox "The tolerance precision has been set to " & newTolerance & " decimal places"
End Sub

Sub Example_AltUnitsFormat()
   ' This example creates an aligned dimension in model space and
   ' uses AltUnitsFormat to cycle through some common unit formats
   ' for the alternate dimension

    Dim dimObj As AcadDimAligned
    Dim point1(0 To 2) As Double, point2(0 To 2) As Double
    Dim location(0 To 2) As Double
    
    ' Define the dimension
    point1(0) = 0: point1(1) = 5: point1(2) = 0
    point2(0) = 5.12345678: point2(1) = 5: point2(2) = 0
    location(0) = 5: location(1) = 7: location(2) = 0
    
    ' Create an aligned dimension object in model space
    Set dimObj = ThisDrawing.ModelSpace.AddDimAligned(point1, point2, location)
    ThisDrawing.Application.ZoomAll
    
    ' Enable alternate unit display
    dimObj.AltUnits = True
      
    dimObj.AltUnitsFormat = acDimScientific     ' Change format to Scientific
    ThisDrawing.Regen acAllViewports
    MsgBox "The alternate dimension units are now set to Scientific"
    
    dimObj.AltUnitsFormat = acDimDecimal        ' Change format to Decimal
    ThisDrawing.Regen acAllViewports
    MsgBox "The alternate dimension units are now set to Decimal"
    
    dimObj.AltUnitsFormat = acDimArchitectural  ' Change format to Architectural
    ThisDrawing.Regen acAllViewports
    MsgBox "The alternate dimension units are now set to Architectural"
    
    dimObj.AltUnitsFormat = acDimWindowsDesktop ' Change format to WindowsDesktop
    ThisDrawing.Regen acAllViewports
    MsgBox "The alternate dimension units are now set to Windows Desktop"
    
End Sub

Sub Example_AltUnits()
   ' This example creates an aligned dimension in model space and
   ' uses AltUnits to toggle the alternate dimension units on and off

    Dim dimObj As AcadDimAligned
    Dim point1(0 To 2) As Double, point2(0 To 2) As Double
    Dim location(0 To 2) As Double
    
    ' Define the dimension
    point1(0) = 0: point1(1) = 5: point1(2) = 0
    point2(0) = 5: point2(1) = 5: point2(2) = 0
    location(0) = 5: location(1) = 7: location(2) = 0
    
    ' Create an aligned dimension object in model space
    Set dimObj = ThisDrawing.ModelSpace.AddDimAligned(point1, point2, location)
    ThisDrawing.Application.ZoomAll
    
    ' Toggle alternate unit display
Toggle:
    Select Case MsgBox("Press OK to toggle the display of alternate dimensions", vbOKCancel)
        Case vbOK
            ' Toggle the alternate dimension display
            dimObj.AltUnits = Not (dimObj.AltUnits)
            ThisDrawing.Regen acAllViewports
        Case vbCancel
            Exit Sub
    End Select
    
    ' Display status of alternate units display
    If dimObj.AltUnits Then
        MsgBox "Alternate units display is on."
    Else
        MsgBox "Alternate units display is off."
    End If
    
    GoTo Toggle
    
End Sub

Sub Example_AltUnitsPrecision()
   ' This example creates an aligned dimension in model space and
   ' uses AltUnitsPrecision to allow the user to change the
   ' precision of the alternate dimension

    Dim dimObj As AcadDimAligned
    Dim point1(0 To 2) As Double, point2(0 To 2) As Double
    Dim location(0 To 2) As Double
    Dim oldPrecision As String, newPrecision As String
    
    ' Define the dimension
    point1(0) = 0: point1(1) = 5: point1(2) = 0
    point2(0) = 5.12345678: point2(1) = 5: point2(2) = 0
    location(0) = 5: location(1) = 7: location(2) = 0
    
    ' Create an aligned dimension object in model space
    Set dimObj = ThisDrawing.ModelSpace.AddDimAligned(point1, point2, location)
    
    ' Enable alternate unit display
    dimObj.AltUnits = True
    
    ThisDrawing.Application.ZoomAll

    ' Store old Precision value as default for input box
    oldPrecision = dimObj.AltUnitsPrecision
    
    ' Allow the user to change the precision for the alternate dimension
    newPrecision = InputBox("Enter a new precision for the alternate dimension.  The value must range from 0 to 8.", "Alternate Dimension Precision", oldPrecision)
    
    Select Case newPrecision
        Case 0: newPrecision = acDimPrecisionZero
        Case 1: newPrecision = acDimPrecisionOne
        Case 2: newPrecision = acDimPrecisionTwo
        Case 3: newPrecision = acDimPrecisionThree
        Case 4: newPrecision = acDimPrecisionFour
        Case 5: newPrecision = acDimPrecisionFive
        Case 6: newPrecision = acDimPrecisionSix
        Case 7: newPrecision = acDimPrecisionSeven
        Case 8: newPrecision = acDimPrecisionEight
        Case Else
            MsgBox "The alternate precision has not been changed."
            Exit Sub
    End Select
    
    dimObj.AltUnitsPrecision = newPrecision   ' Commit changes to precision
    
    ThisDrawing.Regen acAllViewports
    
    ' Read back and display the alternate dimension precision
    newPrecision = dimObj.AltUnitsPrecision
    MsgBox "The alternate dimension precision has been set to " & newPrecision & " decimal places"
End Sub

Sub Example_AltUnitsScale()
   ' This example creates an aligned dimension in model space and
   ' uses AltUnitsScale to cycle through a couple common scales
   ' for the alternate dimension

    Dim dimObj As AcadDimAligned
    Dim point1(0 To 2) As Double, point2(0 To 2) As Double
    Dim location(0 To 2) As Double
    
    ' Define the dimension
    point1(0) = 0: point1(1) = 5: point1(2) = 0
    point2(0) = 5: point2(1) = 5: point2(2) = 0
    location(0) = 5: location(1) = 7: location(2) = 0
    
    ' Create an aligned dimension object in model space
    Set dimObj = ThisDrawing.ModelSpace.AddDimAligned(point1, point2, location)
    ThisDrawing.Application.ZoomAll
    
    ' Enable alternate unit display
    dimObj.AltUnits = True
      
    ' Cycle through some common dimension scales
    
    dimObj.AltUnitsScale = 1         ' Change scale to Inches
    ThisDrawing.Regen acAllViewports
    MsgBox "The alternate dimension units are now set to inches"
    
    dimObj.AltUnitsScale = 25.4     ' Change scale to Millimeters (default)
    ThisDrawing.Regen acAllViewports
    MsgBox "The alternate dimension units are now set to millimeters"
    
    dimObj.AltUnitsScale = 2.54      ' Change scale to Centimeters
    ThisDrawing.Regen acAllViewports
    MsgBox "The alternate dimension units are now set to centimeters"

End Sub

Sub Example_FractionFormat()
   ' This example creates an aligned dimension in model space and
   ' uses FractionFormat to cycle through a couple fractional formats
   ' for the dimension.
   ' * Note the appearance of the "1/2" component of the dimension

    Dim dimObj As AcadDimAligned
    Dim point1(0 To 2) As Double, point2(0 To 2) As Double
    Dim location(0 To 2) As Double
    
    ' Define the dimension
    point1(0) = 0: point1(1) = 5: point1(2) = 0
    point2(0) = 5.5: point2(1) = 5: point2(2) = 0
    location(0) = 5: location(1) = 7: location(2) = 0
    
    ' Create an aligned dimension object in model space
    Set dimObj = ThisDrawing.ModelSpace.AddDimAligned(point1, point2, location)
    ThisDrawing.Application.ZoomAll
    
    ' Switch to a mode that works with the FractionFormat property
    dimObj.UnitsFormat = acDimLArchitectural
      
    ' Cycle through some common fractional formats
    
    dimObj.FractionFormat = acDiagonal      ' Change format to Diagonal
    ThisDrawing.Regen acAllViewports
    MsgBox "The dimension format is now set to diagonal"
    
    dimObj.FractionFormat = acHorizontal    ' Change format to Horizontal
    ThisDrawing.Regen acAllViewports
    MsgBox "The dimension format is now set to horizontal"

    dimObj.FractionFormat = acNotStacked    ' Change format to NotStacked
    ThisDrawing.Regen acAllViewports
    MsgBox "The dimension format is now unstacked"

End Sub

Sub Example_UnitsFormat()
   ' This example creates an aligned dimension in model space and
   ' uses UnitsFormat to cycle through some common unit formats
   ' for the dimension

    Dim dimObj As AcadDimAligned
    Dim point1(0 To 2) As Double, point2(0 To 2) As Double
    Dim location(0 To 2) As Double
    
    ' Define the dimension
    point1(0) = 0: point1(1) = 5: point1(2) = 0
    point2(0) = 5.12345678: point2(1) = 5: point2(2) = 0
    location(0) = 5: location(1) = 7: location(2) = 0
    
    ' Create an aligned dimension object in model space
    Set dimObj = ThisDrawing.ModelSpace.AddDimAligned(point1, point2, location)
    ThisDrawing.Application.ZoomAll
    
    ' Cycle through common unit formats
    
    dimObj.UnitsFormat = acDimLScientific     ' Change format to Scientific
    ThisDrawing.Regen acAllViewports
    MsgBox "The dimension units are now set to Scientific"
    
    dimObj.UnitsFormat = acDimLDecimal        ' Change format to Decimal
    ThisDrawing.Regen acAllViewports
    MsgBox "The dimension units are now set to Decimal"
    
    dimObj.UnitsFormat = acDimLArchitectural  ' Change format to Architectural
    ThisDrawing.Regen acAllViewports
    MsgBox "The dimension units are now set to Architectural"
    
    dimObj.UnitsFormat = acDimLWindowsDesktop ' Change format to WindowsDesktop
    ThisDrawing.Regen acAllViewports
    MsgBox "The dimension units are now set to Windows Desktop"

End Sub


Sub Example_SuppressZeroInches()
   ' This example creates an aligned dimension in model space and
   ' uses SuppressZeroInches to suppress or view the display of
   ' zero inches in the dimension display

    Dim dimObj As AcadDimAligned
    Dim point1(0 To 2) As Double, point2(0 To 2) As Double
    Dim location(0 To 2) As Double
    
    ' Define the dimension
    point1(0) = 0: point1(1) = 5: point1(2) = 0
    point2(0) = 12: point2(1) = 5: point2(2) = 0
    location(0) = 5: location(1) = 7: location(2) = 0
    
    ' Create an aligned dimension object in model space
    Set dimObj = ThisDrawing.ModelSpace.AddDimAligned(point1, point2, location)
    
    ' Set the dimension display to a style that works with SuppressZeroInches
    dimObj.UnitsFormat = acDimLArchitectural
    
    ThisDrawing.Application.ZoomAll
    
Toggle:
    Select Case MsgBox("Press OK to suppress or view the display of zero inches in the dimension", vbOKCancel)
        Case vbOK
            ' Toggle the display of zero inches for the dimension value
            dimObj.SuppressZeroInches = Not (dimObj.SuppressZeroInches)
            ThisDrawing.Regen acAllViewports
        Case vbCancel
            Exit Sub
    End Select
    
    GoTo Toggle
End Sub

Sub Example_SuppressZeroFeet()
   ' This example creates an aligned dimension in model space and
   ' uses SuppressZeroFeet to suppress or view the display of
   ' zero feet in the alternate dimension display

    Dim dimObj As AcadDimAligned
    Dim point1(0 To 2) As Double, point2(0 To 2) As Double
    Dim location(0 To 2) As Double
    
    ' Define the dimension
    point1(0) = 0: point1(1) = 5: point1(2) = 0
    point2(0) = 5: point2(1) = 5: point2(2) = 0
    location(0) = 5: location(1) = 7: location(2) = 0
    
    ' Create an aligned dimension object in model space
    Set dimObj = ThisDrawing.ModelSpace.AddDimAligned(point1, point2, location)
    
    ' Set the dimension display to a style that works with SuppressZeroFeet
    dimObj.UnitsFormat = acDimLArchitectural
    
    ThisDrawing.Application.ZoomAll
    
Toggle:
    Select Case MsgBox("Press OK to suppress or view the display of zero feet in the dimension", vbOKCancel)
        Case vbOK
            ' Toggle the display of zero feet for the dimension value
            dimObj.SuppressZeroFeet = Not (dimObj.SuppressZeroFeet)
            ThisDrawing.Regen acAllViewports
        Case vbCancel
            Exit Sub
    End Select
    
    GoTo Toggle
End Sub

Sub Example_RoundDistance()
   ' This example creates an aligned dimension in model space and
   ' uses RoundDistance to set the unit display
   ' of the dimension to rounded values

    Dim dimObj As AcadDimAligned
    Dim point1(0 To 2) As Double, point2(0 To 2) As Double
    Dim location(0 To 2) As Double
    
    ' Define the dimension
    point1(0) = 5: point1(1) = 5: point1(2) = 0
    point2(0) = 10.123: point2(1) = 5: point2(2) = 0
    location(0) = 5: location(1) = 7: location(2) = 0
    
    ' Create an aligned dimension object in model space
    Set dimObj = ThisDrawing.ModelSpace.AddDimAligned(point1, point2, location)
    
    ThisDrawing.Application.ZoomAll
    
    MsgBox "Press any key to round the dimension unit display to .5"
    
    ' Round the distance of the dimension to 0.50 of a unit
    dimObj.RoundDistance = 0.5
    ThisDrawing.Regen acAllViewports
    
    MsgBox "Dimension units have been rounded to: " & dimObj.RoundDistance

End Sub

Sub Example_AltToleranceSuppressLeadingZeros()
   ' This example creates an aligned dimension in model space and
   ' uses AltToleranceSuppressLeadingZeros to toggle the display of leading zeros
   ' in the alternate dimension tolerance display

    Dim dimObj As AcadDimAligned
    Dim point1(0 To 2) As Double, point2(0 To 2) As Double
    Dim location(0 To 2) As Double
    
    ' Define the dimension
    point1(0) = 5: point1(1) = 5: point1(2) = 0
    point2(0) = 5.01: point2(1) = 5: point2(2) = 0
    location(0) = 5: location(1) = 7: location(2) = 0
    
    ' Create an aligned dimension object in model space
    Set dimObj = ThisDrawing.ModelSpace.AddDimAligned(point1, point2, location)
    
    ' Setup alternate unit tolerance display
    dimObj.AltUnits = True
    dimObj.ToleranceDisplay = acTolLimits
    
    ThisDrawing.Application.ZoomAll
    
Toggle:
    Select Case MsgBox("Press OK to toggle the display of leading zeros in the alternate dimension tolerance", vbOKCancel)
        Case vbOK
            ' Toggle the display of leading zeros for the alternate dimension tolerance value
            dimObj.AltToleranceSuppressLeadingZeros = Not (dimObj.AltToleranceSuppressLeadingZeros)
            ThisDrawing.Regen acAllViewports
        Case vbCancel
            Exit Sub
    End Select
    
    GoTo Toggle
End Sub

Sub Example_AltToleranceSuppressTrailingZeros()
   ' This example creates an aligned dimension in model space and
   ' uses AltToleranceSuppressTrailingZeros to toggle the display of trailing zeros
   ' in the alternate dimension tolerance display

    Dim dimObj As AcadDimAligned
    Dim point1(0 To 2) As Double, point2(0 To 2) As Double
    Dim location(0 To 2) As Double
    
    ' Define the dimension
    point1(0) = 5: point1(1) = 5: point1(2) = 0
    point2(0) = 7: point2(1) = 5: point2(2) = 0
    location(0) = 5: location(1) = 7: location(2) = 0
    
    ' Create an aligned dimension object in model space
    Set dimObj = ThisDrawing.ModelSpace.AddDimAligned(point1, point2, location)
    
    ' Setup alternate unit tolerance display
    dimObj.AltUnits = True
    dimObj.ToleranceDisplay = acTolLimits
    
    ThisDrawing.Application.ZoomAll
    
Toggle:
    Select Case MsgBox("Press OK to toggle the display of trailing zeros in the alternate dimension tolerance", vbOKCancel)
        Case vbOK
            ' Toggle the display of trailing zeros for the alternate dimension tolerance value
            dimObj.AltToleranceSuppressTrailingZeros = Not (dimObj.AltToleranceSuppressTrailingZeros)
            ThisDrawing.Regen acAllViewports
        Case vbCancel
            Exit Sub
    End Select
    
    GoTo Toggle
End Sub

Sub Example_AltToleranceSuppressZeroInches()
   ' This example creates an aligned dimension in model space and
   ' uses AltToleranceSuppressZeroInches to suppress or view the display of
   ' zero inches in the alternate dimension tolerance display

    Dim dimObj As AcadDimAligned
    Dim point1(0 To 2) As Double, point2(0 To 2) As Double
    Dim location(0 To 2) As Double
    
    ' Define the dimension
    point1(0) = 0: point1(1) = 5: point1(2) = 0
    point2(0) = 12: point2(1) = 5: point2(2) = 0
    location(0) = 5: location(1) = 7: location(2) = 0
    
    ' Create an aligned dimension object in model space
    Set dimObj = ThisDrawing.ModelSpace.AddDimAligned(point1, point2, location)
    
    ' Setup alternate unit tolerance display
    dimObj.AltUnits = True
    dimObj.ToleranceDisplay = acTolLimits
    
    ' Set the dimension display to a style that works with AltToleranceSuppressZeroInches
    dimObj.AltUnitsFormat = acDimLArchitectural
    dimObj.AltUnitsScale = 2    ' Set the alternate unit scale to be a multiple of 2
    
    ThisDrawing.Application.ZoomAll
    
Toggle:
    Select Case MsgBox("Press OK to suppress or view the display of zero inches in the alternate dimension tolerance", vbOKCancel)
        Case vbOK
            ' Toggle the display of zero inches for the alternate dimension tolerance value
            dimObj.AltToleranceSuppressZeroInches = Not (dimObj.AltToleranceSuppressZeroInches)
            ThisDrawing.Regen acAllViewports
        Case vbCancel
            Exit Sub
    End Select
    
    GoTo Toggle
End Sub

Sub Example_AltToleranceSuppressZeroFeet()
   ' This example creates an aligned dimension in model space and
   ' uses AltToleranceSuppressZeroFeet to suppress or view the display of
   ' zero feet in the alternate dimension tolerance display

    Dim dimObj As AcadDimAligned
    Dim point1(0 To 2) As Double, point2(0 To 2) As Double
    Dim location(0 To 2) As Double
    
    ' Define the dimension
    point1(0) = 0: point1(1) = 5: point1(2) = 0
    point2(0) = 5: point2(1) = 5: point2(2) = 0
    location(0) = 5: location(1) = 7: location(2) = 0
    
    ' Create an aligned dimension object in model space
    Set dimObj = ThisDrawing.ModelSpace.AddDimAligned(point1, point2, location)
    
    ' Setup alternate unit tolerance display
    dimObj.AltUnits = True
    dimObj.ToleranceDisplay = acTolLimits
    
    ' Set the dimension display to a style that works with AltToleranceSuppressZeroFeet
    dimObj.AltUnitsFormat = acDimLArchitectural
    dimObj.AltUnitsScale = 2    ' Set the alternate unit scale to be a multiple of 2
    
    ThisDrawing.Application.ZoomAll
    
Toggle:
    Select Case MsgBox("Press OK to suppress or view the display of zero feet in the alternate dimension tolerance", vbOKCancel)
        Case vbOK
            ' Toggle the display of zero feet for the alternate dimension value
            dimObj.AltToleranceSuppressZeroFeet = Not (dimObj.AltToleranceSuppressZeroFeet)
            ThisDrawing.Regen acAllViewports
        Case vbCancel
            Exit Sub
    End Select
    
    GoTo Toggle
End Sub

Sub Example_AddDim3PointAngular()
    ' This example creates a Dim3PointAngular object in model space
    
    Dim DimPointAngularObj As AcadDim3PointAngular
    Dim AngleVertex(0 To 2) As Double
    Dim FirstPoint(0 To 2) As Double, SecondPoint(0 To 2) As Double
    Dim TextPoint(0 To 2) As Double
    
    ' Define the new Dim3PointAngular object
    AngleVertex(0) = 0: AngleVertex(1) = 0: AngleVertex(2) = 0
    FirstPoint(0) = 2: FirstPoint(1) = 2: FirstPoint(2) = 0
    SecondPoint(0) = 2: SecondPoint(1) = 4: SecondPoint(2) = 0
    TextPoint(0) = 6: TextPoint(1) = 6: TextPoint(2) = 0

    ' Create the new Dim3PointAngular object in model space
    Set DimPointAngularObj = ThisDrawing.ModelSpace.AddDim3PointAngular(AngleVertex, FirstPoint, SecondPoint, TextPoint)
    ThisDrawing.Application.ZoomAll
    
    MsgBox "A Dim3PointAngular object has been created."
    
End Sub

Sub Example_AngleFormat()
    ' This example creates a Dim3PointAngular object in model space
    ' and sets its Angle Format to some common values
    
    Dim DimPointAngularObj As AcadDim3PointAngular
    Dim AngleVertex(0 To 2) As Double
    Dim FirstPoint(0 To 2) As Double, SecondPoint(0 To 2) As Double
    Dim TextPoint(0 To 2) As Double
    
    ' Define the new Dim3PointAngular object
    AngleVertex(0) = 0: AngleVertex(1) = 0: AngleVertex(2) = 0
    FirstPoint(0) = 2: FirstPoint(1) = 2: FirstPoint(2) = 0
    SecondPoint(0) = 1: SecondPoint(1) = 4: SecondPoint(2) = 0
    TextPoint(0) = 6: TextPoint(1) = 6: TextPoint(2) = 0

    ' Create the new Dim3PointAngular object in model space
    Set DimPointAngularObj = ThisDrawing.ModelSpace.AddDim3PointAngular(AngleVertex, FirstPoint, SecondPoint, TextPoint)
    ThisDrawing.Application.ZoomAll

    ' Cycle through some common angle formats
    
    DimPointAngularObj.AngleFormat = acDegreeMinuteSeconds
    ThisDrawing.Regen acAllViewports
    MsgBox "The angle format of the new Dim3PointAngular object is now set to degree/minute/second"
    
    DimPointAngularObj.AngleFormat = acGrads
    ThisDrawing.Regen acAllViewports
    MsgBox "The angle format of the new Dim3PointAngular object is now set to grads"

    DimPointAngularObj.AngleFormat = acRadians
    ThisDrawing.Regen acAllViewports
    MsgBox "The angle format of the new Dim3PointAngular object is now set to radians"

End Sub

Sub Example_AngleVertex()
    ' This example creates a Dim3PointAngular object in model space
    ' and then alters its angle vertex
    
    Dim DimPointAngularObj As AcadDim3PointAngular
    Dim AngleVertex(0 To 2) As Double, NewAngleVertex(0 To 2) As Double
    Dim FirstPoint(0 To 2) As Double, SecondPoint(0 To 2) As Double
    Dim TextPoint(0 To 2) As Double
    Dim CurrentVertex As Variant
    
    ' Define the new Dim3PointAngular object
    AngleVertex(0) = 0: AngleVertex(1) = 0: AngleVertex(2) = 0
    NewAngleVertex(0) = 1: NewAngleVertex(1) = 1: NewAngleVertex(2) = 0
    FirstPoint(0) = 2: FirstPoint(1) = 2: FirstPoint(2) = 0
    SecondPoint(0) = 1: SecondPoint(1) = 4: SecondPoint(2) = 0
    TextPoint(0) = 6: TextPoint(1) = 6: TextPoint(2) = 0

    ' Create the new Dim3PointAngular object in model space
    Set DimPointAngularObj = ThisDrawing.ModelSpace.AddDim3PointAngular(AngleVertex, FirstPoint, SecondPoint, TextPoint)
    ThisDrawing.Application.ZoomAll

    ' Display current vertex
    CurrentVertex = DimPointAngularObj.AngleVertex
    MsgBox "The angle vertex of the new object is set to:" & vbCrLf & _
            CurrentVertex(0) & vbCrLf & _
            CurrentVertex(1) & vbCrLf & _
            CurrentVertex(2)

    ' Alter vertex setting for this object
    DimPointAngularObj.AngleVertex = NewAngleVertex
    ThisDrawing.Regen acAllViewports
    
    ' Display new vertex settings
    CurrentVertex = DimPointAngularObj.AngleVertex
    MsgBox "The angle vertex of the object has been reset to:" & vbCrLf & _
            CurrentVertex(0) & vbCrLf & _
            CurrentVertex(1) & vbCrLf & _
            CurrentVertex(2)
    
End Sub

Sub Example_ArrowHeadSize()
    ' This example creates a Dim3PointAngular object in model space
    ' and then alters the visible appearance (size) of its arrow heads
    ' using the ArrowHeadSize property
    
    Dim DimPointAngularObj As AcadDim3PointAngular
    Dim AngleVertex(0 To 2) As Double
    Dim FirstPoint(0 To 2) As Double, SecondPoint(0 To 2) As Double
    Dim TextPoint(0 To 2) As Double
    
    ' Define the new Dim3PointAngular object
    AngleVertex(0) = 0: AngleVertex(1) = 0: AngleVertex(2) = 0
    FirstPoint(0) = 2: FirstPoint(1) = 2: FirstPoint(2) = 0
    SecondPoint(0) = 1: SecondPoint(1) = 4: SecondPoint(2) = 0
    TextPoint(0) = 6: TextPoint(1) = 6: TextPoint(2) = 0

    ' Create the new Dim3PointAngular object in model space
    Set DimPointAngularObj = ThisDrawing.ModelSpace.AddDim3PointAngular(AngleVertex, FirstPoint, SecondPoint, TextPoint)
    ThisDrawing.Application.ZoomAll

    ' Read and display current arrow head size
    MsgBox "The arrow head size for this object is currently set to: " & DimPointAngularObj.ArrowheadSize

    ' Alter the arrow head size property for this object
    DimPointAngularObj.ArrowheadSize = 0.5
    ThisDrawing.Regen acAllViewports
    
    ' Read and display new arrow head size setting
    MsgBox "The arrow head size for this object is now set to: " & DimPointAngularObj.ArrowheadSize
End Sub

Sub Example_ArrowHead1Type()
    ' This example creates a Dim3PointAngular object in model space
    ' and then alters the visible appearance (shape) of its arrow heads
    ' using the ArrowHead1Type and ArrowHead2Type properties
    
    Dim DimPointAngularObj As AcadDim3PointAngular
    Dim AngleVertex(0 To 2) As Double
    Dim FirstPoint(0 To 2) As Double, SecondPoint(0 To 2) As Double
    Dim TextPoint(0 To 2) As Double
    
    ' Define the new Dim3PointAngular object
    AngleVertex(0) = 0: AngleVertex(1) = 0: AngleVertex(2) = 0
    FirstPoint(0) = 2: FirstPoint(1) = 2: FirstPoint(2) = 0
    SecondPoint(0) = 1: SecondPoint(1) = 4: SecondPoint(2) = 0
    TextPoint(0) = 6: TextPoint(1) = 6: TextPoint(2) = 0

    ' Create the new Dim3PointAngular object in model space
    Set DimPointAngularObj = ThisDrawing.ModelSpace.AddDim3PointAngular(AngleVertex, FirstPoint, SecondPoint, TextPoint)
    ThisDrawing.Application.ZoomAll

    ' Read and display current arrow head type
    MsgBox "The arrow head type for the first arrow of this object is: " & DimPointAngularObj.Arrowhead1Type & vbCrLf & _
           "The arrow head type for the second arrow of this object is: " & DimPointAngularObj.Arrowhead2Type

    ' Alter the arrow head type property for both arrows of this object
    DimPointAngularObj.Arrowhead1Type = acArrowBoxBlank
    DimPointAngularObj.Arrowhead2Type = acArrowBoxBlank
    ThisDrawing.Regen acAllViewports
    
    ' Read and display current arrow head type
    MsgBox "The arrow head type for the first arrow of this object is now set to: " & DimPointAngularObj.Arrowhead1Type & vbCrLf & _
           "The arrow head type for the second arrow of this object is now set to: " & DimPointAngularObj.Arrowhead2Type
End Sub

Sub Example_ArrowHead2Type()
    ' This example creates a Dim3PointAngular object in model space
    ' and then alters the visible appearance (shape) of its arrow heads
    ' using the ArrowHead1Type and ArrowHead2Type properties
    
    Dim DimPointAngularObj As AcadDim3PointAngular
    Dim AngleVertex(0 To 2) As Double
    Dim FirstPoint(0 To 2) As Double, SecondPoint(0 To 2) As Double
    Dim TextPoint(0 To 2) As Double
    
    ' Define the new Dim3PointAngular object
    AngleVertex(0) = 0: AngleVertex(1) = 0: AngleVertex(2) = 0
    FirstPoint(0) = 2: FirstPoint(1) = 2: FirstPoint(2) = 0
    SecondPoint(0) = 1: SecondPoint(1) = 4: SecondPoint(2) = 0
    TextPoint(0) = 6: TextPoint(1) = 6: TextPoint(2) = 0

    ' Create the new Dim3PointAngular object in model space
    Set DimPointAngularObj = ThisDrawing.ModelSpace.AddDim3PointAngular(AngleVertex, FirstPoint, SecondPoint, TextPoint)
    ThisDrawing.Application.ZoomAll

    ' Read and display current arrow head type
    MsgBox "The arrow head type for the first arrow of this object is: " & DimPointAngularObj.Arrowhead1Type & vbCrLf & _
           "The arrow head type for the second arrow of this object is: " & DimPointAngularObj.Arrowhead2Type

    ' Alter the arrow head type property for both arrows of this object
    DimPointAngularObj.Arrowhead1Type = acArrowBoxBlank
    DimPointAngularObj.Arrowhead2Type = acArrowBoxBlank
    ThisDrawing.Regen acAllViewports
    
    ' Read and display current arrow head type
    MsgBox "The arrow head type for the first arrow of this object is now set to: " & DimPointAngularObj.Arrowhead1Type & vbCrLf & _
           "The arrow head type for the second arrow of this object is now set to: " & DimPointAngularObj.Arrowhead2Type
End Sub


Sub Example_DecimalSeparator()
    ' This example creates a Dim3PointAngular object in model space
    ' and allows the user to change the decimal separator appearance
    ' using the DecimalSeparator property
    
    Dim DimPointAngularObj As AcadDim3PointAngular
    Dim AngleVertex(0 To 2) As Double
    Dim FirstPoint(0 To 2) As Double, SecondPoint(0 To 2) As Double
    Dim TextPoint(0 To 2) As Double
    Dim oldSeparator As String, newSeparator As String
    
    ' Define the new Dim3PointAngular object
    AngleVertex(0) = 0: AngleVertex(1) = 0: AngleVertex(2) = 0
    FirstPoint(0) = 2: FirstPoint(1) = 2: FirstPoint(2) = 0
    SecondPoint(0) = 1: SecondPoint(1) = 4: SecondPoint(2) = 0
    TextPoint(0) = 6: TextPoint(1) = 6: TextPoint(2) = 0

    ' Create the new Dim3PointAngular object in model space
    Set DimPointAngularObj = ThisDrawing.ModelSpace.AddDim3PointAngular(AngleVertex, FirstPoint, SecondPoint, TextPoint)
    
    ' Set precision so degrees are visible
    DimPointAngularObj.TextPrecision = acDimPrecisionFour
    
    ThisDrawing.Application.ZoomAll

    ' Read and display current decimal separator
    MsgBox "The decimal separator for this object is currently set to: [" & DimPointAngularObj.DecimalSeparator & "]"

    ' Alter the decimal separator property for this object
    oldSeparator = DimPointAngularObj.DecimalSeparator
    newSeparator = InputBox("Enter a new decimal separator", "Change Decimal Separator", oldSeparator)
    
    If newSeparator = "" Then
        Exit Sub
    Else
        ' Set new decimal separator, making sure we only use one character
        DimPointAngularObj.DecimalSeparator = Left(newSeparator, 1)
    End If
    
    ThisDrawing.Regen acAllViewports
    
    ' Read and display current decimal separator
    MsgBox "The decimal separator for this object is now set to: [" & DimPointAngularObj.DecimalSeparator & "]"
End Sub

Sub Example_DimensionLineColor()
    ' This example creates a Dim3PointAngular object in model space
    ' and changes the dimension line color to red using the DimensionLineColor property
    
    Dim DimPointAngularObj As AcadDim3PointAngular
    Dim AngleVertex(0 To 2) As Double
    Dim FirstPoint(0 To 2) As Double, SecondPoint(0 To 2) As Double
    Dim TextPoint(0 To 2) As Double
    
    ' Define the new Dim3PointAngular object
    AngleVertex(0) = 0: AngleVertex(1) = 0: AngleVertex(2) = 0
    FirstPoint(0) = 2: FirstPoint(1) = 2: FirstPoint(2) = 0
    SecondPoint(0) = 1: SecondPoint(1) = 4: SecondPoint(2) = 0
    TextPoint(0) = 6: TextPoint(1) = 6: TextPoint(2) = 0

    ' Create the new Dim3PointAngular object in model space
    Set DimPointAngularObj = ThisDrawing.ModelSpace.AddDim3PointAngular(AngleVertex, FirstPoint, SecondPoint, TextPoint)
    ThisDrawing.Application.ZoomAll

    ' Read and display current dimension line color
    MsgBox "The dimension line color for this object is currently set to: " & DimPointAngularObj.DimensionLineColor

    ' Change the dimension line color
    DimPointAngularObj.DimensionLineColor = acRed
    ThisDrawing.Regen acAllViewports
    
    ' Read and display current dimension line color
    MsgBox "The dimension line color for this object is now set to: " & DimPointAngularObj.DimensionLineColor & " (Red)"
    
End Sub

Sub Example_DimensionLineWeight()
    ' This example creates a Dim3PointAngular object in model space
    ' and changes the dimension line weight to a thicker value
    ' using the DimensionLineWeight property
    
    Dim DimPointAngularObj As AcadDim3PointAngular
    Dim AngleVertex(0 To 2) As Double
    Dim FirstPoint(0 To 2) As Double, SecondPoint(0 To 2) As Double
    Dim TextPoint(0 To 2) As Double
    Dim oldLWSetting As Boolean
    Dim CurrentSetting As String
        
    ' Turn on line weight display so we can see the changes
    oldLWSetting = ThisDrawing.preferences.LineWeightDisplay
    ThisDrawing.preferences.LineWeightDisplay = True
    
    ' Define the new Dim3PointAngular object
    AngleVertex(0) = 0: AngleVertex(1) = 0: AngleVertex(2) = 0
    FirstPoint(0) = 2: FirstPoint(1) = 2: FirstPoint(2) = 0
    SecondPoint(0) = 1: SecondPoint(1) = 4: SecondPoint(2) = 0
    TextPoint(0) = 6: TextPoint(1) = 6: TextPoint(2) = 0

    ' Create the new Dim3PointAngular object in model space
    Set DimPointAngularObj = ThisDrawing.ModelSpace.AddDim3PointAngular(AngleVertex, FirstPoint, SecondPoint, TextPoint)
    ThisDrawing.Application.ZoomAll

    ' Read and display current dimension line weight
    CurrentSetting = DimPointAngularObj.DimensionLineWeight
    Select Case CurrentSetting
        Case acLnWtByLayer: CurrentSetting = "By Layer"
        Case acLnWtByBlock: CurrentSetting = "By Block"
        Case acLnWtByLwDefault: CurrentSetting = "By Default"
        Case Else
    End Select

    MsgBox "The dimension line weight setting for this object is currently set to: " & CurrentSetting

    ' Change the dimension line weight
    DimPointAngularObj.DimensionLineWeight = acLnWt100
    ThisDrawing.Regen acAllViewports
    
    ' Read and display current dimension line weight
    MsgBox "The dimension line weight setting for this object is now set to: " & DimPointAngularObj.DimensionLineWeight
    
    ' Return previous line weight setting
    ThisDrawing.preferences.LineWeightDisplay = oldLWSetting

End Sub

Sub Example_DimensionLine1Suppress()
    ' This example creates a Dim3PointAngular object in model space
    ' and suppresses the dimension lines using the DimensionLine1Suppress
    ' and DimensionLine2Suppress properties
    
    Dim DimPointAngularObj As AcadDim3PointAngular
    Dim AngleVertex(0 To 2) As Double
    Dim FirstPoint(0 To 2) As Double, SecondPoint(0 To 2) As Double
    Dim TextPoint(0 To 2) As Double
    Dim Line1Suppressed As String, Line2Suppressed As String
    
    ' Define the new Dim3PointAngular object
    AngleVertex(0) = 0: AngleVertex(1) = 0: AngleVertex(2) = 0
    FirstPoint(0) = 2: FirstPoint(1) = 2: FirstPoint(2) = 0
    SecondPoint(0) = 1: SecondPoint(1) = 4: SecondPoint(2) = 0
    TextPoint(0) = 6: TextPoint(1) = 6: TextPoint(2) = 0

    ' Create the new Dim3PointAngular object in model space
    Set DimPointAngularObj = ThisDrawing.ModelSpace.AddDim3PointAngular(AngleVertex, FirstPoint, SecondPoint, TextPoint)
    ThisDrawing.Application.ZoomAll

    ' Read and display current line suppression information
    Line1Suppressed = IIf(DimPointAngularObj.DimLine1Suppress, "is suppressed", "is not suppressed")
    Line2Suppressed = IIf(DimPointAngularObj.DimLine2Suppress, "is suppressed", "is not suppressed")
    
    MsgBox "Line one of the dimension " & Line1Suppressed & vbCrLf & _
           "Line two of the dimension " & Line2Suppressed

    ' Suppress line one of the dimension
    DimPointAngularObj.DimLine1Suppress = True
    ThisDrawing.Regen acAllViewports
    MsgBox "Line one of the dimension is now suppressed"
    
    ' Suppress line two of the dimension
    DimPointAngularObj.DimLine2Suppress = True
    ThisDrawing.Regen acAllViewports
    MsgBox "Line two of the dimension is now suppressed"
   
   ' Turn both dimension lines back on
    DimPointAngularObj.DimLine1Suppress = False
    DimPointAngularObj.DimLine2Suppress = False
    ThisDrawing.Regen acAllViewports
    MsgBox "Both dimension lines are now visible again"

End Sub

Sub Example_DimensionLine2Suppress()
    ' This example creates a Dim3PointAngular object in model space
    ' and suppresses the dimension lines using the DimensionLine1Suppress
    ' and DimensionLine2Suppress properties
    
    Dim DimPointAngularObj As AcadDim3PointAngular
    Dim AngleVertex(0 To 2) As Double
    Dim FirstPoint(0 To 2) As Double, SecondPoint(0 To 2) As Double
    Dim TextPoint(0 To 2) As Double
    Dim Line1Suppressed As String, Line2Suppressed As String
    
    ' Define the new Dim3PointAngular object
    AngleVertex(0) = 0: AngleVertex(1) = 0: AngleVertex(2) = 0
    FirstPoint(0) = 2: FirstPoint(1) = 2: FirstPoint(2) = 0
    SecondPoint(0) = 1: SecondPoint(1) = 4: SecondPoint(2) = 0
    TextPoint(0) = 6: TextPoint(1) = 6: TextPoint(2) = 0

    ' Create the new Dim3PointAngular object in model space
    Set DimPointAngularObj = ThisDrawing.ModelSpace.AddDim3PointAngular(AngleVertex, FirstPoint, SecondPoint, TextPoint)
    ThisDrawing.Application.ZoomAll

    ' Read and display current line suppression information
    Line1Suppressed = IIf(DimPointAngularObj.DimLine1Suppress, "is suppressed", "is not suppressed")
    Line2Suppressed = IIf(DimPointAngularObj.DimLine2Suppress, "is suppressed", "is not suppressed")
    
    MsgBox "Line one of the dimension " & Line1Suppressed & vbCrLf & _
           "Line two of the dimension " & Line2Suppressed

    ' Suppress line one of the dimension
    DimPointAngularObj.DimLine1Suppress = True
    ThisDrawing.Regen acAllViewports
    MsgBox "Line one of the dimension is now suppressed"
    
    ' Suppress line two of the dimension
    DimPointAngularObj.DimLine2Suppress = True
    ThisDrawing.Regen acAllViewports
    MsgBox "Line two of the dimension is now suppressed"
   
   ' Turn both dimension lines back on
    DimPointAngularObj.DimLine1Suppress = False
    DimPointAngularObj.DimLine2Suppress = False
    ThisDrawing.Regen acAllViewports
    MsgBox "Both dimension lines are now visible again"

End Sub

Sub Example_DimLineInside()
    ' This example creates a DimAligned object in model space
    ' and toggles the dimension lines to be both allowed and disallowed
    ' outside the extension lines
    
    Dim dimObj As AcadDimAligned
    Dim point1(0 To 2) As Double, point2(0 To 2) As Double
    Dim location(0 To 2) As Double
    Dim CurrentValue As String
    
    ' Define the dimension
    point1(0) = 5: point1(1) = 5: point1(2) = 0
    point2(0) = 6: point2(1) = 5: point2(2) = 0
    location(0) = 5: location(1) = 7: location(2) = 0
    
    ' Create an aligned dimension object in model space
    Set dimObj = ThisDrawing.ModelSpace.AddDimAligned(point1, point2, location)
    ThisDrawing.Application.ZoomAll

    ' Read and display current line suppression information
    CurrentValue = IIf(dimObj.DimLineInside, "are not", "are")
    MsgBox "Dimension lines " & CurrentValue & " allowed outside the extension lines"

    ' Suppress the display of dimension lines outside the extension lines
    dimObj.DimLineInside = True
    ThisDrawing.Regen acAllViewports
    MsgBox "Dimension lines are not allowed outside the extension lines"
   
    ' Allow the display of dimension lines outside the extension lines (default)
    dimObj.DimLineInside = False
    ThisDrawing.Regen acAllViewports
    MsgBox "Dimension lines are allowed outside the extension lines"
   
End Sub

Sub Example_ExtensionLineColor()
    ' This example creates a Dim3PointAngular object in model space
    ' and changes the extension line color to red using the ExtensionLineColor property
    
    Dim DimPointAngularObj As AcadDim3PointAngular
    Dim AngleVertex(0 To 2) As Double
    Dim FirstPoint(0 To 2) As Double, SecondPoint(0 To 2) As Double
    Dim TextPoint(0 To 2) As Double
    
    ' Define the new Dim3PointAngular object
    AngleVertex(0) = 0: AngleVertex(1) = 0: AngleVertex(2) = 0
    FirstPoint(0) = 2: FirstPoint(1) = 2: FirstPoint(2) = 0
    SecondPoint(0) = 1: SecondPoint(1) = 4: SecondPoint(2) = 0
    TextPoint(0) = 6: TextPoint(1) = 6: TextPoint(2) = 0

    ' Create the new Dim3PointAngular object in model space
    Set DimPointAngularObj = ThisDrawing.ModelSpace.AddDim3PointAngular(AngleVertex, FirstPoint, SecondPoint, TextPoint)
    ThisDrawing.Application.ZoomAll

    ' Read and display current dimension line color
    MsgBox "The extension line color for this object is currently set to: " & DimPointAngularObj.ExtensionLineColor

    ' Change the extension line color
    DimPointAngularObj.ExtensionLineColor = acRed
    ThisDrawing.Regen acAllViewports
    
    ' Read and display current extension line color
    MsgBox "The extension line color for this object is now set to: " & DimPointAngularObj.ExtensionLineColor & " (Red)"
    
End Sub

Sub Example_ExtensionLineExtend()
    ' This example creates a Dim3PointAngular object in model space
    ' and changes the length of the extension line to extend 1.5 units past
    ' the dimension using the ExtensionLineExtend property
    
    Dim DimPointAngularObj As AcadDim3PointAngular
    Dim AngleVertex(0 To 2) As Double
    Dim FirstPoint(0 To 2) As Double, SecondPoint(0 To 2) As Double
    Dim TextPoint(0 To 2) As Double
    
    ' Define the new Dim3PointAngular object
    AngleVertex(0) = 0: AngleVertex(1) = 0: AngleVertex(2) = 0
    FirstPoint(0) = 2: FirstPoint(1) = 2: FirstPoint(2) = 0
    SecondPoint(0) = 1: SecondPoint(1) = 4: SecondPoint(2) = 0
    TextPoint(0) = 6: TextPoint(1) = 6: TextPoint(2) = 0

    ' Create the new Dim3PointAngular object in model space
    Set DimPointAngularObj = ThisDrawing.ModelSpace.AddDim3PointAngular(AngleVertex, FirstPoint, SecondPoint, TextPoint)
    ThisDrawing.Application.ZoomAll

    ' Read and display current extension line extend length
    MsgBox "The extension line currently extends " & DimPointAngularObj.ExtensionLineExtend & " units past the dimension"

    ' Change the extension line extend length to extend 1.5
    ' units past the dimension
    DimPointAngularObj.ExtensionLineExtend = 1.5
    ThisDrawing.Regen acAllViewports
    
    ' Read and display current extension line extend length
    MsgBox "The extension line now extends " & DimPointAngularObj.ExtensionLineExtend & " units past the dimension"
    
End Sub

Sub Example_ExtensionLineOffset()
    ' This example creates a Dim3PointAngular object in model space
    ' and changes the offset of the extension lines using the
    ' ExtensionLineOffset property
    
    Dim DimPointAngularObj As AcadDim3PointAngular
    Dim AngleVertex(0 To 2) As Double
    Dim FirstPoint(0 To 2) As Double, SecondPoint(0 To 2) As Double
    Dim TextPoint(0 To 2) As Double
    
    ' Define the new Dim3PointAngular object
    AngleVertex(0) = 0: AngleVertex(1) = 0: AngleVertex(2) = 0
    FirstPoint(0) = 2: FirstPoint(1) = 2: FirstPoint(2) = 0
    SecondPoint(0) = 1: SecondPoint(1) = 4: SecondPoint(2) = 0
    TextPoint(0) = 6: TextPoint(1) = 6: TextPoint(2) = 0

    ' Create the new Dim3PointAngular object in model space
    Set DimPointAngularObj = ThisDrawing.ModelSpace.AddDim3PointAngular(AngleVertex, FirstPoint, SecondPoint, TextPoint)
    ThisDrawing.Application.ZoomAll

    ' Read and display current offset of the extension lines from the control points
    MsgBox "The extension lines are currently offset " & DimPointAngularObj.ExtensionLineOffset & " units"

    ' Change the extension lines offset distance from the control points
    DimPointAngularObj.ExtensionLineOffset = 1.5
    ThisDrawing.Regen acAllViewports
    
    ' Read and display current offset of the extension lines from the control points
    MsgBox "The extension lines are now offset " & DimPointAngularObj.ExtensionLineOffset & " units"
    
End Sub

Sub Example_ExtensionLineWeight()
    ' This example creates a Dim3PointAngular object in model space
    ' and changes the extension line weight to a thicker value
    ' using the ExtensionLineWeight property
    
    Dim DimPointAngularObj As AcadDim3PointAngular
    Dim AngleVertex(0 To 2) As Double
    Dim FirstPoint(0 To 2) As Double, SecondPoint(0 To 2) As Double
    Dim TextPoint(0 To 2) As Double
    Dim oldLWSetting As Boolean
    Dim CurrentSetting As String
    
    ' Turn on line weight display so we can see the changes
    oldLWSetting = ThisDrawing.preferences.LineWeightDisplay
    ThisDrawing.preferences.LineWeightDisplay = True
    
    ' Define the new Dim3PointAngular object
    AngleVertex(0) = 0: AngleVertex(1) = 0: AngleVertex(2) = 0
    FirstPoint(0) = 2: FirstPoint(1) = 2: FirstPoint(2) = 0
    SecondPoint(0) = 1: SecondPoint(1) = 4: SecondPoint(2) = 0
    TextPoint(0) = 6: TextPoint(1) = 6: TextPoint(2) = 0

    ' Create the new Dim3PointAngular object in model space
    Set DimPointAngularObj = ThisDrawing.ModelSpace.AddDim3PointAngular(AngleVertex, FirstPoint, SecondPoint, TextPoint)
    ThisDrawing.Application.ZoomAll

    ' Read and display current extension line weight
    CurrentSetting = DimPointAngularObj.ExtensionLineWeight
    Select Case CurrentSetting
        Case acLnWtByLayer: CurrentSetting = "By Layer"
        Case acLnWtByBlock: CurrentSetting = "By Block"
        Case acLnWtByLwDefault: CurrentSetting = "By Default"
        Case Else
    End Select
    
    MsgBox "The extension line weight for this object is currently set to: " & CurrentSetting

    ' Change the extension line weight
    DimPointAngularObj.ExtensionLineWeight = acLnWt100
    ThisDrawing.Regen acAllViewports
    
    ' Read and display current extension line weight
    MsgBox "The extension line weight for this object is now set to: " & DimPointAngularObj.ExtensionLineWeight
    
    ' Return previous line weight setting
    ThisDrawing.preferences.LineWeightDisplay = oldLWSetting
    
End Sub

Sub Example_ExtLine1Suppress()
    ' This example creates a Dim3PointAngular object in model space
    ' and suppresses the extension lines using the ExtLine1Suppress
    ' and ExtLine2Suppress properties
    
    Dim DimPointAngularObj As AcadDim3PointAngular
    Dim AngleVertex(0 To 2) As Double
    Dim FirstPoint(0 To 2) As Double, SecondPoint(0 To 2) As Double
    Dim TextPoint(0 To 2) As Double
    Dim Line1Suppressed As String, Line2Suppressed As String
    
    ' Define the new Dim3PointAngular object
    AngleVertex(0) = 0: AngleVertex(1) = 0: AngleVertex(2) = 0
    FirstPoint(0) = 2: FirstPoint(1) = 2: FirstPoint(2) = 0
    SecondPoint(0) = 1: SecondPoint(1) = 4: SecondPoint(2) = 0
    TextPoint(0) = 6: TextPoint(1) = 6: TextPoint(2) = 0

    ' Create the new Dim3PointAngular object in model space
    Set DimPointAngularObj = ThisDrawing.ModelSpace.AddDim3PointAngular(AngleVertex, FirstPoint, SecondPoint, TextPoint)
    ThisDrawing.Application.ZoomAll

    ' Read and display current extension line suppression information
    Line1Suppressed = IIf(DimPointAngularObj.ExtLine1Suppress, "is suppressed", "is not suppressed")
    Line2Suppressed = IIf(DimPointAngularObj.ExtLine2Suppress, "is suppressed", "is not suppressed")
    
    MsgBox "Line one of the extension " & Line1Suppressed & vbCrLf & _
           "Line two of the extension " & Line2Suppressed

    ' Suppress line one of the extension
    DimPointAngularObj.ExtLine1Suppress = True
    ThisDrawing.Regen acAllViewports
    MsgBox "Line one of the extension is now suppressed"
    
    ' Suppress line two of the extension
    DimPointAngularObj.ExtLine2Suppress = True
    ThisDrawing.Regen acAllViewports
    MsgBox "Line two of the extension is now suppressed"
   
   ' Turn both extension lines back on
    DimPointAngularObj.ExtLine1Suppress = False
    DimPointAngularObj.ExtLine2Suppress = False
    ThisDrawing.Regen acAllViewports
    MsgBox "Both extension lines are now visible again"

End Sub

Sub Example_ExtLine2Suppress()
    ' This example creates a Dim3PointAngular object in model space
    ' and suppresses the extension lines using the ExtLine1Suppress
    ' and ExtLine2Suppress properties
    
    Dim DimPointAngularObj As AcadDim3PointAngular
    Dim AngleVertex(0 To 2) As Double
    Dim FirstPoint(0 To 2) As Double, SecondPoint(0 To 2) As Double
    Dim TextPoint(0 To 2) As Double
    Dim Line1Suppressed As String, Line2Suppressed As String
    
    ' Define the new Dim3PointAngular object
    AngleVertex(0) = 0: AngleVertex(1) = 0: AngleVertex(2) = 0
    FirstPoint(0) = 2: FirstPoint(1) = 2: FirstPoint(2) = 0
    SecondPoint(0) = 1: SecondPoint(1) = 4: SecondPoint(2) = 0
    TextPoint(0) = 6: TextPoint(1) = 6: TextPoint(2) = 0

    ' Create the new Dim3PointAngular object in model space
    Set DimPointAngularObj = ThisDrawing.ModelSpace.AddDim3PointAngular(AngleVertex, FirstPoint, SecondPoint, TextPoint)
    ThisDrawing.Application.ZoomAll

    ' Read and display current extension line suppression information
    Line1Suppressed = IIf(DimPointAngularObj.ExtLine1Suppress, "is suppressed", "is not suppressed")
    Line2Suppressed = IIf(DimPointAngularObj.ExtLine2Suppress, "is suppressed", "is not suppressed")
    
    MsgBox "Line one of the extension " & Line1Suppressed & vbCrLf & _
           "Line two of the extension " & Line2Suppressed

    ' Suppress line one of the extension
    DimPointAngularObj.ExtLine1Suppress = True
    ThisDrawing.Regen acAllViewports
    MsgBox "Line one of the extension is now suppressed"
    
    ' Suppress line two of the extension
    DimPointAngularObj.ExtLine2Suppress = True
    ThisDrawing.Regen acAllViewports
    MsgBox "Line two of the extension is now suppressed"
   
   ' Turn both extension lines back on
    DimPointAngularObj.ExtLine1Suppress = False
    DimPointAngularObj.ExtLine2Suppress = False
    ThisDrawing.Regen acAllViewports
    MsgBox "Both extension lines are now visible again"

End Sub

Sub Example_ForceLineInside()
    ' This example creates an aligned dimension in model space
    ' and toggles dimension lines to be drawn between extension lines
    
    Dim dimObj As AcadDimAligned
    Dim point1(0 To 2) As Double, point2(0 To 2) As Double
    Dim location(0 To 2) As Double
    Dim CurrentValue As String
    
    ' Define the dimension
    point1(0) = 5: point1(1) = 5: point1(2) = 0
    point2(0) = 5.5: point2(1) = 5: point2(2) = 0
    location(0) = 5: location(1) = 7: location(2) = 0
    
    ' Create an aligned dimension object in model space
    Set dimObj = ThisDrawing.ModelSpace.AddDimAligned(point1, point2, location)
    ThisDrawing.Application.ZoomAll

    ' Read and display current line suppression information
    CurrentValue = IIf(dimObj.ForceLineInside, "are", "are not")
    MsgBox "Dimension lines " & CurrentValue & " forced between the extension lines"

    ' Force the display of dimension lines between the extension lines
    dimObj.ForceLineInside = True
    ThisDrawing.Regen acAllViewports
    MsgBox "Dimension lines are forced between the extension lines"
   
    ' Do not force the display of dimension lines between the extension lines (default)
    dimObj.ForceLineInside = False
    ThisDrawing.Regen acAllViewports
    MsgBox "Dimension lines are not forced between the extension lines"

End Sub

Sub Example_HorizontalTextPosition()
    ' This example creates an aligned dimension in model space
    ' and cycles the dimension text through a couple of different
    ' horizontal alignments
    
    Dim dimObj As AcadDimAligned
    Dim point1(0 To 2) As Double, point2(0 To 2) As Double
    Dim location(0 To 2) As Double
    Dim CurrentValue As String
    
    ' Define the dimension
    point1(0) = 5: point1(1) = 5: point1(2) = 0
    point2(0) = 9: point2(1) = 5: point2(2) = 0
    location(0) = 5: location(1) = 7: location(2) = 0
    
    ' Create an aligned dimension object in model space
    Set dimObj = ThisDrawing.ModelSpace.AddDimAligned(point1, point2, location)
    ThisDrawing.Application.ZoomAll

    ' Read and display current text position
    Select Case dimObj.HorizontalTextPosition
        Case acHorzCentered:        CurrentValue = "centered"
        Case acFirstExtensionLine:  CurrentValue = "aligned to first extension line"
        Case acSecondExtensionLine: CurrentValue = "aligned to second extension line"
        Case acOverFirstExtension:  CurrentValue = "aligned over first extension line"
        Case acOverSecondExtension: CurrentValue = "aligned over second extension line"
    End Select
    
    MsgBox "The dimension is " & CurrentValue

    ' Force the alignment of the dimension text to the first extension line
    dimObj.HorizontalTextPosition = acFirstExtensionLine
    ThisDrawing.Regen acAllViewports
    MsgBox "Dimension text is now aligned to the first extension line"
   
    ' Force the alignment of the dimension text to the second extension line
    dimObj.HorizontalTextPosition = acSecondExtensionLine
    ThisDrawing.Regen acAllViewports
    MsgBox "Dimension text is now aligned to the second extension line"

End Sub

Sub Example_Measurement()
    ' This example creates an aligned dimension in model space
    ' and return the measurement of the dimension, which in the case
    ' of a linear dimension will be it's length
    
    Dim dimObj As AcadDimAligned
    Dim point1(0 To 2) As Double, point2(0 To 2) As Double
    Dim location(0 To 2) As Double
    Dim CurrentValue As String
    
    ' Define the dimension
    point1(0) = 5: point1(1) = 5: point1(2) = 0
    point2(0) = 9: point2(1) = 5: point2(2) = 0
    location(0) = 5: location(1) = 7: location(2) = 0
    
    ' Create an aligned dimension object in model space
    Set dimObj = ThisDrawing.ModelSpace.AddDimAligned(point1, point2, location)
    ThisDrawing.Application.ZoomAll

    ' Read and display current measurement
    MsgBox "The current measurement of the new dimension is: " & dimObj.Measurement
End Sub

Sub Example_SuppressLeadingZeros()
   ' This example creates an aligned dimension in model space and
   ' uses the SuppressLeadingZeros property to toggle the display of leading zeros
   ' in the dimension display

    Dim dimObj As AcadDimAligned
    Dim point1(0 To 2) As Double, point2(0 To 2) As Double
    Dim location(0 To 2) As Double
    
    ' Define the dimension
    point1(0) = 5: point1(1) = 5: point1(2) = 0
    point2(0) = 5.01: point2(1) = 5: point2(2) = 0
    location(0) = 5: location(1) = 7: location(2) = 0
    
    ' Create an aligned dimension object in model space
    Set dimObj = ThisDrawing.ModelSpace.AddDimAligned(point1, point2, location)
    ThisDrawing.Application.ZoomAll
    
Toggle:
    Select Case MsgBox("Press OK to toggle the display of leading zeros in the dimension", vbOKCancel)
        Case vbOK
            ' Toggle the display of leading zeros for the dimension value
            dimObj.SuppressLeadingZeros = Not (dimObj.SuppressLeadingZeros)
            ThisDrawing.Regen acAllViewports
        
        Case vbCancel
            Exit Sub
    End Select
    
    GoTo Toggle
End Sub

Sub Example_SuppressTrailingZeros()
   ' This example creates an aligned dimension in model space and
   ' uses the SuppressTrailingZeros property to toggle the display of trailing zeros
   ' in the dimension display

    Dim dimObj As AcadDimAligned
    Dim point1(0 To 2) As Double, point2(0 To 2) As Double
    Dim location(0 To 2) As Double
    
    ' Define the dimension
    point1(0) = 5: point1(1) = 5: point1(2) = 0
    point2(0) = 7: point2(1) = 5: point2(2) = 0
    location(0) = 5: location(1) = 7: location(2) = 0
    
    ' Create an aligned dimension object in model space
    Set dimObj = ThisDrawing.ModelSpace.AddDimAligned(point1, point2, location)
    ThisDrawing.Application.ZoomAll
    
Toggle:
    Select Case MsgBox("Press OK to toggle the display of trailing zeros in the dimension", vbOKCancel)
        Case vbOK
            ' Toggle the display of trailing zeros for the dimension value
            dimObj.SuppressTrailingZeros = Not (dimObj.SuppressTrailingZeros)
            ThisDrawing.Regen acAllViewports
        
        Case vbCancel
            Exit Sub
    End Select
    
    GoTo Toggle
End Sub

Sub Example_TextColor()
   ' This example creates an aligned dimension in model space and
   ' uses the TextColor property to toggle the dimension text color to red

    Dim dimObj As AcadDimAligned
    Dim point1(0 To 2) As Double, point2(0 To 2) As Double
    Dim location(0 To 2) As Double
    
    ' Define the dimension
    point1(0) = 5: point1(1) = 5: point1(2) = 0
    point2(0) = 7: point2(1) = 5: point2(2) = 0
    location(0) = 5: location(1) = 7: location(2) = 0
    
    ' Create an aligned dimension object in model space
    Set dimObj = ThisDrawing.ModelSpace.AddDimAligned(point1, point2, location)
    ThisDrawing.Application.ZoomAll

    ' Read and display current dimension text color
    MsgBox "The dimension text color for this object is currently set to: " & dimObj.TextColor

    ' Change the dimension text color
    dimObj.TextColor = acRed
    ThisDrawing.Regen acAllViewports
    
    ' Read and display current dimension text color
    MsgBox "The dimension text color for this object is now set to: " & dimObj.TextColor & " (Red)"
    
End Sub

Sub Example_TextGap()
   ' This example creates an aligned dimension in model space and
   ' uses the TextGap property to increase the distance between the
   ' dimension line and the dimension text

    Dim dimObj As AcadDimAligned
    Dim point1(0 To 2) As Double, point2(0 To 2) As Double
    Dim location(0 To 2) As Double
    
    ' Define the dimension
    point1(0) = 5: point1(1) = 5: point1(2) = 0
    point2(0) = 5.5: point2(1) = 5: point2(2) = 0
    location(0) = 5: location(1) = 7: location(2) = 0
    
    ' Create an aligned dimension object in model space
    Set dimObj = ThisDrawing.ModelSpace.AddDimAligned(point1, point2, location)
    ThisDrawing.Application.ZoomAll

    ' Read and display current dimension gap
    MsgBox "The dimension gap for this object is currently set to: " & dimObj.TextGap

    ' Increase the distance of the dimension gap
    dimObj.TextGap = 0.5
    ThisDrawing.Regen acAllViewports
    
    ' Read and display current dimension gap
    MsgBox "The dimension gap for this object is now set to: " & dimObj.TextGap
    
End Sub

Sub Example_TextHeight()
   ' This example creates an aligned dimension in model space and
   ' uses the TextHeight property to increase the height of the
   ' dimension text

    Dim dimObj As AcadDimAligned
    Dim point1(0 To 2) As Double, point2(0 To 2) As Double
    Dim location(0 To 2) As Double
    
    ' Define the dimension
    point1(0) = 5: point1(1) = 5: point1(2) = 0
    point2(0) = 5.5: point2(1) = 5: point2(2) = 0
    location(0) = 5: location(1) = 7: location(2) = 0
    
    ' Create an aligned dimension object in model space
    Set dimObj = ThisDrawing.ModelSpace.AddDimAligned(point1, point2, location)
    ThisDrawing.Application.ZoomAll

    ' Read and display current dimension text height
    MsgBox "The dimension text height for this object is currently set to: " & dimObj.textHeight

    ' Increase the distance of the dimension gap
    dimObj.textHeight = 1
    ThisDrawing.Regen acAllViewports
    
    ' Read and display current dimension text height
    MsgBox "The dimension text height for this object is now set to: " & dimObj.textHeight
    
End Sub

Sub Example_TextInside()
   ' This example creates an aligned dimension in model space and
   ' allows the user to toggle forcing the dimension text between the extension lines
   ' using the TextInside property

    Dim dimObj As AcadDimAligned
    Dim point1(0 To 2) As Double, point2(0 To 2) As Double
    Dim location(0 To 2) As Double
    Dim CurrentValue As String
    
    ' Define the dimension
    point1(0) = 5: point1(1) = 5: point1(2) = 0
    point2(0) = 5.5: point2(1) = 5: point2(2) = 0
    location(0) = 5: location(1) = 7: location(2) = 0
    
    ' Create an aligned dimension object in model space
    Set dimObj = ThisDrawing.ModelSpace.AddDimAligned(point1, point2, location)
    ThisDrawing.Application.ZoomAll

Toggle:
    Select Case MsgBox("Press OK to toggle forcing the dimension text inside the extension lines", vbOKCancel)
        Case vbOK
            ' Toggle forcing the dimension text inside the extension lines
            dimObj.TextInside = Not (dimObj.TextInside)
            ThisDrawing.Regen acAllViewports
            
            ' Read and display the new dimension TextInside value
            CurrentValue = IIf(dimObj.TextInside, "is now", "is not")
            MsgBox "The dimension text " & CurrentValue & " forced inside the extension lines"
        
        Case vbCancel
            Exit Sub
    End Select
    
    GoTo Toggle
    
End Sub


Sub Example_TextMovement()
   ' This example creates two aligned dimensions in model space and
   ' set the TextMovement property of each one differently to allow
   ' the user to see the differences this property makes when moving
   ' dimension text
   '
   ' To see the effects of this property:
   ' 1) Run this sample
   ' 2) Enter the drawing and move the dimension text of the leftmost object
   '    on the screen with the mouse or keyboard.
   ' 3) Notice the position of the dimension lines
   ' 4) Repeat with the rightmost object
   
    Dim dimObj1 As AcadDimAligned, dimObj2 As AcadDimAligned
    Dim point1(0 To 2) As Double, point2(0 To 2) As Double
    Dim point3(0 To 2) As Double, point4(0 To 2) As Double
    Dim location1(0 To 2) As Double, location2(0 To 2) As Double
        
    ' Define the two dimensions
    point1(0) = 5: point1(1) = 5: point1(2) = 0
    point2(0) = 6: point2(1) = 5: point2(2) = 0
    location1(0) = 5: location1(1) = 7: location1(2) = 0
    
    point3(0) = 7: point3(1) = 5: point3(2) = 0
    point4(0) = 8: point4(1) = 5: point4(2) = 0
    location2(0) = 5: location2(1) = 7: location2(2) = 0
    
    ' Create the aligned dimension objects in model space
    Set dimObj1 = ThisDrawing.ModelSpace.AddDimAligned(point1, point2, location1)
    Set dimObj2 = ThisDrawing.ModelSpace.AddDimAligned(point3, point4, location2)
    
    ThisDrawing.Application.ZoomAll

    ' Set the text movement of the new dimensions to different values
    dimObj1.TextMovement = acMoveTextNoLeader
    dimObj2.TextMovement = acDimLineWithText
       
End Sub

Sub Example_TextPrecision()
   ' This example creates a Dim3PointAngular object in model space and
   ' uses the TextPrecision property to set the precision of
   ' the dimension text to 4 decimal places

    Dim DimPointAngularObj As AcadDim3PointAngular
    Dim AngleVertex(0 To 2) As Double
    Dim FirstPoint(0 To 2) As Double, SecondPoint(0 To 2) As Double
    Dim TextPoint(0 To 2) As Double
    
    ' Define the new Dim3PointAngular object
    AngleVertex(0) = 0: AngleVertex(1) = 0: AngleVertex(2) = 0
    FirstPoint(0) = 2: FirstPoint(1) = 2: FirstPoint(2) = 0
    SecondPoint(0) = 1: SecondPoint(1) = 4: SecondPoint(2) = 0
    TextPoint(0) = 6: TextPoint(1) = 6: TextPoint(2) = 0

    ' Create the new Dim3PointAngular object in model space
    Set DimPointAngularObj = ThisDrawing.ModelSpace.AddDim3PointAngular(AngleVertex, FirstPoint, SecondPoint, TextPoint)
    ThisDrawing.Application.ZoomAll

    ' Read and display current dimension text precision
    MsgBox "The dimension text precision is currently set to: " & DimPointAngularObj.TextPrecision

    ' Increase the distance of the dimension gap
    DimPointAngularObj.TextPrecision = acDimPrecisionFour
    ThisDrawing.Regen acAllViewports
    
    ' Read and display current dimension text precision
    MsgBox "The dimension text precision is now set to: " & DimPointAngularObj.TextPrecision
    
End Sub


Sub Example_TextPrefix()
   ' This example creates an aligned dimension in model space and
   ' uses TextPrefix to allow the user to change the text prefix for the
   ' dimension

    Dim dimObj As AcadDimAligned
    Dim point1(0 To 2) As Double, point2(0 To 2) As Double
    Dim location(0 To 2) As Double
    Dim prefix As String
    
    ' Define the dimension
    point1(0) = 0: point1(1) = 5: point1(2) = 0
    point2(0) = 5: point2(1) = 5: point2(2) = 0
    location(0) = 5: location(1) = 7: location(2) = 0
    
    ' Create an aligned dimension object in model space
    Set dimObj = ThisDrawing.ModelSpace.AddDimAligned(point1, point2, location)
    
    ThisDrawing.Application.ZoomAll

    ' Allow the user to change the text prefix for the dimension
    prefix = InputBox("Enter a new text prefix for the dimension", "Set Dimension Prefix", "PREFIX:")
    dimObj.TextPrefix = prefix   ' Commit changes to prefix
    
    ThisDrawing.Regen acAllViewports
    
    ' Read back and display the dimension text prefix
    prefix = dimObj.TextPrefix
    If prefix <> "" Then
        MsgBox "The prefix of the dimension has been changed to: " & prefix
    Else
        MsgBox "The prefix of the dimension has been removed"
    End If
End Sub

Sub Example_TextSuffix()
   ' This example creates an aligned dimension in model space and
   ' uses TextSuffix to allow the user to change the text suffix for the
   ' dimension

    Dim dimObj As AcadDimAligned
    Dim point1(0 To 2) As Double, point2(0 To 2) As Double
    Dim location(0 To 2) As Double
    Dim suffix As String
    
    ' Define the dimension
    point1(0) = 0: point1(1) = 5: point1(2) = 0
    point2(0) = 5: point2(1) = 5: point2(2) = 0
    location(0) = 5: location(1) = 7: location(2) = 0
    
    ' Create an aligned dimension object in model space
    Set dimObj = ThisDrawing.ModelSpace.AddDimAligned(point1, point2, location)
    
    ThisDrawing.Application.ZoomAll

    ' Allow the user to change the text suffix for the dimension
    suffix = InputBox("Enter a new text suffix for the dimension", "Set Dimension Suffix", ":SUFFIX")
    dimObj.TextSuffix = suffix   ' Commit changes to suffix
    
    ThisDrawing.Regen acAllViewports
    
    ' Read back and display the dimension text suffix
    suffix = dimObj.TextSuffix
    If suffix <> "" Then
        MsgBox "The suffix of the dimension has been changed to: " & suffix
    Else
        MsgBox "The suffix of the dimension has been removed"
    End If
End Sub

Sub Example_TextStyle()
   ' This example creates an aligned dimension in model space and
   ' creates a new system text style.  We then assign the new text style to
   ' the new dimension

    Dim dimObj As AcadDimAligned
    Dim newText As AcadTextStyle
    Dim point1(0 To 2) As Double, point2(0 To 2) As Double
    Dim location(0 To 2) As Double
    
    ' Define the dimension
    point1(0) = 5: point1(1) = 5: point1(2) = 0
    point2(0) = 5.5: point2(1) = 5: point2(2) = 0
    location(0) = 5: location(1) = 7: location(2) = 0
    
    ' Create an aligned dimension object in model space
    Set dimObj = ThisDrawing.ModelSpace.AddDimAligned(point1, point2, location)
    
    ' Create new text style
    Set newText = ThisDrawing.TextStyles.Add("MYSTYLE")
    newText.height = 0.5    ' Just set the height of the new style so we can differentiate
    
    ThisDrawing.Application.ZoomAll
    
    ' Read and display the current text style for this dimension
    MsgBox "The text style is currently set to: " & dimObj.textStyle
    
    ' Change the text style to use the new style we created
    dimObj.textStyle = "MYSTYLE"
    ThisDrawing.Regen acAllViewports
    
    ' Read and display the current text style for this dimension
    MsgBox "The text style is now set to: " & dimObj.textStyle

End Sub

Sub Example_ToleranceDisplay()
   ' This example creates an aligned dimension in model space and
   ' turns on the tolerance display for the new dimension

    Dim dimObj As AcadDimAligned
    Dim newText As AcadTextStyle
    Dim point1(0 To 2) As Double, point2(0 To 2) As Double
    Dim location(0 To 2) As Double
    Dim CurrentDisplay As String
    
    ' Define the dimension
    point1(0) = 5: point1(1) = 5: point1(2) = 0
    point2(0) = 5.5: point2(1) = 5: point2(2) = 0
    location(0) = 5: location(1) = 7: location(2) = 0
    
    ' Create an aligned dimension object in model space
    Set dimObj = ThisDrawing.ModelSpace.AddDimAligned(point1, point2, location)
    
    ThisDrawing.Application.ZoomAll
    
    ' Read and display the current tolerance display for this dimension
    CurrentDisplay = IIf(dimObj.ToleranceDisplay = acTolNone, "Hidden", "Visible")
    MsgBox "The tolerance display is currently: " & CurrentDisplay
    
    ' Toggle the tolerance display for this dimension
    If dimObj.ToleranceDisplay = acTolNone Then
        dimObj.ToleranceDisplay = acTolSymmetrical
        CurrentDisplay = "Symmetrical"
    Else
        dimObj.ToleranceDisplay = acTolNone
        CurrentDisplay = "None"
    End If
    
    ThisDrawing.Regen acAllViewports
    
    ' Display the current tolerance display for this dimension
    MsgBox "The tolerance display is now set to: " & CurrentDisplay

End Sub

Sub Example_ToleranceHeightScale()
   ' This example creates an aligned dimension in model space and
   ' turns on the tolerance display for the new dimension.  The height
   ' of the tolerance text can then be adjusted by the user

    Dim dimObj As AcadDimAligned
    Dim newText As AcadTextStyle
    Dim point1(0 To 2) As Double, point2(0 To 2) As Double
    Dim location(0 To 2) As Double
    Dim CurrentScale As Integer
    
    ' Define the dimension
    point1(0) = 5: point1(1) = 5: point1(2) = 0
    point2(0) = 5.5: point2(1) = 5: point2(2) = 0
    location(0) = 5: location(1) = 7: location(2) = 0
    
    ' Create an aligned dimension object in model space
    Set dimObj = ThisDrawing.ModelSpace.AddDimAligned(point1, point2, location)
    
    ' Turn on the tolerance display
    dimObj.ToleranceDisplay = acTolSymmetrical
    
    ThisDrawing.Application.ZoomAll
    
Increase:
    ' Read and display the current tolerance height scale for this dimension
    If MsgBox("The tolerance height scale is currently set to: " & dimObj.ToleranceHeightScale & vbCrLf & _
               "Press OK to increase, or cancel to finish", vbOKCancel) = vbCancel Then
        
        Exit Sub
    End If
    
    ' Increase the tolerance height scale for this dimension
    dimObj.ToleranceHeightScale = dimObj.ToleranceHeightScale + 1
    
    ThisDrawing.Regen acAllViewports
    
    GoTo Increase
End Sub


Sub Example_ToleranceJustification()
   ' This example creates an aligned dimension in model space and
   ' sets the tolerance justification for the dimension to
   ' a couple of common values
   '
   ' * Note the vertical position of the tolerance text

    Dim dimObj As AcadDimAligned
    Dim newText As AcadTextStyle
    Dim point1(0 To 2) As Double, point2(0 To 2) As Double
    Dim location(0 To 2) As Double
    Dim CurrentDisplay As String
    
    ' Define the dimension
    point1(0) = 5: point1(1) = 5: point1(2) = 0
    point2(0) = 5.5: point2(1) = 5: point2(2) = 0
    location(0) = 5: location(1) = 7: location(2) = 0
    
    ' Create an aligned dimension object in model space
    Set dimObj = ThisDrawing.ModelSpace.AddDimAligned(point1, point2, location)
    
    ' Turn on tolerance display and increase the dimension text height,
    ' so the alignment of the tolerance is visible
    dimObj.ToleranceDisplay = acTolSymmetrical
    dimObj.textHeight = 1
    dimObj.ToleranceHeightScale = 0.25
    
    ThisDrawing.Application.ZoomAll
    
    ' Read and display the current tolerance justification for this dimension
    Select Case dimObj.ToleranceJustification
        Case acTolBottom: CurrentDisplay = "Bottom"
        Case acTolTop: CurrentDisplay = "Top"
        Case acTolMiddle: CurrentDisplay = "Middle"
    End Select
    
    MsgBox "The tolerance justification is currently: " & CurrentDisplay
    
    ' Set the tolerance justification for this dimension
    dimObj.ToleranceJustification = acTolBottom
    
    ThisDrawing.Regen acAllViewports
    
    ' Display the current tolerance justification for this dimension
    MsgBox "The tolerance display is now set to: Bottom"

End Sub

Sub Example_TolerancePrecision()
   ' This example creates an aligned dimension in model space and
   ' uses TolerancePrecision to allow the user to change the
   ' precision of the dimension tolerance

    Dim dimObj As AcadDimAligned
    Dim point1(0 To 2) As Double, point2(0 To 2) As Double
    Dim location(0 To 2) As Double
    Dim oldTolerance As String, newTolerance As String
    
    ' Define the dimension
    point1(0) = 0: point1(1) = 5: point1(2) = 0
    point2(0) = 5.12345678: point2(1) = 5: point2(2) = 0
    location(0) = 5: location(1) = 7: location(2) = 0
    
    ' Create an aligned dimension object in model space
    Set dimObj = ThisDrawing.ModelSpace.AddDimAligned(point1, point2, location)
    
    ' Enable and setup tolerance display
    dimObj.ToleranceDisplay = acTolSymmetrical
    dimObj.ToleranceLowerLimit = -0.0001
    dimObj.ToleranceUpperLimit = 0.005
    
    ThisDrawing.Application.ZoomAll

    ' Store old tolerance value as default for input box
    oldTolerance = dimObj.TolerancePrecision
    
    ' Allow the user to change the precision for the dimension tolerance
    newTolerance = InputBox("Enter a new tolerance precision for the dimension.  The value must range from 0 to 8.", "Dimension Tolerance Precision", oldTolerance)
    
    Select Case newTolerance
        Case 0: newTolerance = acDimPrecisionZero
        Case 1: newTolerance = acDimPrecisionOne
        Case 2: newTolerance = acDimPrecisionTwo
        Case 3: newTolerance = acDimPrecisionThree
        Case 4: newTolerance = acDimPrecisionFour
        Case 5: newTolerance = acDimPrecisionFive
        Case 6: newTolerance = acDimPrecisionSix
        Case 7: newTolerance = acDimPrecisionSeven
        Case 8: newTolerance = acDimPrecisionEight
        Case Else
            MsgBox "The tolerance precision has not been changed."
            Exit Sub
    End Select
    
    dimObj.TolerancePrecision = newTolerance   ' Commit changes to tolerance precision
    
    ThisDrawing.Regen acAllViewports
    
    ' Read back and display the dimension tolerance precision
    newTolerance = dimObj.TolerancePrecision
    MsgBox "The tolerance precision has been set to " & newTolerance & " decimal places"
End Sub


Sub Example_ToleranceSuppressLeadingZeros()
   ' This example creates an aligned dimension in model space and
   ' uses ToleranceSuppressLeadingZeros to toggle the display of leading zeros
   ' in the dimension tolerance display

    Dim dimObj As AcadDimAligned
    Dim point1(0 To 2) As Double, point2(0 To 2) As Double
    Dim location(0 To 2) As Double
    
    ' Define the dimension
    point1(0) = 5: point1(1) = 5: point1(2) = 0
    point2(0) = 5.01: point2(1) = 5: point2(2) = 0
    location(0) = 5: location(1) = 7: location(2) = 0
    
    ' Create an aligned dimension object in model space
    Set dimObj = ThisDrawing.ModelSpace.AddDimAligned(point1, point2, location)
    
    ' Enable and setup tolerance display
    dimObj.ToleranceDisplay = acTolSymmetrical
    dimObj.ToleranceLowerLimit = -0.0001: dimObj.ToleranceUpperLimit = 0.005
    
    ThisDrawing.Application.ZoomAll
    
Toggle:
    Select Case MsgBox("Press OK to toggle the display of leading zeros in the dimension tolerance", vbOKCancel)
        Case vbOK
            ' Toggle the display of leading zeros for the dimension tolerance value
            dimObj.ToleranceSuppressLeadingZeros = Not (dimObj.ToleranceSuppressLeadingZeros)
            ThisDrawing.Regen acAllViewports
        
        Case vbCancel
            Exit Sub
    End Select
    
    GoTo Toggle
End Sub

Sub Example_ToleranceSuppressTrailingZeros()
   ' This example creates an aligned dimension in model space and
   ' uses ToleranceSuppressTrailingZeros to toggle the display of trailing zeros
   ' in the dimension tolerance display

    Dim dimObj As AcadDimAligned
    Dim point1(0 To 2) As Double, point2(0 To 2) As Double
    Dim location(0 To 2) As Double
    
    ' Define the dimension
    point1(0) = 5: point1(1) = 5: point1(2) = 0
    point2(0) = 5.01: point2(1) = 5: point2(2) = 0
    location(0) = 5: location(1) = 7: location(2) = 0
    
    ' Create an aligned dimension object in model space
    Set dimObj = ThisDrawing.ModelSpace.AddDimAligned(point1, point2, location)
    
    ' Enable and setup tolerance display
    dimObj.ToleranceDisplay = acTolSymmetrical
    dimObj.ToleranceLowerLimit = -0.0001: dimObj.ToleranceUpperLimit = 0.005
    
    ThisDrawing.Application.ZoomAll
    
Toggle:
    Select Case MsgBox("Press OK to toggle the display of trailing zeros in the dimension tolerance", vbOKCancel)
        Case vbOK
            ' Toggle the display of trailing zeros for the dimension tolerance value
            dimObj.ToleranceSuppressTrailingZeros = Not (dimObj.ToleranceSuppressTrailingZeros)
            ThisDrawing.Regen acAllViewports
        
        Case vbCancel
            Exit Sub
    End Select
    
    GoTo Toggle
End Sub
Sub Example_ToleranceSuppressZeroFeet()
   ' This example creates an aligned dimension in model space and
   ' uses ToleranceSuppressZeroFeet to toggle the display of zeros feet
   ' in the dimension tolerance display

    Dim dimObj As AcadDimAligned
    Dim point1(0 To 2) As Double, point2(0 To 2) As Double
    Dim location(0 To 2) As Double
    
    ' Define the dimension
    point1(0) = 5: point1(1) = 5: point1(2) = 0
    point2(0) = 6.01: point2(1) = 5: point2(2) = 0
    location(0) = 5: location(1) = 8: location(2) = 0
    
    ' Create an aligned dimension object in model space
    Set dimObj = ThisDrawing.ModelSpace.AddDimAligned(point1, point2, location)
    dimObj.UnitsFormat = acDimLArchitectural
    
    ' Enable and setup tolerance display
    dimObj.ToleranceDisplay = acTolLimits
    dimObj.ToleranceLowerLimit = -0.0001: dimObj.ToleranceUpperLimit = 0.0001
    
    ZoomAll
    
Toggle:
    Select Case MsgBox("Press OK to toggle the display of zero feet in the dimension tolerance", vbOKCancel)
        Case vbOK
            ' Toggle the display of zero feet for the dimension tolerance value
            dimObj.ToleranceSuppressZeroFeet = Not (dimObj.ToleranceSuppressZeroFeet)
            ThisDrawing.Regen acAllViewports
        
        Case vbCancel
            Exit Sub
    End Select
    
    GoTo Toggle
End Sub
Sub Example_ToleranceSuppressZeroInches()
   ' This example creates an aligned dimension in model space and
   ' uses ToleranceSuppressZeroInches to toggle the display of zeros inches
   ' in the dimension tolerance display

    Dim dimObj As AcadDimAligned
    Dim point1(0 To 2) As Double, point2(0 To 2) As Double
    Dim location(0 To 2) As Double
    
    ' Define the dimension
    point1(0) = 5: point1(1) = 5: point1(2) = 0
    point2(0) = 6.01: point2(1) = 5: point2(2) = 0
    location(0) = 5: location(1) = 8: location(2) = 0
    
    ' Create an aligned dimension object in model space
    Set dimObj = ThisDrawing.ModelSpace.AddDimAligned(point1, point2, location)
    dimObj.UnitsFormat = acDimLArchitectural
    
    ' Enable and setup tolerance display
    dimObj.ToleranceDisplay = acTolLimits
    dimObj.ToleranceLowerLimit = -95#: dimObj.ToleranceUpperLimit = 95#
    
    ZoomAll
    
Toggle:
    Select Case MsgBox("Press OK to toggle the display of zero inches in the dimension tolerance", vbOKCancel)
        Case vbOK
            ' Toggle the display of zero inches for the dimension tolerance value
            dimObj.ToleranceSuppressZeroInches = Not (dimObj.ToleranceSuppressZeroInches)
            ThisDrawing.Regen acAllViewports
        
        Case vbCancel
            Exit Sub
    End Select
    
    GoTo Toggle
End Sub
Sub Example_VerticalTextPosition()
    ' This example creates an aligned dimension in model space
    ' and cycles the dimension text through a couple of different
    ' vertical alignments
    
    Dim dimObj As AcadDimAligned
    Dim point1(0 To 2) As Double, point2(0 To 2) As Double
    Dim location(0 To 2) As Double
    Dim CurrentValue As String
    
    ' Define the dimension
    point1(0) = 5: point1(1) = 5: point1(2) = 0
    point2(0) = 9: point2(1) = 5: point2(2) = 0
    location(0) = 5: location(1) = 7: location(2) = 0
    
    ' Create an aligned dimension object in model space
    Set dimObj = ThisDrawing.ModelSpace.AddDimAligned(point1, point2, location)
    ThisDrawing.Application.ZoomAll

    ' Read and display current text position
    Select Case dimObj.VerticalTextPosition
        Case acVertCentered:    CurrentValue = "centered"
        Case acAbove:           CurrentValue = "above"
        Case acOutside:         CurrentValue = "outside"
        Case acJIS:             CurrentValue = "to Japanesee industrial standards"
    End Select

    MsgBox "The vertical position of the dimension is: " & CurrentValue

    ' Change the position of the dimension text to be above the extesnion lines
    dimObj.VerticalTextPosition = acAbove
    ThisDrawing.Regen acAllViewports
    MsgBox "Dimension text is now aligned above extension lines"
   
    ' Change the position of the dimension text to be centered with the extension lines
    dimObj.VerticalTextPosition = acVertCentered
    ThisDrawing.Regen acAllViewports
    MsgBox "Dimension text is now centered with the extension lines"

End Sub

Sub Example_SendCommand()
   ' This example sends a command to the AutoCAD commandline
   ' of a particular drawing for evaluation
   
   ' We will create a Circle in the active drawing and will
   ' zoom to display the entire circle
   ThisDrawing.SendCommand "_Circle" & vbCr & "2,2,0" & vbCr & "4" & vbCr
   ThisDrawing.SendCommand "_zoom" & vbCr & "a" & vbCr
   
   ' Refresh view
   ThisDrawing.Regen acAllViewports
   
   MsgBox "A circle command has been sent to the command line of the current drawing."
End Sub

Sub Example_VBE()
    ' This example taps into the VBA IDE extensibility model to dynamically
    ' create a VBA procedure.  After running this example jump to the first line of code
    ' in the VBA IDE code window (This Window) and notice that a new subroutine was created.
    '
    ' * Note: Don't forget to remove the new routine before continuing

    Dim VBEModel As Object
    Dim newRoutine As String
    
    Set VBEModel = VBE  ' Get VBE object
    
    ' Define new subroutine to be added.  This could be created dynamically from user feedback.
    newRoutine = "Sub Dynamic_Procedure()" & vbCrLf
    newRoutine = newRoutine & vbTab & "MsgBox ""Isn't this cool!""" & vbCrLf
    newRoutine = newRoutine & "End Sub" & vbCrLf
    
    ' Insert new script at the top of this script
    VBEModel.CodePanes(1).CodeModule.InsertLines 1, newRoutine
    
    MsgBox "We just added a new subroutine to the top of the current VBA script called Dynamic_Procedure!"
End Sub

Sub Example_WindowState()
    ' This example reads and displays the current window state of the AutoCAD application.

    Dim CurrentState As String
    
    ' Use the "WindowState" variable to determine the window state of AutoCAD
    Select Case WindowState
        Case acMin: CurrentState = "Minimized"
        Case acMax: CurrentState = "Maximized"
        Case acNorm: CurrentState = "Normal Size"
    End Select

    ' Display window state
    MsgBox "AutoCAD is now: " & CurrentState
End Sub

Sub Example_LoadDVB()
    ' This example loads a DVB file into AutoCAD the VBA system and runs a macro
    ' contained in the file using the RunMacro method.
    '
    ' For this example we will use one of the sample files installed
    ' with the system, so the filename used in this example may
    ' have to be modified for this example to work.
    '
    ' * Note: If the he drawline DVB is already open, there will be an error
    ' when trying to unload the drawline DVB.

    Dim FileName As String
    
    FileName = "c:\program files\Acad2000\sample\vba\drawline.dvb"
    
    ' Load a sample VBA project DVB file
    LoadDVB FileName
    
    ' Run the drawline sample macro
    RunMacro "Module1.Drawline"
    
    ' Unload the drawline VBA project DVB file now that we are done
    UnloadDVB FileName
    
    MsgBox "We just loaded, ran, and unloaded a VBA sample from code!"
End Sub

Sub Example_UnloadDVB()
    ' This example loads a DVB file into AutoCAD the VBA system and runs a macro
    ' contained in the file using the RunMacro method.
    '
    ' For this example we will use one of the sample files installed
    ' with the system, so the filename used in this example may
    ' have to be modified for this example to work.
    '
    ' * Note: If the he drawline DVB is already open, there will be an error
    ' when trying to unload the drawline DVB.

    Dim FileName As String
    
    FileName = "c:\program files\Acad2000\sample\vba\drawline.dvb"
    
    ' Load a sample VBA project DVB file
    LoadDVB FileName
    
    ' Run the drawline sample macro
    RunMacro "Module1.Drawline"
    
    ' Unload the drawline VBA project DVB file now that we are done
    UnloadDVB FileName
    
    MsgBox "We just loaded, ran, and unloaded a VBA sample from code!"
End Sub

Sub Example_RunMacro()
    ' This example loads a DVB file into AutoCAD the VBA system and runs a macro
    ' contained in the file using the RunMacro method.
    '
    ' For this example we will use one of the sample files installed
    ' with the system, so the filename used in this example may
    ' have to be modified for this example to work.
    '
    ' * Note: If the he drawline DVB is already open, there will be an error
    ' when trying to unload the drawline DVB.

    Dim FileName As String
    
    FileName = "c:\program files\Acad2000\sample\vba\drawline.dvb"
    
    ' Load a sample VBA project DVB file
    LoadDVB FileName
    
    ' Run the drawline sample macro
    RunMacro "Module1.Drawline"
    
    ' Unload the drawline VBA project DVB file now that we are done
    UnloadDVB FileName
    
    MsgBox "We just loaded, ran, and unloaded a VBA sample from code!"

End Sub

Sub Example_Clipped()
    ' This example scans the current drawing paper space Viewports
    ' and displays whether or not any of the PViewports are clipped.
    
    Dim pviewportObj As Object
    Dim msg As String, ClippedState As String
    
    ' Make sure this drawing contains paper space viewports before we continue
    If ThisDrawing.PaperSpace.count = 0 Then
        MsgBox "There are no paper space viewports in the current drawing."
        Exit Sub
    End If
    
    ' Go through each PViewport object in the drawing paper space
    ' and determine if the PViewport is clipped or not
    
    For Each pviewportObj In ThisDrawing.PaperSpace
        
        ' Determine if this is a PViewport
        If TypeName(pviewportObj) = "IAcadPViewport" Then
            
            ' Determine if this PViewport is clipped
            ClippedState = IIf(pviewportObj.Clipped, " is clipped", " is not clipped")
            msg = msg & "PViewport ID " & pviewportObj.objectID & ClippedState & vbCrLf
        
        End If
    
    Next

    ' Display clipped state of paper space Viewports
    MsgBox msg
End Sub

Sub Example_DisplayLocked()
    ' This example scans the current drawing paper space Viewports
    ' and displays whether or not any of the PViewports are locked.
    
    Dim pviewportObj As Object
    Dim msg As String, ClippedState As String
   
    ' Make sure this drawing contains paper space viewports before we continue
    If ThisDrawing.PaperSpace.count = 0 Then
        MsgBox "There are no paper space viewports in the current drawing."
        Exit Sub
    End If
    
    ' Go through each PViewport object in the drawing paper space
    ' and determine if the PViewport is locked or not
    
    For Each pviewportObj In ThisDrawing.PaperSpace
        
        ' Determine if this is a PViewport
        If TypeName(pviewportObj) = "IAcadPViewport" Then
            
            ' Determine if this PViewport is locked
            ClippedState = IIf(pviewportObj.Clipped, " is locked", " is not locked")
            msg = msg & "PViewport ID " & pviewportObj.objectID & ClippedState & vbCrLf
        
        End If
    
    Next

    ' Display locked state of paper space Viewports
    MsgBox msg
End Sub

Sub Example_AutoTrackingVecColor()
    ' This example reads and modifies the preference value which controls
    ' the color of the auto tracking vector. When finished, this example
    ' resets the preference value back to it's original value.
    
    Dim ACADPref As AcadPreferencesDisplay
    Dim originalValue As Variant, newValue As Variant
    
    ' Get the display preferences object
    Set ACADPref = ThisDrawing.Application.preferences.DISPLAY
    
    ' Read and display the original value
    originalValue = ACADPref.AutoTrackingVecColor
    MsgBox "The AutoTrackingVecColor preference is: " & originalValue

    ' Modify the AutoTrackingVecColor preference by making it red
    ACADPref.AutoTrackingVecColor = vbRed
    newValue = ACADPref.AutoTrackingVecColor
    MsgBox "The AutoTrackingVecColor preference has been set to: " & newValue

    ' Reset the preference back to it's original value
    '
    ' * Note: Comment out this last section to leave the change to
    '         this preference in effect
    ACADPref.AutoTrackingVecColor = originalValue
    MsgBox "The AutoTrackingVecColor preference was reset back to: " & originalValue
End Sub

Sub Example_DisplayLayoutTabs()
    ' This example reads and modifies the preference value which controls
    ' the display of the Model and Layout tabs. When finished, this example
    ' resets the preference value back to it's original value.
    
    Dim ACADPref As AcadPreferencesDisplay
    Dim originalValue As Variant, newValue As Variant
    
    ' Get the display preferences object
    Set ACADPref = ThisDrawing.Application.preferences.DISPLAY
    
    ' Read and display the original value
    originalValue = ACADPref.DisplayLayoutTabs
    MsgBox "The DisplayLayoutTabs preference is set to: " & originalValue

    ' Modify the DisplayLayoutTabs preference by toggling the value
    ACADPref.DisplayLayoutTabs = Not (originalValue)
    newValue = ACADPref.DisplayLayoutTabs
    MsgBox "The DisplayLayoutTabs preference has been set to: " & newValue

    ' Reset the preference back to it's original value
    '
    ' * Note: Comment out this last section to leave the change to
    '         this preference in effect
    ACADPref.DisplayLayoutTabs = originalValue
    MsgBox "The DisplayLayoutTabs preference was reset back to: " & originalValue
End Sub

Sub Example_ImageFrameHighlight()
    ' This example reads and modifies the preference value which controls
    ' the display of raster images during selection. When finished, this example
    ' resets the preference value back to it's original value.
    
    Dim ACADPref As AcadPreferencesDisplay
    Dim originalValue As Variant, newValue As Variant
    
    ' Get the display preferences object
    Set ACADPref = ThisDrawing.Application.preferences.DISPLAY
    
    ' Read and display the original value
    originalValue = ACADPref.ImageFrameHighlight
    MsgBox "The ImageFrameHighlight preference is set to: " & originalValue

    ' Modify the ImageFrameHighlight preference by toggling the value
    ACADPref.ImageFrameHighlight = Not (originalValue)
    newValue = ACADPref.ImageFrameHighlight
    MsgBox "The ImageFrameHighlight preference has been set to: " & newValue

    ' Reset the preference back to it's original value
    '
    ' * Note: Comment out this last section to leave the change to
    '         this preference in effect
    ACADPref.ImageFrameHighlight = originalValue
    MsgBox "The ImageFrameHighlight preference was reset back to: " & originalValue
End Sub

Sub Example_LayoutCreateViewport()
    ' This example reads and modifies the preference value which controls
    ' the automatic creation of a viewport for new layouts. When finished, this example
    ' resets the preference value back to it's original value.
    
    Dim ACADPref As AcadPreferencesDisplay
    Dim originalValue As Variant, newValue As Variant
    
    ' Get the display preferences object
    Set ACADPref = ThisDrawing.Application.preferences.DISPLAY
    
    ' Read and display the original value
    originalValue = ACADPref.LayoutCreateViewport
    MsgBox "The LayoutCreateViewport preference is set to: " & originalValue

    ' Modify the LayoutCreateViewport preference by toggling the value
    ACADPref.LayoutCreateViewport = Not (originalValue)
    newValue = ACADPref.LayoutCreateViewport
    MsgBox "The LayoutCreateViewport preference has been set to: " & newValue

    ' Reset the preference back to it's original value
    '
    ' * Note: Comment out this last section to leave the change to
    '         this preference in effect
    ACADPref.LayoutCreateViewport = originalValue
    MsgBox "The LayoutCreateViewport preference was reset back to: " & originalValue
End Sub

Sub Example_LayoutCrosshairColor()
    ' This example reads and modifies the preference value which controls
    ' the color of the crosshairs and text for paper space layouts.
    ' When finished, this example resets the preference value back to
    ' it's original value.
    
    Dim ACADPref As AcadPreferencesDisplay
    Dim originalValue As Variant, newValue As Variant
    
    ' Get the display preferences object
    Set ACADPref = ThisDrawing.Application.preferences.DISPLAY
    
    ' Switch to paper space where we can view this change
    ThisDrawing.ActiveSpace = acPaperSpace
   
    ' Read and display the original value
    originalValue = ACADPref.LayoutCrosshairColor
    MsgBox "The LayoutCrosshairColor preference is: " & originalValue

    ' Modify the LayoutCrosshairColor preference by making it red
    ACADPref.LayoutCrosshairColor = vbRed
    newValue = ACADPref.LayoutCrosshairColor
    ThisDrawing.Regen acAllViewports
    
    MsgBox "The LayoutCrosshairColor preference has been set to: " & newValue

    ' Reset the preference back to it's original value
    '
    ' * Note: Comment out this last section to leave the change to
    '         this preference in effect
    ACADPref.LayoutCrosshairColor = originalValue
    ThisDrawing.Regen acAllViewports
    
    MsgBox "The LayoutCrosshairColor preference was reset back to: " & originalValue
End Sub

Sub Example_LayoutDisplayMargins()
    ' This example reads and modifies the preference value which controls
    ' the display of margins in layouts. When finished, this example
    ' resets the preference value back to it's original value.
    
    Dim ACADPref As AcadPreferencesDisplay
    Dim originalValue As Variant, newValue As Variant
    
    ' Get the display preferences object
    Set ACADPref = ThisDrawing.Application.preferences.DISPLAY
    
    ' Switch to paper space where we can view this change
    ThisDrawing.ActiveSpace = acPaperSpace
    
    ' Read and display the original value
    originalValue = ACADPref.LayoutDisplayMargins
    MsgBox "The LayoutDisplayMargins preference is set to: " & originalValue

    ' Modify the LayoutDisplayMargins preference by toggling the value
    ACADPref.LayoutDisplayMargins = Not (originalValue)
    newValue = ACADPref.LayoutDisplayMargins
    ThisDrawing.Regen acAllViewports
    
    MsgBox "The LayoutDisplayMargins preference has been set to: " & newValue

    ' Reset the preference back to it's original value
    '
    ' * Note: Comment out this last section to leave the change to
    '         this preference in effect
    ACADPref.LayoutDisplayMargins = originalValue
    ThisDrawing.Regen acAllViewports
    
    MsgBox "The LayoutDisplayMargins preference was reset back to: " & originalValue
End Sub

Sub Example_LayoutDisplayPaper()
    ' This example reads and modifies the preference value which controls
    ' the display of the paper background in layouts. When finished, this example
    ' resets the preference value back to it's original value.
    
    Dim ACADPref As AcadPreferencesDisplay
    Dim originalValue As Variant, newValue As Variant
    
    ' Get the display preferences object
    Set ACADPref = ThisDrawing.Application.preferences.DISPLAY
    
    ' Switch to paper space where we can view this change
    ThisDrawing.ActiveSpace = acPaperSpace
    
    ' Read and display the original value
    originalValue = ACADPref.LayoutDisplayPaper
    MsgBox "The LayoutDisplayPaper preference is set to: " & originalValue

    ' Modify the LayoutDisplayPaper preference by toggling the value
    ACADPref.LayoutDisplayPaper = Not (originalValue)
    newValue = ACADPref.LayoutDisplayPaper
    ThisDrawing.Regen acAllViewports

    MsgBox "The LayoutDisplayPaper preference has been set to: " & newValue

    ' Reset the preference back to it's original value
    '
    ' * Note: Comment out this last section to leave the change to
    '         this preference in effect
    ACADPref.LayoutDisplayPaper = originalValue
    ThisDrawing.Regen acAllViewports
    
    MsgBox "The LayoutDisplayPaper preference was reset back to: " & originalValue
End Sub

Sub Example_LayoutDisplayPaperShadow()
    ' This example reads and modifies the preference value which controls
    ' the display of the paper background shadow in layouts. When finished, this example
    ' resets the preference value back to it's original value.
    
    Dim ACADPref As AcadPreferencesDisplay
    Dim originalValue As Variant, newValue As Variant
    
    ' Get the display preferences object
    Set ACADPref = ThisDrawing.Application.preferences.DISPLAY
    
    ' Switch to paper space where we can view this change
    ThisDrawing.ActiveSpace = acPaperSpace
    
    ' Read and display the original value
    originalValue = ACADPref.LayoutDisplayPaperShadow
    MsgBox "The LayoutDisplayPaperShadow preference is set to: " & originalValue

    ' Modify the LayoutDisplayPaperShadow preference by toggling the value
    ACADPref.LayoutDisplayPaperShadow = Not (originalValue)
    newValue = ACADPref.LayoutDisplayPaperShadow
    ThisDrawing.Regen acAllViewports
        
    MsgBox "The LayoutDisplayPaperShadow preference has been set to: " & newValue

    ' Reset the preference back to it's original value
    '
    ' * Note: Comment out this last section to leave the change to
    '         this preference in effect
    ACADPref.LayoutDisplayPaperShadow = originalValue
    ThisDrawing.Regen acAllViewports
    
    MsgBox "The LayoutDisplayPaperShadow preference was reset back to: " & originalValue
End Sub

Sub Example_LayoutShowPlotSetup()
    ' This example reads and modifies the preference value which controls
    ' the display of the Plot Setup dialog when a new layout is created.
    ' When finished, this example resets the preference value back to
    ' it's original value.
    
    Dim ACADPref As AcadPreferencesDisplay
    Dim originalValue As Variant, newValue As Variant
    
    ' Get the display preferences object
    Set ACADPref = ThisDrawing.Application.preferences.DISPLAY
    
    ' Read and display the original value
    originalValue = ACADPref.LayoutShowPlotSetup
    MsgBox "The LayoutShowPlotSetup preference is set to: " & originalValue

    ' Modify the LayoutShowPlotSetup preference by toggling the value
    ACADPref.LayoutShowPlotSetup = Not (originalValue)
    newValue = ACADPref.LayoutShowPlotSetup
    MsgBox "The LayoutShowPlotSetup preference has been set to: " & newValue

    ' Reset the preference back to it's original value
    '
    ' * Note: Comment out this last section to leave the change to
    '         this preference in effect
    ACADPref.LayoutShowPlotSetup = originalValue
    MsgBox "The LayoutShowPlotSetup preference was reset back to: " & originalValue
End Sub

Sub Example_TrueColorImages()
    ' This example reads and modifies the preference value which determines
    ' if raster and render images are displayed at true color or palletized color.
    ' When finished, this example resets the preference value back to
    ' it's original value.
    '
    ' This example uses the "watch.jpg" found in the sample
    ' directory. If you do not have this image, or it is located
    ' in a different directory, insert a valid path and filename
    ' for the imageName variable below.
    
    Dim ACADPref As AcadPreferencesDisplay
    Dim originalValue As Variant, newValue As Variant
    Dim insertionPoint(0 To 2) As Double
    Dim scalefactor As Double, rotationAngle As Double
    Dim imageName As String
    Dim rasterObj As AcadRasterImage
    
    imageName = "c:\program files\Autocad\sample\watch.jpg"
    
    ' Define Raster object
    insertionPoint(0) = 5: insertionPoint(1) = 5: insertionPoint(2) = 0
    scalefactor = 5#: rotationAngle = 0
    
    On Error GoTo ERRORTRAP
    
    ' Loads a raster image into model space
    Set rasterObj = ThisDrawing.ModelSpace.AddRaster(imageName, insertionPoint, scalefactor, rotationAngle)
    ThisDrawing.Application.ZoomAll
    
    ' Get the display preferences object
    Set ACADPref = ThisDrawing.Application.preferences.DISPLAY
    
    ' Read and display the original value
    originalValue = ACADPref.TrueColorImages
    MsgBox "The TrueColorImages preference is set to: " & originalValue

    ' Modify the TrueColorImages preference by toggling the value
    ACADPref.TrueColorImages = Not (originalValue)
    newValue = ACADPref.TrueColorImages
    ThisDrawing.Regen acAllViewports
    
    MsgBox "The TrueColorImages preference has been set to: " & newValue

    ' Reset the preference back to it's original value
    '
    ' * Note: Comment out this last section to leave the change to
    '         this preference in effect
    ACADPref.TrueColorImages = originalValue
    ThisDrawing.Regen acAllViewports
    
    MsgBox "The TrueColorImages preference was reset back to: " & originalValue

    Exit Sub
    
    ' If we ran into an error (most likely a problem with the file path),
    ' then display error message
ERRORTRAP:
    If Err.Description <> "" Then
        MsgBox Err.Description
    End If
End Sub

Sub Example_AlignmentPointAcquisition()
    ' This example reads and modifies the preference value which controls
    ' how AutoAlignment points are acquired. When finished, this example resets
    ' the preference value back to it's original value.
    
    Dim ACADPref As AcadPreferencesDrafting
    Dim originalValue As Variant, newValue As Variant
    
    ' Get the drafting preferences object
    Set ACADPref = ThisDrawing.Application.preferences.Drafting
    
    ' Read and display the original value
    originalValue = ACADPref.AlignmentPointAcquisition
    MsgBox "The AlignmentPointAcquisition preference is: " & originalValue

    ' Toggle and display the AlignmentPointAcquisition preference
    If ACADPref.AlignmentPointAcquisition = acAlignPntAcquisitionAutomatic Then
        ACADPref.AlignmentPointAcquisition = acAlignPntAcquisitionShiftToAcquire
    Else
        ACADPref.AlignmentPointAcquisition = acAlignPntAcquisitionAutomatic
    End If
    
    newValue = ACADPref.AlignmentPointAcquisition
    MsgBox "The AlignmentPointAcquisition preference has been set to: " & newValue

    ' Reset the preference back to it's original value
    '
    ' * Note: Comment out this last section to leave the change to
    '         this preference in effect
    ACADPref.AlignmentPointAcquisition = originalValue
    MsgBox "The AlignmentPointAcquisition preference was reset back to: " & originalValue
End Sub

Sub Example_AutoSnapAperture()
    ' This example reads and modifies the preference value which controls
    ' the display of the AutoSnap aperture.
    ' When finished, this example resets the preference value back to
    ' it's original value.
    
    Dim ACADPref As AcadPreferencesDrafting
    Dim originalValue As Variant, newValue As Variant
    
    ' Get the drafting preferences object
    Set ACADPref = ThisDrawing.Application.preferences.Drafting
    
    ' Read and display the original value
    originalValue = ACADPref.AutoSnapAperture
    MsgBox "The AutoSnapAperture preference is set to: " & originalValue

    ' Modify the AutoSnapAperture preference by toggling the value
    ACADPref.AutoSnapAperture = Not (originalValue)
    newValue = ACADPref.AutoSnapAperture
    MsgBox "The AutoSnapAperture preference has been set to: " & newValue

    ' Reset the preference back to it's original value
    '
    ' * Note: Comment out this last section to leave the change to
    '         this preference in effect
    ACADPref.AutoSnapAperture = originalValue
    MsgBox "The AutoSnapAperture preference was reset back to: " & originalValue
End Sub

Sub Example_AutoSnapApertureSize()
    ' This example reads and modifies the preference value which controls
    ' the size of the AutoSnap aperture. When finished, this example resets
    ' the preference value back to it's original value.
    
    Dim ACADPref As AcadPreferencesDrafting
    Dim originalValue As Variant, newValue As Variant
    
    ' Get the drafting preferences object
    Set ACADPref = ThisDrawing.Application.preferences.Drafting
    
    ' Read and display the original value
    originalValue = ACADPref.AutoSnapApertureSize
    MsgBox "The AutoSnapApertureSize preference is: " & originalValue

    ' Modify the AutoSnapApertureSize preference by setting it to 25
    ACADPref.AutoSnapApertureSize = 25
    newValue = ACADPref.AutoSnapApertureSize
    MsgBox "The AutoSnapApertureSize preference has been set to: " & newValue

    ' Reset the preference back to it's original value
    '
    ' * Note: Comment out this last section to leave the change to
    '         this preference in effect
    ACADPref.AutoSnapApertureSize = originalValue
    MsgBox "The AutoSnapApertureSize preference was reset back to: " & originalValue
End Sub

Sub Example_AutoSnapMagnet()
    ' This example reads and modifies the preference value which controls
    ' the AutoSnap magnet.  When finished, this example resets the
    ' preference value back to it's original value.
    
    Dim ACADPref As AcadPreferencesDrafting
    Dim originalValue As Variant, newValue As Variant
    
    ' Get the drafting preferences object
    Set ACADPref = ThisDrawing.Application.preferences.Drafting
    
    ' Read and display the original value
    originalValue = ACADPref.AutoSnapMagnet
    MsgBox "The AutoSnapMagnet preference is set to: " & originalValue

    ' Modify the AutoSnapMagnet preference by toggling the value
    ACADPref.AutoSnapMagnet = Not (originalValue)
    newValue = ACADPref.AutoSnapMagnet
    MsgBox "The AutoSnapMagnet preference has been set to: " & newValue

    ' Reset the preference back to it's original value
    '
    ' * Note: Comment out this last section to leave the change to
    '         this preference in effect
    ACADPref.AutoSnapMagnet = originalValue
    MsgBox "The AutoSnapMagnet preference was reset back to: " & originalValue
End Sub

Sub Example_AutoSnapMarker()
    ' This example reads and modifies the preference value which controls
    ' the AutoSnap marker.  When finished, this example resets the
    ' preference value back to it's original value.
    
    Dim ACADPref As AcadPreferencesDrafting
    Dim originalValue As Variant, newValue As Variant
    
    ' Get the drafting preferences object
    Set ACADPref = ThisDrawing.Application.preferences.Drafting
    
    ' Read and display the original value
    originalValue = ACADPref.AutoSnapMarker
    MsgBox "The AutoSnapMarker preference is set to: " & originalValue

    ' Modify the AutoSnapMarker preference by toggling the value
    ACADPref.AutoSnapMarker = Not (originalValue)
    newValue = ACADPref.AutoSnapMarker
    MsgBox "The AutoSnapMarker preference has been set to: " & newValue

    ' Reset the preference back to it's original value
    '
    ' * Note: Comment out this last section to leave the change to
    '         this preference in effect
    ACADPref.AutoSnapMarker = originalValue
    MsgBox "The AutoSnapMarker preference was reset back to: " & originalValue
End Sub

Sub Example_AutoSnapMarkerColor()
    ' This example reads and modifies the preference value which controls
    ' the color of the AutoSnap marker. When finished, this example resets
    ' the preference value back to it's original value.
    
    Dim ACADPref As AcadPreferencesDrafting
    Dim originalValue As Variant, newValue As Variant
    
    ' Get the drafting preferences object
    Set ACADPref = ThisDrawing.Application.preferences.Drafting
    
    ' Read and display the original value
    originalValue = ACADPref.AutoSnapMarkerColor
    MsgBox "The AutoSnapMarkerColor preference is: " & originalValue

    ' Modify the AutoSnapMarkerColor preference by setting it to red
    ACADPref.AutoSnapMarkerColor = acRed
    newValue = ACADPref.AutoSnapMarkerColor
    MsgBox "The AutoSnapMarkerColor preference has been set to: " & newValue

    ' Reset the preference back to it's original value
    '
    ' * Note: Comment out this last section to leave the change to
    '         this preference in effect
    ACADPref.AutoSnapMarkerColor = originalValue
    MsgBox "The AutoSnapMarkerColor preference was reset back to: " & originalValue
End Sub

Sub Example_AutoSnapMarkerSize()
    ' This example reads and modifies the preference value which controls
    ' the size of the AutoSnap marker. When finished, this example resets
    ' the preference value back to it's original value.
    
    Dim ACADPref As AcadPreferencesDrafting
    Dim originalValue As Variant, newValue As Variant
    
    ' Get the drafting preferences object
    Set ACADPref = ThisDrawing.Application.preferences.Drafting
    
    ' Read and display the original value
    originalValue = ACADPref.AutoSnapMarkerSize
    MsgBox "The AutoSnapMarkerSize preference is: " & originalValue

    ' Modify the AutoSnapMarkerSize preference by setting it to 10
    ACADPref.AutoSnapMarkerSize = 10
    newValue = ACADPref.AutoSnapMarkerSize
    MsgBox "The AutoSnapMarkerSize preference has been set to: " & newValue

    ' Reset the preference back to it's original value
    '
    ' * Note: Comment out this last section to leave the change to
    '         this preference in effect
    ACADPref.AutoSnapMarkerSize = originalValue
    MsgBox "The AutoSnapMarkerSize preference was reset back to: " & originalValue
End Sub

Sub Example_AutoSnapToolTip()
    ' This example reads and modifies the preference value which controls
    ' the AutoSnap tooltips.  When finished, this example resets the
    ' preference value back to it's original value.
    
    Dim ACADPref As AcadPreferencesDrafting
    Dim originalValue As Variant, newValue As Variant
    
    ' Get the drafting preferences object
    Set ACADPref = ThisDrawing.Application.preferences.Drafting
    
    ' Read and display the original value
    originalValue = ACADPref.AutoSnapTooltip
    MsgBox "The AutoSnapToolTip preference is set to: " & originalValue

    ' Modify the AutoSnapToolTip preference by toggling the value
    ACADPref.AutoSnapTooltip = Not (originalValue)
    newValue = ACADPref.AutoSnapTooltip
    MsgBox "The AutoSnapToolTip preference has been set to: " & newValue

    ' Reset the preference back to it's original value
    '
    ' * Note: Comment out this last section to leave the change to
    '         this preference in effect
    ACADPref.AutoSnapTooltip = originalValue
    MsgBox "The AutoSnapToolTip preference was reset back to: " & originalValue
End Sub

Sub Example_AutoTrackToolTip()
    ' This example reads and modifies the preference value which controls
    ' the display of the AutoTrack tooltips.  When finished, this example resets the
    ' preference value back to it's original value.
    
    Dim ACADPref As AcadPreferencesDrafting
    Dim originalValue As Variant, newValue As Variant
    
    ' Get the drafting preferences object
    Set ACADPref = ThisDrawing.Application.preferences.Drafting
    
    ' Read and display the original value
    originalValue = ACADPref.AutoTrackTooltip
    MsgBox "The AutoTrackToolTip preference is set to: " & originalValue

    ' Modify the AutoTrackToolTip preference by toggling the value
    ACADPref.AutoTrackTooltip = Not (originalValue)
    newValue = ACADPref.AutoTrackTooltip
    MsgBox "The AutoTrackToolTip preference has been set to: " & newValue

    ' Reset the preference back to it's original value
    '
    ' * Note: Comment out this last section to leave the change to
    '         this preference in effect
    ACADPref.AutoTrackTooltip = originalValue
    MsgBox "The AutoTrackToolTip preference was reset back to: " & originalValue
End Sub

Sub Example_FullScreenTrackingVector()
    ' This example reads and modifies the preference value which controls
    ' the display of full screen tracking vectors.
    ' When finished, this example resets the preference value back to
    ' it's original value.
    
    Dim ACADPref As AcadPreferencesDrafting
    Dim originalValue As Variant, newValue As Variant
    
    ' Get the drafting preferences object
    Set ACADPref = ThisDrawing.Application.preferences.Drafting
    
    ' Read and display the original value
    originalValue = ACADPref.FullScreenTrackingVector
    MsgBox "The FullScreenTrackingVector preference is set to: " & originalValue

    ' Modify the FullScreenTrackingVector preference by toggling the value
    ACADPref.FullScreenTrackingVector = Not (originalValue)
    newValue = ACADPref.FullScreenTrackingVector
    MsgBox "The FullScreenTrackingVector preference has been set to: " & newValue

    ' Reset the preference back to it's original value
    '
    ' * Note: Comment out this last section to leave the change to
    '         this preference in effect
    ACADPref.FullScreenTrackingVector = originalValue
    MsgBox "The FullScreenTrackingVector preference was reset back to: " & originalValue
End Sub

Sub Example_PolarTrackingVector()
    ' This example reads and modifies the preference value which controls
    ' the display of polar tracking vectors.
    ' When finished, this example resets the preference value back to
    ' it's original value.
    
    Dim ACADPref As AcadPreferencesDrafting
    Dim originalValue As Variant, newValue As Variant
    
    ' Get the drafting preferences object
    Set ACADPref = ThisDrawing.Application.preferences.Drafting
    
    ' Read and display the original value
    originalValue = ACADPref.PolarTrackingVector
    MsgBox "The PolarTrackingVector preference is set to: " & originalValue

    ' Modify the PolarTrackingVector preference by toggling the value
    ACADPref.PolarTrackingVector = Not (originalValue)
    newValue = ACADPref.PolarTrackingVector
    MsgBox "The PolarTrackingVector preference has been set to: " & newValue

    ' Reset the preference back to it's original value
    '
    ' * Note: Comment out this last section to leave the change to
    '         this preference in effect
    ACADPref.PolarTrackingVector = originalValue
    MsgBox "The PolarTrackingVector preference was reset back to: " & originalValue
End Sub

Sub Example_ObjectARXPath()
    ' This example reads and modifies the preference value which controls
    ' the location for ObjectARX applications.
    ' When finished, this example resets the preference value back to
    ' it's original value.
    
    Dim ACADPref As AcadPreferencesFiles
    Dim originalValue As Variant, newValue As Variant
    
    ' Get the files preferences object
    Set ACADPref = ThisDrawing.Application.preferences.Files
    
    ' Read and display the original value
    originalValue = ACADPref.ObjectARXPath
    MsgBox "The ObjectARXPath preference is set to: " & originalValue

    ' Modify the ObjectARXPath preference by changing the path to "C:\"
    ACADPref.ObjectARXPath = "C:\"
    newValue = ACADPref.ObjectARXPath
    MsgBox "The ObjectARXPath preference has been set to: " & newValue

    ' Reset the preference back to it's original value
    '
    ' * Note: Comment out this last section to leave the change to
    '         this preference in effect
    ACADPref.ObjectARXPath = originalValue
    MsgBox "The ObjectARXPath preference was reset back to: " & originalValue
End Sub

Sub Example_PrinterConfigPath()
    ' This example reads and modifies the preference value which controls
    ' the location for printer configuration files.
    ' When finished, this example resets the preference value back to
    ' it's original value.
    
    Dim ACADPref As AcadPreferencesFiles
    Dim originalValue As Variant, newValue As Variant
    
    ' Get the files preferences object
    Set ACADPref = ThisDrawing.Application.preferences.Files
    
    ' Read and display the original value
    originalValue = ACADPref.PrinterConfigPath
    MsgBox "The PrinterConfigPath preference is set to: " & originalValue

    ' Modify the PrinterConfigPath preference by changing the path to "C:\"
    ACADPref.PrinterConfigPath = "C:\"
    newValue = ACADPref.PrinterConfigPath
    MsgBox "The PrinterConfigPath preference has been set to: " & newValue

    ' Reset the preference back to it's original value
    '
    ' * Note: Comment out this last section to leave the change to
    '         this preference in effect
    ACADPref.PrinterConfigPath = originalValue
    MsgBox "The PrinterConfigPath preference was reset back to: " & originalValue
End Sub

Sub Example_PrinterDescPath()
    ' This example reads and modifies the preference value which controls
    ' the location for printer description files.
    ' When finished, this example resets the preference value back to
    ' it's original value.
    
    Dim ACADPref As AcadPreferencesFiles
    Dim originalValue As Variant, newValue As Variant
    
    ' Get the files preferences object
    Set ACADPref = ThisDrawing.Application.preferences.Files
    
    ' Read and display the original value
    originalValue = ACADPref.PrinterDescPath
    MsgBox "The PrinterDescPath preference is set to: " & originalValue

    ' Modify the PrinterDescPath preference by changing the path to "C:\"
    ACADPref.PrinterDescPath = "C:\"
    newValue = ACADPref.PrinterDescPath
    MsgBox "The PrinterDescPath preference has been set to: " & newValue

    ' Reset the preference back to it's original value
    '
    ' * Note: Comment out this last section to leave the change to
    '         this preference in effect
    ACADPref.PrinterDescPath = originalValue
    MsgBox "The PrinterDescPath preference was reset back to: " & originalValue
End Sub

Sub Example_PrinterStyleSheetPath()
    ' This example reads and modifies the preference value which controls
    ' the location for printer style sheet files.
    ' When finished, this example resets the preference value back to
    ' it's original value.
    
    Dim ACADPref As AcadPreferencesFiles
    Dim originalValue As Variant, newValue As Variant
    
    ' Get the files preferences object
    Set ACADPref = ThisDrawing.Application.preferences.Files
    
    ' Read and display the original value
    originalValue = ACADPref.PrinterStyleSheetPath
    MsgBox "The PrinterStyleSheetPath preference is set to: " & originalValue

    ' Modify the PrinterStyleSheetPath preference by changing the path to "C:\"
    ACADPref.PrinterStyleSheetPath = "C:\"
    newValue = ACADPref.PrinterStyleSheetPath
    MsgBox "The PrinterStyleSheetPath preference has been set to: " & newValue

    ' Reset the preference back to it's original value
    '
    ' * Note: Comment out this last section to leave the change to
    '         this preference in effect
    ACADPref.PrinterStyleSheetPath = originalValue
    MsgBox "The PrinterStyleSheetPath preference was reset back to: " & originalValue
End Sub

Sub Example_WorkspacePath()
    ' This example reads and modifies the preference value which controls
    ' the path for the database workspace file.
    ' When finished, this example resets the preference value back to
    ' it's original value.
    
    Dim ACADPref As AcadPreferencesFiles
    Dim originalValue As Variant, newValue As Variant
    
    ' Get the files preferences object
    Set ACADPref = ThisDrawing.Application.preferences.Files
    
    ' Read and display the original value
    originalValue = ACADPref.WorkspacePath
    MsgBox "The WorkspacePath preference is set to: " & originalValue

    ' Modify the WorkspacePath preference by changing the path to "C:\"
    ACADPref.WorkspacePath = "C:\"
    newValue = ACADPref.WorkspacePath
    MsgBox "The WorkspacePath preference has been set to: " & newValue

    ' Reset the preference back to it's original value
    '
    ' * Note: Comment out this last section to leave the change to
    '         this preference in effect
    ACADPref.WorkspacePath = originalValue
    MsgBox "The WorkspacePath preference was reset back to: " & originalValue
End Sub


Sub Example_MRUNumber()
    ' This example reads the preference value which contains
    ' the number of most recently used files that appear in the File menu.
    
    Dim ACADPref As AcadPreferencesOpenSave
    Dim originalValue As Variant
    
    ' Get the OpenSave preferences object
    Set ACADPref = ThisDrawing.Application.preferences.OpenSave
    
    ' Read and display the preference value
    originalValue = ACADPref.MRUNumber
    MsgBox "The number of most recently used files that are shown is: " & originalValue

End Sub

Sub Example_SaveAsType()
    ' This example reads and modifies the preference value which controls
    ' the drawing type to save the drawing as.
    ' When finished, this example resets the preference value back to
    ' it's original value.
    
    Dim ACADPref As AcadPreferencesOpenSave
    Dim originalValue As Variant, DisplayValue As String
    
    ' Get the OpenSave preferences object
    Set ACADPref = ThisDrawing.Application.preferences.OpenSave
    
    ' Store current setting
    originalValue = ACADPref.SaveAsType
    
    ' Read and display the original value
    GoSub GETVALUE
    MsgBox "The SaveAsType preference is: " & DisplayValue

    ' Modify the SaveAsType preference by changing it to AutoCAD R14/LT97 DXF
    ACADPref.SaveAsType = acR14_dxf
    GoSub GETVALUE
    MsgBox "The SaveAsType preference has been set to: " & DisplayValue

    ' Reset the preference back to it's original value
    '
    ' * Note: Comment out this last section to leave the change to
    '         this preference in effect
    ACADPref.SaveAsType = originalValue
    
    GoSub GETVALUE
    MsgBox "The SaveAsType preference was reset back to: " & DisplayValue
    
    Exit Sub
    
GETVALUE:
    ' Convert the value of this setting to a meaningful text string
    DisplayValue = ACADPref.SaveAsType
    Select Case DisplayValue
        Case acR12_dxf:  DisplayValue = "AutoCAD R12/LT2 DXF (*.dxf)"
        Case acR13_dwg:  DisplayValue = "AutoCAD R13/LT95 DWG (*.dwg)"
        Case acR13_dxf:  DisplayValue = "AutoCAD R13/LT95 DXF (*.dxf)"
        Case acR14_dwg:  DisplayValue = "AutoCAD R14/LT97 DWG (*.dwg)"
        Case acR14_dxf:  DisplayValue = "AutoCAD R14/LT97 DXF (*.dxf)"
        Case acR15_dwg:  DisplayValue = "AutoCAD T DWG (*.dwg)"
        Case acR15_dxf:  DisplayValue = "AutoCAD T DXF (*.dxf)"
        Case acR15_Template: DisplayValue = "AutoCAD T Drawing Template File (*.dwt)"
        Case acNative:   DisplayValue = "Latest drawing release"
        Case acUnknown:  DisplayValue = "The drawing type is unknown"
    End Select
    
    Return
End Sub

Sub Example_DefaultOutputDevice()
    ' This example reads and modifies the preference value which controls
    ' the default output device for new layouts and model space.
    ' When finished, this example resets the preference value back to
    ' it's original value.
    
    Dim ACADPref As AcadPreferencesOutput
    Dim originalValue As Variant, newValue As Variant
    
    ' Get the output preferences object
    Set ACADPref = ThisDrawing.Application.preferences.Output
    
    ' Read and display the original value
    originalValue = ACADPref.DefaultOutputDevice
    MsgBox "The DefaultOutputDevice preference is: " & originalValue

    ' Modify the DefaultOutputDevice preference by changing it to "LOCALOUTPUT"
    ACADPref.DefaultOutputDevice = "LOCALOUTPUT"
    newValue = ACADPref.DefaultOutputDevice
    MsgBox "The DefaultOutputDevice preference has been set to: " & newValue

    ' Reset the preference back to it's original value
    '
    ' * Note: Comment out this last section to leave the change to
    '         this preference in effect
    ACADPref.DefaultOutputDevice = originalValue
    MsgBox "The DefaultOutputDevice preference was reset back to: " & originalValue
End Sub

Sub Example_DefaultPlotStyleForLayer()
    ' This example reads and modifies the preference value which controls
    ' the default plot style assigned to layers.
    ' When finished, this example resets the preference value back to
    ' it's original value.
    
    Dim ACADPref As AcadPreferencesOutput
    Dim originalValue As Variant, newValue As Variant
    
    ' Get the output preferences object
    Set ACADPref = ThisDrawing.Application.preferences.Output
    
    ' Read and display the original value
    originalValue = ACADPref.DefaultPlotStyleForLayer
    MsgBox "The DefaultPlotStyleForLayer preference is: " & originalValue

    ' Toggle and display the DefaultPlotStyleForLayer preference
    If ACADPref.DefaultPlotStyleForLayer = "ByBlock" Then
        ACADPref.DefaultPlotStyleForLayer = "Normal"
    Else
        ACADPref.DefaultPlotStyleForLayer = "ByBlock"
    End If

    newValue = ACADPref.DefaultPlotStyleForLayer
    MsgBox "The DefaultPlotStyleForLayer preference has been set to: " & newValue

    ' Reset the preference back to it's original value
    '
    ' * Note: Comment out this last section to leave the change to
    '         this preference in effect
    ACADPref.DefaultPlotStyleForLayer = originalValue
    MsgBox "The DefaultPlotStyleForLayer preference was reset back to: " & originalValue
End Sub

Sub Example_DefaultPlotStyleForObjects()
    ' This example reads and modifies the preference value which controls
    ' the default plot style name for newly created objects.
    ' When finished, this example resets the preference value back to
    ' it's original value.
    
    Dim ACADPref As AcadPreferencesOutput
    Dim originalValue As Variant, newValue As Variant
    
    ' Get the output preferences object
    Set ACADPref = ThisDrawing.Application.preferences.Output
    
    ' Read and display the original value
    originalValue = ACADPref.DefaultPlotStyleForObjects
    MsgBox "The DefaultPlotStyleForObjects preference is: " & originalValue

    ' Toggle and display the DefaultPlotStyleForObjects preference
    If ACADPref.DefaultPlotStyleForObjects = "ByBlock" Then
        ACADPref.DefaultPlotStyleForObjects = "Normal"
    Else
        ACADPref.DefaultPlotStyleForObjects = "ByBlock"
    End If
    
    newValue = ACADPref.DefaultPlotStyleForObjects
    MsgBox "The DefaultPlotStyleForObjects preference has been set to: " & newValue

    ' Reset the preference back to it's original value
    '
    ' * Note: Comment out this last section to leave the change to
    '         this preference in effect
    ACADPref.DefaultPlotStyleForObjects = originalValue
    MsgBox "The DefaultPlotStyleForObjects preference was reset back to: " & originalValue
End Sub


Sub Example_OLEQuality()
    ' This example reads and modifies the preference value which controls
    ' the plot quality of OLE objects. When finished, this example resets
    ' the preference value back to it's original value.
    
    Dim ACADPref As AcadPreferencesOutput
    Dim originalValue As Variant, DisplayValue As String
    
    ' Get the output preferences object
    Set ACADPref = ThisDrawing.Application.preferences.Output
    
    ' Store original value
    originalValue = ACADPref.OLEQuality
    
    ' Read and display the original value
    GoSub GETVALUE
    MsgBox "The OLEQuality preference is currently set to: " & DisplayValue

    ' Modify the OLEQuality preference by changing it to High Quality Photographic
    ACADPref.OLEQuality = acOQHighPhoto
    GoSub GETVALUE
    MsgBox "The OLEQuality preference has been set to: " & DisplayValue

    ' Reset the preference back to it's original value
    '
    ' * Note: Comment out this last section to leave the change to
    '         this preference in effect
    ACADPref.OLEQuality = originalValue
    GoSub GETVALUE
    MsgBox "The OLEQuality preference was reset back to: " & DisplayValue

    Exit Sub
    
GETVALUE:
    ' Convert the value of this setting to a meaningful text string
    DisplayValue = ACADPref.OLEQuality
    Select Case DisplayValue
        Case acOQLineArt: DisplayValue = "Line Art"
        Case acOQText: DisplayValue = "Text"
        Case acOQGraphics: DisplayValue = "Graphics"
        Case acOQPhoto: DisplayValue = "Photo"
        Case acOQHighPhoto: DisplayValue = "High Photo"
    End Select
    
    Return

End Sub

Sub Example_DisplayGrips()
    ' This example reads and modifies the preference value which controls
    ' the display of selection set grips for the Stretch, Move, Rotate,
    ' Scale, and Mirror grip modes.
    ' When finished, this example resets the preference value back to
    ' it's original value.
    
    Dim ACADPref As AcadPreferencesSelection
    Dim originalValue As Variant, newValue As Variant
    
    ' Get the selection preferences object
    Set ACADPref = ThisDrawing.Application.preferences.Selection
    
    ' Read and display the original value
    originalValue = ACADPref.DisplayGrips
    MsgBox "The DisplayGrips preference is set to: " & originalValue

    ' Modify the DisplayGrips preference by toggling the value
    ACADPref.DisplayGrips = Not (originalValue)
    newValue = ACADPref.DisplayGrips
    MsgBox "The DisplayGrips preference has been set to: " & newValue

    ' Reset the preference back to it's original value
    '
    ' * Note: Comment out this last section to leave the change to
    '         this preference in effect
    ACADPref.DisplayGrips = originalValue
    MsgBox "The DisplayGrips preference was reset back to: " & originalValue
End Sub

Sub Example_DisplayGripsWithinBlocks()
    ' This example reads and modifies the preference value which controls
    ' the assignment of grips within blocks.
    ' When finished, this example resets the preference value back to
    ' it's original value.
    
    Dim ACADPref As AcadPreferencesSelection
    Dim originalValue As Variant, newValue As Variant
    
    ' Get the selection preferences object
    Set ACADPref = ThisDrawing.Application.preferences.Selection
    
    ' Read and display the original value
    originalValue = ACADPref.DisplayGripsWithinBlocks
    MsgBox "The DisplayGripsWithinBlocks preference is set to: " & originalValue

    ' Modify the DisplayGripsWithinBlocks preference by toggling the value
    ACADPref.DisplayGripsWithinBlocks = Not (originalValue)
    newValue = ACADPref.DisplayGripsWithinBlocks
    MsgBox "The DisplayGripsWithinBlocks preference has been set to: " & newValue

    ' Reset the preference back to it's original value
    '
    ' * Note: Comment out this last section to leave the change to
    '         this preference in effect
    ACADPref.DisplayGripsWithinBlocks = originalValue
    MsgBox "The DisplayGripsWithinBlocks preference was reset back to: " & originalValue
End Sub

Sub Example_GripColorSelected()
    ' This example reads and modifies the preference value which controls
    ' the color of selected grips.
    ' When finished, this example resets the preference value back to
    ' it's original value.
    
    Dim ACADPref As AcadPreferencesSelection
    Dim originalValue As Variant, newValue As Variant
    
    ' Get the selection preferences object
    Set ACADPref = ThisDrawing.Application.preferences.Selection
    
    ' Read and display the original value
    originalValue = ACADPref.GripColorSelected
    MsgBox "The GripColorSelected preference is set to: " & originalValue

    ' Modify the GripColorSelected preference by setting it to green
    ACADPref.GripColorSelected = acGreen
    newValue = ACADPref.GripColorSelected
    MsgBox "The GripColorSelected preference has been set to: " & newValue

    ' Reset the preference back to it's original value
    '
    ' * Note: Comment out this last section to leave the change to
    '         this preference in effect
    ACADPref.GripColorSelected = originalValue
    MsgBox "The GripColorSelected preference was reset back to: " & originalValue
End Sub

Sub Example_GripColorUnselected()
    ' This example reads and modifies the preference value which controls
    ' the color of unselected grips.
    ' When finished, this example resets the preference value back to
    ' it's original value.
    
    Dim ACADPref As AcadPreferencesSelection
    Dim originalValue As Variant, newValue As Variant
    
    ' Get the selection preferences object
    Set ACADPref = ThisDrawing.Application.preferences.Selection
    
    ' Read and display the original value
    originalValue = ACADPref.GripColorUnselected
    MsgBox "The GripColorUnselected preference is set to: " & originalValue

    ' Modify the GripColorUnselected preference by setting it to green
    ACADPref.GripColorUnselected = acGreen
    newValue = ACADPref.GripColorUnselected
    MsgBox "The GripColorUnselected preference has been set to: " & newValue

    ' Reset the preference back to it's original value
    '
    ' * Note: Comment out this last section to leave the change to
    '         this preference in effect
    ACADPref.GripColorUnselected = originalValue
    MsgBox "The GripColorUnselected preference was reset back to: " & originalValue
End Sub

Sub Example_GripSize()
    ' This example reads and modifies the preference value which controls
    ' the size of grips. When finished, this example resets the
    ' preference value back to it's original value.
    
    Dim ACADPref As AcadPreferencesSelection
    Dim originalValue As Variant, newValue As Variant
    
    ' Get the selection preferences object
    Set ACADPref = ThisDrawing.Application.preferences.Selection
    
    ' Read and display the original value
    originalValue = ACADPref.GripSize
    MsgBox "The GripSize preference is set to: " & originalValue

    ' Modify the GripSize preference by setting it to 5
    ACADPref.GripSize = 5
    newValue = ACADPref.GripSize
    MsgBox "The GripSize preference has been set to: " & newValue

    ' Reset the preference back to it's original value
    '
    ' * Note: Comment out this last section to leave the change to
    '         this preference in effect
    ACADPref.GripSize = originalValue
    MsgBox "The GripSize preference was reset back to: " & originalValue
End Sub

Sub Example_PickAdd()
    ' This example reads and modifies the preference value which controls
    ' whether objects are added to the selection set using the Shift key.
    ' When finished, this example resets the preference value back to
    ' it's original value.
    
    Dim ACADPref As AcadPreferencesSelection
    Dim originalValue As Variant, newValue As Variant
    
    ' Get the selection preferences object
    Set ACADPref = ThisDrawing.Application.preferences.Selection
    
    ' Read and display the original value
    originalValue = ACADPref.PickAdd
    MsgBox "The PickAdd preference is set to: " & originalValue

    ' Modify the PickAdd preference by toggling the value
    ACADPref.PickAdd = Not (ACADPref.PickAdd)
    newValue = ACADPref.PickAdd
    MsgBox "The PickAdd preference has been set to: " & newValue

    ' Reset the preference back to it's original value
    '
    ' * Note: Comment out this last section to leave the change to
    '         this preference in effect
    ACADPref.PickAdd = originalValue
    MsgBox "The PickAdd preference was reset back to: " & originalValue
End Sub

Sub Example_PickAuto()
    ' This example reads and modifies the preference value which controls
    ' automatic windowing at the Select Objects prompt.
    ' When finished, this example resets the preference value back to
    ' it's original value.
    
    Dim ACADPref As AcadPreferencesSelection
    Dim originalValue As Variant, newValue As Variant
    
    ' Get the selection preferences object
    Set ACADPref = ThisDrawing.Application.preferences.Selection
    
    ' Read and display the original value
    originalValue = ACADPref.PickAuto
    MsgBox "The PickAuto preference is set to: " & originalValue

    ' Modify the PickAuto preference by toggling the value
    ACADPref.PickAuto = Not (ACADPref.PickAuto)
    newValue = ACADPref.PickAuto
    MsgBox "The PickAuto preference has been set to: " & newValue

    ' Reset the preference back to it's original value
    '
    ' * Note: Comment out this last section to leave the change to
    '         this preference in effect
    ACADPref.PickAuto = originalValue
    MsgBox "The PickAuto preference was reset back to: " & originalValue
End Sub

Sub Example_PickDrag()
    ' This example reads and modifies the preference value which controls
    ' the method of drawing a selection window.
    ' When finished, this example resets the preference value back to
    ' it's original value.
    
    Dim ACADPref As AcadPreferencesSelection
    Dim originalValue As Variant, newValue As Variant
    
    ' Get the selection preferences object
    Set ACADPref = ThisDrawing.Application.preferences.Selection
    
    ' Read and display the original value
    originalValue = ACADPref.PickDrag
    MsgBox "The PickDrag preference is set to: " & originalValue

    ' Modify the PickDrag preference by toggling the value
    ACADPref.PickDrag = Not (ACADPref.PickDrag)
    newValue = ACADPref.PickDrag
    MsgBox "The PickDrag preference has been set to: " & newValue

    ' Reset the preference back to it's original value
    '
    ' * Note: Comment out this last section to leave the change to
    '         this preference in effect
    ACADPref.PickDrag = originalValue
    MsgBox "The PickDrag preference was reset back to: " & originalValue
End Sub

Sub Example_PickFirst()
    ' This example reads and modifies the preference value which controls
    ' whether you select objects before (noun-verb selection) or after
    ' you issue a command.
    ' When finished, this example resets the preference value back to
    ' it's original value.
    
    Dim ACADPref As AcadPreferencesSelection
    Dim originalValue As Variant, newValue As Variant
    
    ' Get the selection preferences object
    Set ACADPref = ThisDrawing.Application.preferences.Selection
    
    ' Read and display the original value
    originalValue = ACADPref.PickFirst
    MsgBox "The PickFirst preference is set to: " & originalValue

    ' Modify the PickFirst preference by toggling the value
    ACADPref.PickFirst = Not (ACADPref.PickFirst)
    newValue = ACADPref.PickFirst
    MsgBox "The PickFirst preference has been set to: " & newValue

    ' Reset the preference back to it's original value
    '
    ' * Note: Comment out this last section to leave the change to
    '         this preference in effect
    ACADPref.PickFirst = originalValue
    MsgBox "The PickFirst preference was reset back to: " & originalValue
End Sub

Sub Example_PickBoxSize()
    ' This example reads and modifies the preference value which controls
    ' the size of the object selection target.
    ' When finished, this example resets the preference value back to
    ' it's original value.
    
    Dim ACADPref As AcadPreferencesSelection
    Dim originalValue As Variant, newValue As Variant
    
    ' Get the selection preferences object
    Set ACADPref = ThisDrawing.Application.preferences.Selection
    
    ' Read and display the original value
    originalValue = ACADPref.PickBoxSize
    MsgBox "The PickBoxSize preference is set to: " & originalValue

    ' Modify the PickBoxSize preference by setting it to 5
    ACADPref.PickBoxSize = 5
    newValue = ACADPref.PickBoxSize
    MsgBox "The PickBoxSize preference has been set to: " & newValue

    ' Reset the preference back to it's original value
    '
    ' * Note: Comment out this last section to leave the change to
    '         this preference in effect
    ACADPref.PickBoxSize = originalValue
    MsgBox "The PickBoxSize preference was reset back to: " & originalValue
End Sub

Sub Example_DisplayOLEScale()
    ' This example reads and modifies the preference value which controls
    ' whether the OLE scaling dialog is displayed when OLE objects are
    ' inserted into a drawing.
    ' When finished, this example resets the preference value back to
    ' it's original value.
    
    Dim ACADPref As AcadPreferencesSystem
    Dim originalValue As Variant, newValue As Variant
    
    ' Get the system preferences object
    Set ACADPref = ThisDrawing.Application.preferences.System
    
    ' Read and display the original value
    originalValue = ACADPref.DisplayOLEScale
    MsgBox "The DisplayOLEScale preference is set to: " & originalValue

    ' Modify the DisplayOLEScale preference by toggling the value
    ACADPref.DisplayOLEScale = Not (ACADPref.DisplayOLEScale)
    newValue = ACADPref.DisplayOLEScale
    MsgBox "The DisplayOLEScale preference has been set to: " & newValue

    ' Reset the preference back to it's original value
    '
    ' * Note: Comment out this last section to leave the change to
    '         this preference in effect
    ACADPref.DisplayOLEScale = originalValue
    MsgBox "The DisplayOLEScale preference was reset back to: " & originalValue
End Sub

Sub Example_ShowWarningMessages()
    ' This example reads and modifies the preference value which
    ' resets all dialog boxes that have the
    ' “Don’t Display This Warning Again” check box so they display again.
    '
    ' When finished, this example resets the preference value back to
    ' it's original value.
    
    Dim ACADPref As AcadPreferencesSystem
    Dim originalValue As Variant, newValue As Variant
    
    ' Get the system preferences object
    Set ACADPref = ThisDrawing.Application.preferences.System
    
    ' Read and display the original value
    originalValue = ACADPref.ShowWarningMessages
    MsgBox "The ShowWarningMessages preference is set to: " & originalValue

    ' Modify the ShowWarningMessages preference by toggling the value
    ACADPref.ShowWarningMessages = Not (ACADPref.ShowWarningMessages)
    newValue = ACADPref.ShowWarningMessages
    MsgBox "The ShowWarningMessages preference has been set to: " & newValue

    ' Reset the preference back to it's original value
    '
    ' * Note: Comment out this last section to leave the change to
    '         this preference in effect
    ACADPref.ShowWarningMessages = originalValue
    MsgBox "The ShowWarningMessages preference was reset back to: " & originalValue
End Sub

Sub Example_SingleDocumentMode()
    ' This example reads and modifies the preference value which controls
    ' whether AutoCAD runs in single- or multiple-document mode.
    ' When finished, this example resets the preference value back to
    ' it's original value.
    
    Dim ACADPref As AcadPreferencesSystem
    Dim originalValue As Variant, newValue As Variant
    
    ' Get the system preferences object
    Set ACADPref = ThisDrawing.Application.preferences.System
    
    ' Read and display the original value
    originalValue = ACADPref.SingleDocumentMode
    MsgBox "The SingleDocumentMode preference is set to: " & originalValue

    ' Modify the SingleDocumentMode preference by toggling the value
    ACADPref.SingleDocumentMode = Not (ACADPref.SingleDocumentMode)
    newValue = ACADPref.SingleDocumentMode
    MsgBox "The SingleDocumentMode preference has been set to: " & newValue

    ' Reset the preference back to it's original value
    '
    ' * Note: Comment out this last section to leave the change to
    '         this preference in effect
    ACADPref.SingleDocumentMode = originalValue
    MsgBox "The SingleDocumentMode preference was reset back to: " & originalValue
End Sub

Sub Example_StoreSQLIndex()
    ' This example reads and modifies the preference value which controls
    ' whether the SQL index is stored in the drawing.
    ' When finished, this example resets the preference value back to
    ' it's original value.
    
    Dim ACADPref As AcadPreferencesSystem
    Dim originalValue As Variant, newValue As Variant
    
    ' Get the system preferences object
    Set ACADPref = ThisDrawing.Application.preferences.System
    
    ' Read and display the original value
    originalValue = ACADPref.StoreSQLIndex
    MsgBox "The StoreSQLIndex preference is set to: " & originalValue

    ' Modify the StoreSQLIndex preference by toggling the value
    ACADPref.StoreSQLIndex = Not (ACADPref.StoreSQLIndex)
    newValue = ACADPref.StoreSQLIndex
    MsgBox "The StoreSQLIndex preference has been set to: " & newValue

    ' Reset the preference back to it's original value
    '
    ' * Note: Comment out this last section to leave the change to
    '         this preference in effect
    ACADPref.StoreSQLIndex = originalValue
    MsgBox "The StoreSQLIndex preference was reset back to: " & originalValue
End Sub

Sub Example_TablesReadOnly()
    ' This example reads and modifies the preference value which controls
    ' whether to open database tables in read-only mode.
    ' When finished, this example resets the preference value back to
    ' it's original value.
    
    Dim ACADPref As AcadPreferencesSystem
    Dim originalValue As Variant, newValue As Variant
    
    ' Get the system preferences object
    Set ACADPref = ThisDrawing.Application.preferences.System
    
    ' Read and display the original value
    originalValue = ACADPref.TablesReadOnly
    MsgBox "The TablesReadOnly preference is set to: " & originalValue

    ' Modify the TablesReadOnly preference by toggling the value
    ACADPref.TablesReadOnly = Not (ACADPref.TablesReadOnly)
    newValue = ACADPref.TablesReadOnly
    MsgBox "The TablesReadOnly preference has been set to: " & newValue

    ' Reset the preference back to it's original value
    '
    ' * Note: Comment out this last section to leave the change to
    '         this preference in effect
    ACADPref.TablesReadOnly = originalValue
    MsgBox "The TablesReadOnly preference was reset back to: " & originalValue
End Sub

Sub Example_HyperlinkDisplayCursor()
    ' This example reads and modifies the preference value which controls
    ' the display of the hyperlink cursor and shortcut menu.
    ' When finished, this example resets the preference value back to
    ' it's original value.
    
    Dim ACADPref As AcadPreferencesUser
    Dim originalValue As Variant, newValue As Variant
    
    ' Get the user preferences object
    Set ACADPref = ThisDrawing.Application.preferences.User
    
    ' Read and display the original value
    originalValue = ACADPref.HyperlinkDisplayCursor
    MsgBox "The HyperlinkDisplayCursor preference is set to: " & originalValue

    ' Modify the HyperlinkDisplayCursor preference by toggling the value
    ACADPref.HyperlinkDisplayCursor = Not (ACADPref.HyperlinkDisplayCursor)
    newValue = ACADPref.HyperlinkDisplayCursor
    MsgBox "The HyperlinkDisplayCursor preference has been set to: " & newValue

    ' Reset the preference back to it's original value
    '
    ' * Note: Comment out this last section to leave the change to
    '         this preference in effect
    ACADPref.HyperlinkDisplayCursor = originalValue
    MsgBox "The HyperlinkDisplayCursor preference was reset back to: " & originalValue
End Sub

Sub Example_HyperLinkDisplayTooltip()
    ' This example reads and modifies the preference value which controls
    ' the display of hyperlink tooltips.
    ' When finished, this example resets the preference value back to
    ' it's original value.
    
    Dim ACADPref As AcadPreferencesUser
    Dim originalValue As Variant, newValue As Variant
    
    ' Get the user preferences object
    Set ACADPref = ThisDrawing.Application.preferences.User
    
    ' Read and display the original value
    originalValue = ACADPref.HyperlinkDisplayTooltip
    MsgBox "The HyperLinkDisplayTooltip preference is set to: " & originalValue

    ' Modify the HyperLinkDisplayTooltip preference by toggling the value
    ACADPref.HyperlinkDisplayTooltip = Not (ACADPref.HyperlinkDisplayTooltip)
    newValue = ACADPref.HyperlinkDisplayTooltip
    MsgBox "The HyperLinkDisplayTooltip preference has been set to: " & newValue

    ' Reset the preference back to it's original value
    '
    ' * Note: Comment out this last section to leave the change to
    '         this preference in effect
    ACADPref.HyperlinkDisplayTooltip = originalValue
    MsgBox "The HyperLinkDisplayTooltip preference was reset back to: " & originalValue
End Sub

Sub Example_Drafting()
    ' This example obtains a reference to the Drafting Preferences object
    ' from the Application Preferences object, and reads one of the Drafting
    ' preferences
    
    Dim ACADPref As AcadPreferencesDrafting
    
    ' Obtain a reference to the Drafting Preferences object
    Set ACADPref = ThisDrawing.Application.preferences.Drafting
    
    MsgBox "We now have access to the properties and methods of the Drafting Preferences object!"
    MsgBox "The Drafting preference AutoSnapTooltip is set to: " & ACADPref.AutoSnapTooltip
    
    ' Release Drafting Preferences object
    Set ACADPref = Nothing
    MsgBox "We have now released the Drafting Preferences object!"
End Sub

Sub Example_Display()
    ' This example obtains a reference to the Display Preferences object
    ' from the Application Preferences object, and reads one of the Display
    ' preferences
    
    Dim ACADPref As AcadPreferencesDisplay
    
    ' Obtain a reference to the Display Preferences object
    Set ACADPref = ThisDrawing.Application.preferences.DISPLAY
    
    MsgBox "We now have access to the properties and methods of the Display Preferences object!"
    MsgBox "The Display preference CursorSize is set to: " & ACADPref.CursorSize
    
    ' Release Display Preferences object
    Set ACADPref = Nothing
    MsgBox "We have now released the Display Preferences object!"
End Sub

Sub Example_Files()
    ' This example obtains a reference to the Files Preferences object
    ' from the Application Preferences object, and reads one of the File
    ' preferences
    
    Dim ACADPref As AcadPreferencesFiles
    
    ' Obtain a reference to the Files Preferences object
    Set ACADPref = ThisDrawing.Application.preferences.Files
    
    MsgBox "We now have access to the properties and methods of the Files Preferences object!"
    MsgBox "The File preference AutoSavePath is set to: " & ACADPref.AutoSavePath
    
    ' Release Files Preferences object
    Set ACADPref = Nothing
    MsgBox "We have now released the Files Preferences object!"
End Sub

Sub Example_OpenSave()
    ' This example obtains a reference to the OpenSave Preferences object
    ' from the Application Preferences object, and reads one of the OpenSave
    ' preferences
    
    Dim ACADPref As AcadPreferencesOpenSave
    
    ' Obtain a reference to the OpenSave Preferences object
    Set ACADPref = ThisDrawing.Application.preferences.OpenSave
    
    MsgBox "We now have access to the properties and methods of the OpenSave Preferences object!"
    MsgBox "The OpenSave preference TempFileExtension is set to: " & ACADPref.TempFileExtension
    
    ' Release OpenSave Preferences object
    Set ACADPref = Nothing
    MsgBox "We have now released the OpenSave Preferences object!"
End Sub

Sub Example_Output()
    ' This example obtains a reference to the Output Preferences object
    ' from the Application Preferences object, and reads one of the Output
    ' preferences
    
    Dim ACADPref As AcadPreferencesOutput
    
    ' Obtain a reference to the Output Preferences object
    Set ACADPref = ThisDrawing.Application.preferences.Output
    
    MsgBox "We now have access to the properties and methods of the Output Preferences object!"
    MsgBox "The Output preference DefaultOutputDevice is set to: " & ACADPref.DefaultOutputDevice
    
    ' Release Output Preferences object
    Set ACADPref = Nothing
    MsgBox "We have now released the Output Preferences object!"
End Sub

Sub Example_Profiles()
    ' This example obtains a reference to the Profiles Preferences object
    ' from the Application Preferences object, and reads one of the Profiles
    ' preferences
    
    Dim ACADPref As AcadPreferencesProfiles
    
    ' Obtain a reference to the Profiles Preferences object
    Set ACADPref = ThisDrawing.Application.preferences.Profiles
    
    MsgBox "We now have access to the properties and methods of the Profiles Preferences object!"
    MsgBox "The Profiles preference ActiveProfile is set to: " & ACADPref.ActiveProfile
    
    ' Release Profiles Preferences object
    Set ACADPref = Nothing
    MsgBox "We have now released the Profiles Preferences object!"
End Sub

Sub Example_Selection()
    ' This example obtains a reference to the Selection Preferences object
    ' from the Application Preferences object, and reads one of the Selection
    ' preferences
    
    Dim ACADPref As AcadPreferencesSelection
    
    ' Obtain a reference to the Selection Preferences object
    Set ACADPref = ThisDrawing.Application.preferences.Selection
    
    MsgBox "We now have access to the properties and methods of the Selection Preferences object!"
    MsgBox "The Selection preference GripSize is set to: " & ACADPref.GripSize
    
    ' Release Selection Preferences object
    Set ACADPref = Nothing
    MsgBox "We have now released the Selection Preferences object!"
End Sub

Sub Example_System()
    ' This example obtains a reference to the System Preferences object
    ' from the Application Preferences object, and reads one of the System
    ' preferences
    
    Dim ACADPref As AcadPreferencesSystem
    
    ' Obtain a reference to the System Preferences object
    Set ACADPref = ThisDrawing.Application.preferences.System
    
    MsgBox "We now have access to the properties and methods of the System Preferences object!"
    MsgBox "The System preference BeepOnError is set to: " & ACADPref.BeepOnError
    
    ' Release System Preferences object
    Set ACADPref = Nothing
    MsgBox "We have now released the System Preferences object!"
End Sub

Sub Example_User()
    ' This example obtains a reference to the User Preferences object
    ' from the Application Preferences object, and reads one of the User
    ' preferences
    
    Dim ACADPref As AcadPreferencesUser
    
    ' Obtain a reference to the User Preferences object
    Set ACADPref = ThisDrawing.Application.preferences.User
    
    MsgBox "We now have access to the properties and methods of the User Preferences object!"
    MsgBox "The User preference KeyboardAccelerator is set to: " & ACADPref.KeyboardAccelerator
    
    ' Release User Preferences object
    Set ACADPref = Nothing
    MsgBox "We have now released the User Preferences object!"
End Sub


Sub Example_AllowLongSymbolNames()
    ' This example reads and modifies the preference value which controls
    ' whether symbol names may include extended character sets, or more
    ' than 31 characters.
    '
    ' When finished, this example resets the preference value back to
    ' it's original value.
    
    Dim ACADPref As AcadDatabasePreferences
    Dim originalValue As Variant, newValue As Variant
    
    ' Get the user preferences object
    Set ACADPref = ThisDrawing.preferences
    
    ' Read and display the original value
    originalValue = ACADPref.AllowLongSymbolNames
    MsgBox "The AllowLongSymbolNames preference is set to: " & originalValue

    ' Modify the AllowLongSymbolNames preference by toggling the value
    ACADPref.AllowLongSymbolNames = Not (ACADPref.AllowLongSymbolNames)
    newValue = ACADPref.AllowLongSymbolNames
    MsgBox "The AllowLongSymbolNames preference has been set to: " & newValue

    ' Reset the preference back to it's original value
    '
    ' * Note: Comment out this last section to leave the change to
    '         this preference in effect
    ACADPref.AllowLongSymbolNames = originalValue
    MsgBox "The AllowLongSymbolNames preference was reset back to: " & originalValue
End Sub

Sub Example_ObjectSortByPlotting()
    ' This example reads and modifies the preference value which controls
    ' the sorting of drawing objects by plotting order.
    ' When finished, this example resets the preference value back to
    ' it's original value.
    
    Dim ACADPref As AcadDatabasePreferences
    Dim originalValue As Variant, newValue As Variant
    
    ' Get the user preferences object
    Set ACADPref = ThisDrawing.preferences
    
    ' Read and display the original value
    originalValue = ACADPref.ObjectSortByPlotting
    MsgBox "The ObjectSortByPlotting preference is set to: " & originalValue

    ' Modify the ObjectSortByPlotting preference by toggling the value
    ACADPref.ObjectSortByPlotting = Not (ACADPref.ObjectSortByPlotting)
    newValue = ACADPref.ObjectSortByPlotting
    MsgBox "The ObjectSortByPlotting preference has been set to: " & newValue

    ' Reset the preference back to it's original value
    '
    ' * Note: Comment out this last section to leave the change to
    '         this preference in effect
    ACADPref.ObjectSortByPlotting = originalValue
    MsgBox "The ObjectSortByPlotting preference was reset back to: " & originalValue
End Sub

Sub Example_ObjectSortByPSOutput()
    ' This example reads and modifies the preference value which controls
    ' the sorting of drawing objects by PostScript output order.
    ' When finished, this example resets the preference value back to
    ' it's original value.
    
    Dim ACADPref As AcadDatabasePreferences
    Dim originalValue As Variant, newValue As Variant
    
    ' Get the user preferences object
    Set ACADPref = ThisDrawing.preferences
    
    ' Read and display the original value
    originalValue = ACADPref.ObjectSortByPSOutput
    MsgBox "The ObjectSortByPSOutput preference is set to: " & originalValue

    ' Modify the ObjectSortByPSOutput preference by toggling the value
    ACADPref.ObjectSortByPSOutput = Not (ACADPref.ObjectSortByPSOutput)
    newValue = ACADPref.ObjectSortByPSOutput
    MsgBox "The ObjectSortByPSOutput preference has been set to: " & newValue

    ' Reset the preference back to it's original value
    '
    ' * Note: Comment out this last section to leave the change to
    '         this preference in effect
    ACADPref.ObjectSortByPSOutput = originalValue
    MsgBox "The ObjectSortByPSOutput preference was reset back to: " & originalValue
End Sub

Sub Example_ObjectSortByRedraws()
    ' This example reads and modifies the preference value which controls
    ' the sorting of drawing objects by redraw order.
    ' When finished, this example resets the preference value back to
    ' it's original value.
    
    Dim ACADPref As AcadDatabasePreferences
    Dim originalValue As Variant, newValue As Variant
    
    ' Get the user preferences object
    Set ACADPref = ThisDrawing.preferences
    
    ' Read and display the original value
    originalValue = ACADPref.ObjectSortByRedraws
    MsgBox "The ObjectSortByRedraws preference is set to: " & originalValue

    ' Modify the ObjectSortByRedraws preference by toggling the value
    ACADPref.ObjectSortByRedraws = Not (ACADPref.ObjectSortByRedraws)
    newValue = ACADPref.ObjectSortByRedraws
    MsgBox "The ObjectSortByRedraws preference has been set to: " & newValue

    ' Reset the preference back to it's original value
    '
    ' * Note: Comment out this last section to leave the change to
    '         this preference in effect
    ACADPref.ObjectSortByRedraws = originalValue
    MsgBox "The ObjectSortByRedraws preference was reset back to: " & originalValue
End Sub

Sub Example_ObjectSortByRegens()
    ' This example reads and modifies the preference value which controls
    ' the sorting of drawing objects by regeneration order.
    ' When finished, this example resets the preference value back to
    ' it's original value.
    
    Dim ACADPref As AcadDatabasePreferences
    Dim originalValue As Variant, newValue As Variant
    
    ' Get the user preferences object
    Set ACADPref = ThisDrawing.preferences
    
    ' Read and display the original value
    originalValue = ACADPref.ObjectSortByRegens
    MsgBox "The ObjectSortByRegens preference is set to: " & originalValue

    ' Modify the ObjectSortByRegens preference by toggling the value
    ACADPref.ObjectSortByRegens = Not (ACADPref.ObjectSortByRegens)
    newValue = ACADPref.ObjectSortByRegens
    MsgBox "The ObjectSortByRegens preference has been set to: " & newValue

    ' Reset the preference back to it's original value
    '
    ' * Note: Comment out this last section to leave the change to
    '         this preference in effect
    ACADPref.ObjectSortByRegens = originalValue
    MsgBox "The ObjectSortByRegens preference was reset back to: " & originalValue
End Sub

Sub Example_ObjectSortBySelection()
    ' This example reads and modifies the preference value which controls
    ' the sorting of drawing objects by object selection.
    ' When finished, this example resets the preference value back to
    ' it's original value.
    
    Dim ACADPref As AcadDatabasePreferences
    Dim originalValue As Variant, newValue As Variant
    
    ' Get the user preferences object
    Set ACADPref = ThisDrawing.preferences
    
    ' Read and display the original value
    originalValue = ACADPref.ObjectSortBySelection
    MsgBox "The ObjectSortBySelection preference is set to: " & originalValue

    ' Modify the ObjectSortBySelection preference by toggling the value
    ACADPref.ObjectSortBySelection = Not (ACADPref.ObjectSortBySelection)
    newValue = ACADPref.ObjectSortBySelection
    MsgBox "The ObjectSortBySelection preference has been set to: " & newValue

    ' Reset the preference back to it's original value
    '
    ' * Note: Comment out this last section to leave the change to
    '         this preference in effect
    ACADPref.ObjectSortBySelection = originalValue
    MsgBox "The ObjectSortBySelection preference was reset back to: " & originalValue
End Sub

Sub Example_ObjectSortBySnap()
    ' This example reads and modifies the preference value which controls
    ' the sorting of drawing objects by object snap.
    ' When finished, this example resets the preference value back to
    ' it's original value.
    
    Dim ACADPref As AcadDatabasePreferences
    Dim originalValue As Variant, newValue As Variant
    
    ' Get the user preferences object
    Set ACADPref = ThisDrawing.preferences
    
    ' Read and display the original value
    originalValue = ACADPref.ObjectSortBySnap
    MsgBox "The ObjectSortBySnap preference is set to: " & originalValue

    ' Modify the ObjectSortBySnap preference by toggling the value
    ACADPref.ObjectSortBySnap = Not (ACADPref.ObjectSortBySnap)
    newValue = ACADPref.ObjectSortBySnap
    MsgBox "The ObjectSortBySnap preference has been set to: " & newValue

    ' Reset the preference back to it's original value
    '
    ' * Note: Comment out this last section to leave the change to
    '         this preference in effect
    ACADPref.ObjectSortBySnap = originalValue
    MsgBox "The ObjectSortBySnap preference was reset back to: " & originalValue
End Sub

Sub Example_OLELaunch()
    ' This example reads and modifies the preference value which controls
    ' whether to launch the parent application when plotting OLE objects.
    ' When finished, this example resets the preference value back to
    ' it's original value.
    
    Dim ACADPref As AcadDatabasePreferences
    Dim originalValue As Variant, newValue As Variant
    
    ' Get the user preferences object
    Set ACADPref = ThisDrawing.preferences
    
    ' Read and display the original value
    originalValue = ACADPref.OLELaunch
    MsgBox "The OLELaunch preference is set to: " & originalValue

    ' Modify the OLELaunch preference by toggling the value
    ACADPref.OLELaunch = Not (ACADPref.OLELaunch)
    newValue = ACADPref.OLELaunch
    MsgBox "The OLELaunch preference has been set to: " & newValue

    ' Reset the preference back to it's original value
    '
    ' * Note: Comment out this last section to leave the change to
    '         this preference in effect
    ACADPref.OLELaunch = originalValue
    MsgBox "The OLELaunch preference was reset back to: " & originalValue
End Sub

Sub Example_SolidFill()
    ' This example reads and modifies the preference value which controls
    ' whether multilines, traces, solids, all hatches (including solid-fill)
    ' and wide polylines are filled in.
    '
    ' When finished, this example resets the preference value back to
    ' it's original value.
    
    Dim ACADPref As AcadDatabasePreferences
    Dim originalValue As Variant, newValue As Variant
    
    ' Get the user preferences object
    Set ACADPref = ThisDrawing.preferences
    
    ' Read and display the original value
    originalValue = ACADPref.SolidFill
    MsgBox "The SolidFill preference is set to: " & originalValue

    ' Modify the SolidFill preference by toggling the value
    ACADPref.SolidFill = Not (ACADPref.SolidFill)
    newValue = ACADPref.SolidFill
    MsgBox "The SolidFill preference has been set to: " & newValue

    ' Reset the preference back to it's original value
    '
    ' * Note: Comment out this last section to leave the change to
    '         this preference in effect
    ACADPref.SolidFill = originalValue
    MsgBox "The SolidFill preference was reset back to: " & originalValue
End Sub

Sub Example_XRefEdit()
    ' This example reads and modifies the preference value which controls
    ' whether the current drawing can be edited in place when being
    ' referenced by another user.
    '
    ' When finished, this example resets the preference value back to
    ' it's original value.
    
    Dim ACADPref As AcadDatabasePreferences
    Dim originalValue As Variant, newValue As Variant
    
    ' Get the user preferences object
    Set ACADPref = ThisDrawing.preferences
    
    ' Read and display the original value
    originalValue = ACADPref.XRefEdit
    MsgBox "The XRefEdit preference is set to: " & originalValue

    ' Modify the XRefEdit preference by toggling the value
    ACADPref.XRefEdit = Not (ACADPref.XRefEdit)
    newValue = ACADPref.XRefEdit
    MsgBox "The XRefEdit preference has been set to: " & newValue

    ' Reset the preference back to it's original value
    '
    ' * Note: Comment out this last section to leave the change to
    '         this preference in effect
    ACADPref.XRefEdit = originalValue
    MsgBox "The XRefEdit preference was reset back to: " & originalValue
End Sub

Sub Example_XRefLayerVisibility()
    ' This example reads and modifies the preference value which controls
    ' the visibility of xref-dependent layers and specifies if nested xref
    ' path changes are saved.
    '
    ' When finished, this example resets the preference value back to
    ' it's original value.
    
    Dim ACADPref As AcadDatabasePreferences
    Dim originalValue As Variant, newValue As Variant
    
    ' Get the user preferences object
    Set ACADPref = ThisDrawing.preferences
    
    ' Read and display the original value
    originalValue = ACADPref.XRefLayerVisibility
    MsgBox "The XRefLayerVisibility preference is set to: " & originalValue

    ' Modify the XRefLayerVisibility preference by toggling the value
    ACADPref.XRefLayerVisibility = Not (ACADPref.XRefLayerVisibility)
    newValue = ACADPref.XRefLayerVisibility
    MsgBox "The XRefLayerVisibility preference has been set to: " & newValue

    ' Reset the preference back to it's original value
    '
    ' * Note: Comment out this last section to leave the change to
    '         this preference in effect
    ACADPref.XRefLayerVisibility = originalValue
    MsgBox "The XRefLayerVisibility preference was reset back to: " & originalValue
End Sub

Sub Example_CopyProfile()
    ' This example copies an existing profile.
    ' You can see the new profile under Options/Profiles
    '
    ' *Note: This example relies on the default profile "<<Unnamed Profile>>".
    ' If this profile has already been renamed or removed, be sure to change the
    ' name of the SourceProfile to one that currently exists.
    
    Dim ACADPref As AcadPreferencesProfiles
    Dim SourceProfile As String, DestinationProfile As String
    
    ' Get the profiles preferences object
    Set ACADPref = ThisDrawing.Application.preferences.Profiles
    
    ' Copy the default profile
    On Error GoTo ERRORTRAP
    
    SourceProfile = "<<Unnamed Profile>>"
    DestinationProfile = "NEW_PROFILE"
    
    ACADPref.CopyProfile SourceProfile, DestinationProfile
    
    MsgBox "We have just copied the existing profile " & SourceProfile & " to " & DestinationProfile
    
    Exit Sub
    
ERRORTRAP:
    If Err.Description <> "" Then
        MsgBox "The default profile '" & SourceProfile & "' cannot be found, please use a different source profile."
    End If
End Sub

Sub Example_RenameProfile()
    ' This example renames an existing profile.
    ' You can see the renamed profile under Options/Profiles
    '
    ' *Note: This example relies on the default profile "<<Unnamed Profile>>".
    ' If this profile has already been renamed or removed, be sure to change the
    ' name of the SourceProfile to one that currently exists.
    
    Dim ACADPref As AcadPreferencesProfiles
    Dim SourceProfile As String, DestinationProfile As String
    
    ' Get the profiles preferences object
    Set ACADPref = ThisDrawing.Application.preferences.Profiles
    
    ' Rename the default profile
    On Error GoTo ERRORTRAP
    
    SourceProfile = "<<Unnamed Profile>>"
    DestinationProfile = "NEW_PROFILE_NAME"
        
    ACADPref.RenameProfile SourceProfile, DestinationProfile

    MsgBox "We have just renamed the profile " & SourceProfile & " to " & DestinationProfile
    
    Exit Sub
    
ERRORTRAP:
    If Err.Description <> "" Then
        MsgBox "The default profile '" & SourceProfile & "' cannot be found, please use a different source profile."
    End If

End Sub

Sub Example_HyperLinks()
    ' This example creates a Circle object in model space and
    ' adds a new Hyperlink to its Hyperlink collection
    
    Dim Hyperlinks As AcadHyperlinks
    Dim Hyperlink As AcadHyperlink
    Dim circleObj As AcadCircle
    Dim centerPoint(0 To 2) As Double
    Dim radius As Double
    Dim HLList As String
    
    ' Define the Circle object
    centerPoint(0) = 0: centerPoint(1) = 0: centerPoint(2) = 0
    radius = 5#
    
    ' Create the Circle object in model space
    Set circleObj = ThisDrawing.ModelSpace.AddCircle(centerPoint, radius)

    ThisDrawing.Application.ZoomAll
    
    ' Get reference to the Circle's Hyperlinks collection
    Set Hyperlinks = circleObj.Hyperlinks
    
    ' Add a new Hyperlink complete with all properties
    Set Hyperlink = Hyperlinks.Add("AutoDesk")
    Hyperlink.URL = "www.autodesk.com"
    Hyperlink.URLDescription = "Autodesk Main Site"
    Hyperlink.URLNamedLocation = "MY_LOCATION"
    
    ' Read and display a list of existing Hyperlinks and
    ' their properties for this object
    For Each Hyperlink In Hyperlinks
        HLList = HLList & "____________________________________" & vbCrLf   ' Separator
        HLList = HLList & "URL: " & Hyperlink.URL & vbCrLf
        HLList = HLList & "URL Description: " & Hyperlink.URLDescription & vbCrLf
        HLList = HLList & "URL Named Location: " & Hyperlink.URLNamedLocation & vbCrLf
    Next
    
    MsgBox "The circle has " & Hyperlinks.count & " Hyperlink: " & vbCrLf & HLList
End Sub

Sub Example_URLNamedLocation()
    ' This example creates a Circle object in model space and
    ' adds a new Hyperlink to its Hyperlink collection
    
    Dim Hyperlinks As AcadHyperlinks
    Dim Hyperlink As AcadHyperlink
    Dim circleObj As AcadCircle
    Dim centerPoint(0 To 2) As Double
    Dim radius As Double
    Dim HLList As String
    
    ' Define the Circle object
    centerPoint(0) = 0: centerPoint(1) = 0: centerPoint(2) = 0
    radius = 5#
    
    ' Create the Circle object in model space
    Set circleObj = ThisDrawing.ModelSpace.AddCircle(centerPoint, radius)

    ThisDrawing.Application.ZoomAll
    
    ' Get reference to the Circle's Hyperlinks collection
    Set Hyperlinks = circleObj.Hyperlinks
    
    ' Add a new Hyperlink complete with all properties
    Set Hyperlink = Hyperlinks.Add("AutoDesk")
    Hyperlink.URL = "www.autodesk.com"
    Hyperlink.URLDescription = "Autodesk Main Site"
    Hyperlink.URLNamedLocation = "MY_LOCATION"
    
    ' Read and display a list of existing Hyperlinks and
    ' their properties for this object
    For Each Hyperlink In Hyperlinks
        HLList = HLList & "____________________________________" & vbCrLf   ' Separator
        HLList = HLList & "URL: " & Hyperlink.URL & vbCrLf
        HLList = HLList & "URL Description: " & Hyperlink.URLDescription & vbCrLf
        HLList = HLList & "URL Named Location: " & Hyperlink.URLNamedLocation & vbCrLf
    Next
    
    MsgBox "The circle has " & Hyperlinks.count & " Hyperlink: " & vbCrLf & HLList
End Sub

Sub Example_URL()
    ' This example creates a Circle object in model space and
    ' adds a new Hyperlink to its Hyperlink collection
    
    Dim Hyperlinks As AcadHyperlinks
    Dim Hyperlink As AcadHyperlink
    Dim circleObj As AcadCircle
    Dim centerPoint(0 To 2) As Double
    Dim radius As Double
    Dim HLList As String
    
    ' Define the Circle object
    centerPoint(0) = 0: centerPoint(1) = 0: centerPoint(2) = 0
    radius = 5#
    
    ' Create the Circle object in model space
    Set circleObj = ThisDrawing.ModelSpace.AddCircle(centerPoint, radius)

    ThisDrawing.Application.ZoomAll
    
    ' Get reference to the Circle's Hyperlinks collection
    Set Hyperlinks = circleObj.Hyperlinks
    
    ' Add a new Hyperlink complete with all properties
    Set Hyperlink = Hyperlinks.Add("AutoDesk")
    Hyperlink.URL = "www.autodesk.com"
    Hyperlink.URLDescription = "Autodesk Main Site"
    Hyperlink.URLNamedLocation = "MY_LOCATION"
    
    ' Read and display a list of existing Hyperlinks and
    ' their properties for this object
    For Each Hyperlink In Hyperlinks
        HLList = HLList & "____________________________________" & vbCrLf   ' Separator
        HLList = HLList & "URL: " & Hyperlink.URL & vbCrLf
        HLList = HLList & "URL Description: " & Hyperlink.URLDescription & vbCrLf
        HLList = HLList & "URL Named Location: " & Hyperlink.URLNamedLocation & vbCrLf
    Next
    
    MsgBox "The circle has " & Hyperlinks.count & " Hyperlink: " & vbCrLf & HLList
End Sub

Sub Example_URLDescription()
    ' This example creates a Circle object in model space and
    ' adds a new Hyperlink to its Hyperlink collection
    
    Dim Hyperlinks As AcadHyperlinks
    Dim Hyperlink As AcadHyperlink
    Dim circleObj As AcadCircle
    Dim centerPoint(0 To 2) As Double
    Dim radius As Double
    Dim HLList As String
    
    ' Define the Circle object
    centerPoint(0) = 0: centerPoint(1) = 0: centerPoint(2) = 0
    radius = 5#
    
    ' Create the Circle object in model space
    Set circleObj = ThisDrawing.ModelSpace.AddCircle(centerPoint, radius)

    ThisDrawing.Application.ZoomAll
    
    ' Get reference to the Circle's Hyperlinks collection
    Set Hyperlinks = circleObj.Hyperlinks
    
    ' Add a new Hyperlink complete with all properties
    Set Hyperlink = Hyperlinks.Add("AutoDesk")
    Hyperlink.URL = "www.autodesk.com"
    Hyperlink.URLDescription = "Autodesk Main Site"
    Hyperlink.URLNamedLocation = "MY_LOCATION"
    
    ' Read and display a list of existing Hyperlinks and
    ' their properties for this object
    For Each Hyperlink In Hyperlinks
        HLList = HLList & "____________________________________" & vbCrLf   ' Separator
        HLList = HLList & "URL: " & Hyperlink.URL & vbCrLf
        HLList = HLList & "URL Description: " & Hyperlink.URLDescription & vbCrLf
        HLList = HLList & "URL Named Location: " & Hyperlink.URLNamedLocation & vbCrLf
    Next
    
    MsgBox "The circle has " & Hyperlinks.count & " Hyperlink: " & vbCrLf & HLList
End Sub

Sub Example_Database()
    ' This example references the Database object obtained from the model space.
    ' We then display information from the Database object.
    
    Dim Database As AcadDatabase
    
    ' Attach to Database object
    Set Database = ThisDrawing.ModelSpace.Database
    MsgBox "We now have access to the properties and methods of the Database object!"
    
    ' Retrieve the number of Blocks in this database
    MsgBox "The number of Blocks in this database is: " & Database.Blocks.count

    ' Release object
    Set Database = Nothing
    MsgBox "The Database object has been released!"
End Sub

Sub Example_IsLayout()
    ' This example cycles through each Block object in a drawing
    ' and determines the style of each Block by accessing the
    ' IsLayout and IsXRef properties of the Block.  We also add a Block
    ' object at runtime so the results are mixed and do not only
    ' come from the default Blocks.
    
    Dim circleObj As AcadCircle
    Dim centerPoint(0 To 2) As Double, InsertPoint(0 To 2) As Double
    Dim radius As Double
    Dim newBlock As AcadBlock, insertedBlock As AcadBlockReference
    Dim tempBlock As AcadBlock
    Dim msg As String
    
    ' Define the Circle object that will be inserted into the block
    centerPoint(0) = 0: centerPoint(1) = 0: centerPoint(2) = 0
    InsertPoint(0) = 1: InsertPoint(1) = 1: InsertPoint(2) = 0
    radius = 0.5
    
    ' Create a new block to hold the Circle object
    Set newBlock = ThisDrawing.Blocks.Add(centerPoint, "CBlock")
    
    ' Add the Circle object to the new block object
    Set circleObj = ThisDrawing.Blocks("CBlock").AddCircle(centerPoint, radius)
    
    ' Add the new block to model space
    Set insertedBlock = ThisDrawing.ModelSpace.InsertBlock(InsertPoint, "CBlock", 1, 1, 1, 0)
        
    ThisDrawing.Application.ZoomAll
    
    msg = vbCrLf & vbCrLf
    
    For Each tempBlock In ThisDrawing.Blocks
        If Not (tempBlock.IsLayout) And Not (tempBlock.IsXRef) Then
            ' Block is simple
            msg = msg & tempBlock.name & ": Simple"
        ElseIf tempBlock.IsXRef Then
            ' Block is an external reference
            msg = msg & tempBlock.name & ": External Reference"
            If tempBlock.IsLayout Then
                ' Block also contains layout geometry
                msg = msg & tempBlock.name & " and Contains Layout Geometry"
            End If
        ElseIf tempBlock.IsLayout Then
            ' Block contains layout geometry
            msg = msg & tempBlock.name & ": Contains Layout Geometry"
        End If
        
        msg = msg & vbCrLf      ' Move to next line
    Next
        
    ' Display Block information for this drawing
    MsgBox "Blocks in this drawing have the following styles: " & msg

End Sub

Sub Example_IsXRef()
    ' This example cycles through each Block object in a drawing
    ' and determines the style of each Block by accessing the
    ' IsLayout and IsXRef properties of the Block.  We also add a Block
    ' object at runtime so the results are mixed and do not only
    ' come from the default Blocks.
    
    Dim circleObj As AcadCircle
    Dim centerPoint(0 To 2) As Double, InsertPoint(0 To 2) As Double
    Dim radius As Double
    Dim newBlock As AcadBlock, insertedBlock As AcadBlockReference
    Dim tempBlock As AcadBlock
    Dim msg As String
    
    ' Define the Circle object that will be inserted into the block
    centerPoint(0) = 0: centerPoint(1) = 0: centerPoint(2) = 0
    InsertPoint(0) = 1: InsertPoint(1) = 1: InsertPoint(2) = 0
    radius = 0.5
    
    ' Create a new block to hold the Circle object
    Set newBlock = ThisDrawing.Blocks.Add(centerPoint, "CBlock")
    
    ' Add the Circle object to the new block object
    Set circleObj = ThisDrawing.Blocks("CBlock").AddCircle(centerPoint, radius)
    
    ' Add the new block to model space
    Set insertedBlock = ThisDrawing.ModelSpace.InsertBlock(InsertPoint, "CBlock", 1, 1, 1, 0)
        
    ThisDrawing.Application.ZoomAll
    
    msg = vbCrLf & vbCrLf
    
    For Each tempBlock In ThisDrawing.Blocks
        If Not (tempBlock.IsLayout) And Not (tempBlock.IsXRef) Then
            ' Block is simple
            msg = msg & tempBlock.name & ": Simple"
        ElseIf tempBlock.IsXRef Then
            ' Block is an external reference
            msg = msg & tempBlock.name & ": External Reference"
            If tempBlock.IsLayout Then
                ' Block also contains layout geometry
                msg = msg & tempBlock.name & " and Contains Layout Geometry"
            End If
        ElseIf tempBlock.IsLayout Then
            ' Block contains layout geometry
            msg = msg & tempBlock.name & ": Contains Layout Geometry"
        End If
        
        msg = msg & vbCrLf      ' Move to next line
    Next
        
    ' Display Block information for this drawing
    MsgBox "Blocks in this drawing have the following styles: " & msg

End Sub

Sub Example_Layout()
    ' This example references the Layout object obtained from the model space.
    ' We then display information from the Layout object.
    
    Dim Layout As ACADLayout
    
    ' Attach to Layout object
    Set Layout = ThisDrawing.ModelSpace.Layout
    MsgBox "We now have access to the properties and methods of the model space Layout object!"
    
    ' Retrieve the name of the model space Layout
    MsgBox "The name of the model space Layout is: " & Layout.name
    
    ' Release object
    Set Layout = Nothing
    MsgBox "The Layout object has been released!"
End Sub

Sub Example_XRefDatabase()
    ' This example adds an external reference to the current drawing.
    ' It then cycles through each Block object in the drawing
    ' and determines the style of each Block by accessing the
    ' IsLayout and IsXRef properties of the Block.  If the Block is an
    ' XRef Block, we obtain a reference to the external Database object
    ' for that Block and display the number of Blocks the Database contains
    '
    ' This example uses the "downtown.dwg" found in the sample
    ' directory. If you do not have this image, or it is located
    ' in a different directory, insert a valid path and filename
    ' for the PathName variable below.
    
    Dim InsertPoint(0 To 2) As Double
    Dim insertedBlock As AcadExternalReference
    Dim tempBlock As AcadBlock
    Dim msg As String, PathName As String
    
    ' Define external reference to be inserted
    InsertPoint(0) = 1: InsertPoint(1) = 1: InsertPoint(2) = 0
    PathName = "c:\program files\Autocad\sample\downtown.dwg"
    
    ' Add the external block to model space
    Set insertedBlock = ThisDrawing.ModelSpace.AttachExternalReference(PathName, "XREF_IMAGE", InsertPoint, 1, 1, 1, 0, False)
        
    ThisDrawing.Application.ZoomAll
    
    msg = vbCrLf & vbCrLf
    
    For Each tempBlock In ThisDrawing.Blocks
        If tempBlock.IsXRef Then
            ' Block is an external reference, so add it to list
            msg = msg & tempBlock.name & " contains " & _
            tempBlock.XRefDatabase.Blocks.count & " blocks"
            
            msg = msg & vbCrLf      ' Insert line
        End If
    Next
        
    ' Display Block information for the XRefDatabase
    MsgBox "Externally referenced blocks attached to this drawing have the following block counts: " & msg

End Sub

Sub Example_AttachExternalReference()
    ' This example displays all the blocks in the current drawing
    ' before and after adding an external reference.
    '
    ' This example uses the "downtown.dwg" found in the sample
    ' directory. If you do not have this image, or it is located
    ' in a different directory, insert a valid path and filename
    ' for the PathName variable below.
    
    Dim InsertPoint(0 To 2) As Double
    Dim insertedBlock As AcadExternalReference
    Dim tempBlock As AcadBlock
    Dim msg As String, PathName As String
    
    ' Define external reference to be inserted
    InsertPoint(0) = 1: InsertPoint(1) = 1: InsertPoint(2) = 0
    PathName = "c:\program files\Autocad\sample\downtown.dwg"
    
    ' Display current Block information for this drawing
    GoSub ListBlocks
    
    ' Add the external reference to the drawing
    Set insertedBlock = ThisDrawing.ModelSpace.AttachExternalReference(PathName, "XREF_IMAGE", InsertPoint, 1, 1, 1, 0, False)
        
    ThisDrawing.Application.ZoomAll
    
    ' Display new Block information for this drawing
    GoSub ListBlocks
    
    Exit Sub

ListBlocks:
    msg = vbCrLf    ' Reset message
    
    For Each tempBlock In ThisDrawing.Blocks
        msg = msg & tempBlock.name & vbCrLf     ' Add Block to list
    Next
    
    MsgBox "The current blocks in this drawing are: " & msg
    
    Return
End Sub

Sub Example_Documents()
    ' This example obtains a reference to the Documents collection
    ' and displays information about the loaded documents.

    Dim Document As AcadDocument
    Dim msg As String
    msg = vbCrLf
    
    ' Cycle through the Documents collection and retrieve the names
    ' of the loaded documents
    For Each Document In Documents
        msg = msg & Document.name & vbCrLf
    Next
    
    ' Display loaded document information
    If Documents.count > 0 Then
        MsgBox "The loaded documents are: " & msg
    Else
        MsgBox "There are no loaded documents!"
    End If
End Sub

Sub Example_MenuGroups()
    ' This example uses MenuGroups to obtain a reference to the ACAD main menu.
    ' It then creates a new menu called TestMenu and inserts a menu item
    ' into it. The menu is then displayed on the menu bar.
    '
    ' The menu item will be automatically removed when ACAD is restarted
        
    Dim currMenuGroup As acadMenuGroup
    Dim newMenu As AcadPopupMenu, newMenuItem As AcadPopupMenuItem
    Dim openMacro As String
    
    On Error GoTo ERRORTRAP
    
    ' Use MenuGroups property to obtain reference to main ACAD menu
    Set currMenuGroup = ThisDrawing.Application.MenuGroups.Item("ACAD")
    
    ' Create the new menu in this group
    Set newMenu = currMenuGroup.Menus.Add("TestMenu")
    
    ' Add a menu item to the new menu and
    ' assign an Open macro (VBA equivalent of: "ESC ESC _open ")
    openMacro = Chr(3) & Chr(3) & Chr(95) & "open" & Chr(32)
    
    Set newMenuItem = newMenu.AddMenuItem(newMenu.count + 1, "Open", openMacro)
   
    ' Display the menu on the menu bar
    newMenu.InsertInMenuBar (ThisDrawing.Application.MenuBar.count + 1)
    
    MsgBox "A new menu has been added to the ACAD menu system!"
    
    Exit Sub
    
ERRORTRAP:
    MsgBox "The following error has occurred: " & Err.Description
End Sub

Sub Example_MenuBar()
    ' This example uses MenuBar to obtain a reference to the ACAD File menu.
    ' It then creates a new menu item and inserts it at the bottom of the File menu.
    '
    ' The menu item will be automatically removed when ACAD is restarted
    
    Dim menu As AcadPopupMenu, newMenuItem As AcadPopupMenuItem
    Dim openMacro As String
    
    On Error GoTo ERRORTRAP
        
    ' Use MenuBar property to obtain reference to main ACAD File menu
    Set menu = ThisDrawing.Application.MenuBar.Item("&File")
    
    ' Add a menu item to the new menu and
    ' assign an Open macro (VBA equivalent of: "ESC ESC _open ")
    openMacro = Chr(3) & Chr(3) & Chr(95) & "open" & Chr(32)
    
    ' Add a menu separator
    menu.AddSeparator (menu.count + 1)
    
    ' Add new menu item to File menu
    Set newMenuItem = menu.AddMenuItem(menu.count + 1, "NEW MENU ITEM", openMacro)
   
    MsgBox "A new menu item has been added under the File menu!"
   
    Exit Sub
    
ERRORTRAP:
    MsgBox "The following error has occurred: " & Err.Description
   
End Sub
Sub Example_Eval()
    ' This example shows how we can use Eval to run a VBA code fragment
    ' without having to create a Module or procedure.

    Dim VBACode As String
    
    ' Create VBA code fragment
    VBACode = "MsgBox ""Simple code fragment"""
    
    ' Use Eval method to evaluate our small VBA script
    Eval (VBACode)
End Sub

Sub Example_Close()
    ' This example cycles through the documents collection
    ' and closes all open drawings using the Close method.

    Dim DOC As AcadDocument
    
    ' If there are no open documents, then exit
    If Documents.count = 0 Then
        MsgBox "There are no open documents!"
        Exit Sub
    End If
    
    ' Close all open documents
    For Each DOC In Documents
        If MsgBox("Do you wish to close the document: " & DOC.WindowTitle, vbYesNo & vbQuestion) = vbYes Then
            If DOC.FullName <> "" Then
                DOC.Close
            Else
                MsgBox DOC.name & " has not been saved yet, so it will not be closed."
            End If
        End If
    Next
End Sub

Sub Example_ActiveLayout()
    ' This example cycles through the documents collection
    ' and uses the ActiveLayout object to list the active layout
    ' for all open documents.

    Dim DOC As AcadDocument
    Dim msg As String
    
    ' If there are no open documents, then exit
    If Documents.count = 0 Then
        MsgBox "There are no open documents!"
        Exit Sub
    End If
    
    msg = vbCrLf & vbCrLf   ' Start with a space
    
    ' Cycle through documents and determine the active layout name using the
    ' ActiveLayout property of the document object
    For Each DOC In Documents
        msg = msg & DOC.WindowTitle & ": " & DOC.ActiveLayout.name
    Next
    
    ' Display results
    MsgBox "The active layouts for the open drawings are: " & msg
End Sub



Sub Example_HWND()
    ' This example returns the handle (Hwnd) of a document window that can be
    ' used with WindowsAPI calls, or ActiveX components that require a handle
    ' to a window.
   
    ' If there are no open documents, then exit
    If Documents.count = 0 Then
        MsgBox "There are no open documents!"
        Exit Sub
    End If
    
    MsgBox "The HWND of the active document is: " & ActiveDocument.HWND
End Sub

Sub Example_WindowTitle()
    ' This example cycles through the documents collection
    ' and uses the WindowTitle property to create a list of all open documents.

    Dim DOC As AcadDocument
    Dim msg As String
    
    ' If there are no open documents, then exit
    If Documents.count = 0 Then
        MsgBox "There are no open documents!"
        Exit Sub
    End If
    
    msg = vbCrLf & vbCrLf   ' Start with a space
    
    ' Cycle through all open drawings and get the window title of each drawing
    For Each DOC In Documents
        msg = msg & DOC.WindowTitle
    Next
    
    ' Display a list of open drawings
    MsgBox "The open drawing titles are: " & msg
End Sub

Sub Example_Layouts()
    ' This example will access the Layouts collection for the current drawing
    ' and list basic information about the Layouts in the drawing.

    Dim Layouts As AcadLayouts, Layout As ACADLayout
    Dim msg As String
    
    ' Get layouts collection from document object
    Set Layouts = ThisDrawing.Layouts
    
    msg = vbCrLf & vbCrLf   ' Start with a space
    
    ' Get the names of every layout in this drawing
    For Each Layout In Layouts
        msg = msg & Layout.name & vbCrLf
    Next
    
    ' Display a list of available layouts
    MsgBox "There are " & Layouts.count & " layouts in " & _
            ThisDrawing.WindowTitle & ":" & msg
End Sub

Sub Example_PlotConfigurations()
    ' This example will access the PlotConfigurations collection for the current drawing,
    ' add a plot configuration, and list basic information about the
    ' plot configurations in the drawing.

    Dim PlotConfigurations As AcadPlotConfigurations
    Dim PlotConfiguration As AcadPlotConfiguration
    Dim msg As String
    
    ' Get PlotConfigurations collection from document object
    Set PlotConfigurations = ThisDrawing.PlotConfigurations
    
    ' If there aren't any plot configurations, then we'll add one
    If PlotConfigurations.count = 0 Then
        '*** Customize the new configuration to your satisfaction ***
        PlotConfigurations.Add "NEW_CONFIGURATION"
    End If
    
    msg = vbCrLf & vbCrLf   ' Start with a space
    
    ' Get the names of the plot configurations in this drawing
    For Each PlotConfiguration In PlotConfigurations
        msg = msg & PlotConfiguration.name & vbCrLf
    Next
    
    ' Display a list of available plot configurations
    MsgBox "There are " & PlotConfigurations.count & " plot configuration(s) in " & _
            ThisDrawing.WindowTitle & ":" & msg
End Sub

Sub Example_CopyFrom()
    ' This example will create two new plot configurations and will use
    ' the CopyFrom method to duplicate the settings in the first PC
    ' to the second PC.

    Dim PlotConfigurations As AcadPlotConfigurations
    Dim PlotConfiguration As AcadPlotConfiguration
    Dim NewPC1 As AcadPlotConfiguration, NewPC2 As AcadPlotConfiguration
    
    ' Get PlotConfigurations collection from document object
    Set PlotConfigurations = ThisDrawing.PlotConfigurations
    
    ' Add a new PC and customize some of the properties
    Set NewPC1 = PlotConfigurations.Add("NEW_CONFIGURATION1")
        NewPC1.PlotRotation = ac270degrees
        NewPC1.PlotHidden = True
        NewPC1.PaperUnits = acMillimeters
    
    ' Add another PC and leave default values intact
    Set NewPC2 = PlotConfigurations.Add("NEW_CONFIGURATION2")
    
    ' Show PC2 settings before we copy information from PC1
    GoSub VIEWPC2SETTINGS
    
    ' Copy setting information from PC1 to PC2
    NewPC2.CopyFrom NewPC1
    
    ' Show PC2 settings after we copy information from PC1
    GoSub VIEWPC2SETTINGS
    
    Exit Sub
    
VIEWPC2SETTINGS:
    MsgBox "The settings for NEW_CONFIGURATION2 are: " & vbCrLf & _
            "Plot Rotation: " & NewPC2.PlotRotation & vbCrLf & _
            "Plot Hidden: " & NewPC2.PlotHidden & vbCrLf & _
            "Paper Units: " & NewPC2.PaperUnits

    Return
End Sub

Sub Example_ConstantWidth()
     ' This example creates a light weight polyline in model space and
     ' uses the ConstantWidth property to determine if the polyline is
     ' comprised of equal width segments.  If the segments are not equal,
     ' we use the ConstantWidth property to set all the segments to the same
     ' width.
    
    Dim plineObj As AcadLWPolyline
    Dim points(0 To 9) As Double
    Dim msg As String, CWidth As Double
    
    ' Define the 2D polyline points
    points(0) = 1: points(1) = 1
    points(2) = 1: points(3) = 2
    points(4) = 2: points(5) = 2
    points(6) = 3: points(7) = 2
    points(8) = 4: points(9) = 4
        
    ' Create a light weight Polyline object in model space
    '
    ' * Note: We are returning the new PolyLine object into a Module
    ' level variable.  This allows us to intercept events associated
    ' with that particular object.
    Set plineObj = ThisDrawing.ModelSpace.AddLightWeightPolyline(points)
    ThisDrawing.Application.ZoomAll
    
    ' Display segment information before we alter the width of segment 1
    GoSub DISPLAYSEGMENTS
    
    ' Set the first segment with
    plineObj.SetWidth 1, 0.1, 0.3
    ThisDrawing.Regen acAllViewports
    
    ' Display segment information after we alter the width of segment 1
    GoSub DISPLAYSEGMENTS
    
    ' Make all segments uniform in width
    plineObj.ConstantWidth = 0.1
    ThisDrawing.Regen acAllViewports
    
    ' Display segment information after we make the segments uniform
    GoSub DISPLAYSEGMENTS
    
    Exit Sub
    
DISPLAYSEGMENTS:
    On Error Resume Next
    
    ' Check to see if the segment widths are uniform
    CWidth = plineObj.ConstantWidth
    
    ' If ConstantWidth returns an error, we know the
    ' segments are not all the same width
    If Err.Description = "Invalid input" Then
        msg = " are not equal."
    Else
        msg = " are all equal."
    End If
    On Error GoTo 0
    
    MsgBox "The segments of the new polyline" & msg
    
    Return
End Sub

Sub Example_Plottable()
    ' This example creates a new layer called "New_Layer".  It then uses
    ' the Plottable property of each Layer to display whether or not that layer
    ' is plottable.  The user has the ability to toggle the plottable state
    ' for each layer, and the final plottable status for all layers is displayed.
    
    Dim layerObj As AcadLayer, tempLayer As AcadLayer
    Dim msg As String

    ' Add the layer to the layers collection
    Set layerObj = ThisDrawing.Layers.Add("New_Layer")
    
    ' Make the new layer the active layer for the drawing
    ThisDrawing.ActiveLayer = layerObj
    
    ' Cycle through the layers and allow user to make them plottable or not
    
    For Each tempLayer In ThisDrawing.Layers
        If tempLayer.Plottable Then     ' Determine if this layer is plottable
            If MsgBox("The layer '" & tempLayer.name & "' will plot.  Would you like to turn off plotting for this layer?", vbYesNo & vbQuestion) = vbYes Then
                tempLayer.Plottable = False     ' Change plottable state
            End If
        Else
            If MsgBox("The layer '" & tempLayer.name & "' will not plot.  Would you like to turn on plotting for this layer?", vbYesNo & vbQuestion) = vbYes Then
                tempLayer.Plottable = True      ' Change plottable state
            End If
        End If
    Next
    
    ' Display the new plottable status of the layers in this drawing
    
    For Each tempLayer In ThisDrawing.Layers
        ' Determine if this layer is plottable
        If tempLayer.Plottable Then
            msg = msg & "The layer '" & tempLayer.name & "' will plot." & vbCrLf
        Else
            msg = msg & "The layer '" & tempLayer.name & "' will not plot." & vbCrLf
        End If
    Next

    MsgBox msg
End Sub

Sub Example_ViewportDefault()
    ' This example creates a new layer called "New_Layer".  It then uses
    ' the ViewportDefault property of each Layer to display whether or not that layer
    ' is frozen in new viewports.  The user has the ability to toggle whether or not
    ' each layer will be frozen in new viewports, and the final ViewportDefault status
    ' for all layers is displayed.
    
    Dim layerObj As AcadLayer, tempLayer As AcadLayer
    Dim msg As String

    ' Add the layer to the layers collection
    Set layerObj = ThisDrawing.Layers.Add("New_Layer")
    
    ' Make the new layer the active layer for the drawing
    ThisDrawing.ActiveLayer = layerObj
    
    ' Cycle through the layers and allow user to make them frozen in new viewports or not
    
    For Each tempLayer In ThisDrawing.Layers
        If tempLayer.ViewportDefault Then     ' Determine if this layer is fozen in new viewports
            If MsgBox("The layer '" & tempLayer.name & "' will be frozen in new viewports.  Would you like to make this layer unfrozen in new viewports?", vbYesNo & vbQuestion) = vbYes Then
                tempLayer.ViewportDefault = False     ' Change frozen state
            End If
        Else
            If MsgBox("The layer '" & tempLayer.name & "' will not be frozen in new viewports.  Would you like to make this layer frozen in new viewports?", vbYesNo & vbQuestion) = vbYes Then
                tempLayer.ViewportDefault = True      ' Change frozen state
            End If
        End If
    Next
    
    ' Display the new viewport freeze status of the layers in this drawing
    
    For Each tempLayer In ThisDrawing.Layers
        ' Determine if this layer is frozen in new viewports
        If tempLayer.ViewportDefault Then
            msg = msg & "The layer '" & tempLayer.name & "' will be frozen in new viewports." & vbCrLf
        Else
            msg = msg & "The layer '" & tempLayer.name & "' will not be frozen in new viewports." & vbCrLf
        End If
    Next

    MsgBox msg
End Sub

Sub Example_GetRemoteFile()
    ' This example will prompt the user for a URL to download and will verify that
    ' a proper URL was entered.  After downloading, the example will attempt load
    ' the downloaded URL as a drawing.
    '
    ' * Note: Remember to delete the downloaded file from your disk drive when finished.
    
    Dim Utility As AcadUtility
    Dim URL As String, DestFile As String, FileURL As String
    
    Set Utility = ThisDrawing.Utility   ' Connect to Utility object
    
GETURL:
    ' Prompt user for a URL to download.  This should be a URL to an AutoCAD drawing file.
    URL = InputBox("Enter the complete URL of the file you wish to download. " & _
                    "Enter BROWSER to select the URL from a web browser", _
                    "Enter URL To Download", URL)
    
    URL = Trim(URL)                     ' Get rid of blank spaces
    
    If URL = "" Then Exit Sub           ' Did user cancel

    ' Does the user want to select from a browser
    If StrComp(URL, "BROWSER", vbTextCompare) = 0 Then
        Utility.LaunchBrowserDialog _
        URL, "AutoCAD Browser", "Open", "http://www.autodesk.com", "ACADBROWSER", True
        
        GoTo GETURL     ' Return to display chosen URL and allow modifications
    End If

    ' Determine if user entered a valid URL, if not prompt again
    If Not (Utility.IsURL(URL)) Then
        MsgBox "The URL you entered is not valid.  Make sure the syntax is a valid URL."
        GoTo GETURL
    End If
        
    ' Download URL
    Utility.GetRemoteFile URL, DestFile, True
    
    ' Display download file information
    MsgBox URL & " was downloaded to: " & DestFile & vbCrLf & vbCrLf & _
           "Press any key to attempt to load the new file as a drawing."

    ' Attempt to load file as drawing, if an error occurs, this was probably not a drawing
    ' file, but rather the text from a web page.
    ' Try loading the downloaded file into a text editor to view the contents.
    On Error Resume Next
    ThisDrawing.Application.Documents.Open DestFile
    If Err.Number <> 0 Then
        MsgBox "Error loading downloaded file as a drawing: " & Err.Description & vbCrLf & vbCrLf & _
               "This is probably not a valid drawing file!"
    End If
    On Error GoTo 0
    
    ' Use IsRemoteFile to determine is this file was downloaded from a URL.
    ' If it was, display the URL it was downloaded from
    '
    ' * Note: Although we already know the results IsRemoteFile will return
    ' since we just downloaded the file, it is important to know how this
    ' method can be used.
    If Utility.IsRemoteFile(DestFile, FileURL) Then
        MsgBox "The file: " & DestFile & " is a downloaded file and was downloaded from: " & FileURL
    Else
        MsgBox "The file: " & DestFile & " is not a downloaded file."
    End If

End Sub

Sub Example_IsURL()
    ' This example will prompt the user for a URL to download and will verify that
    ' a proper URL was entered.  After downloading, the example will attempt load
    ' the downloaded URL as a drawing.
    '
    ' * Note: Remember to delete the downloaded file from your disk drive when finished.
    
    Dim Utility As AcadUtility
    Dim URL As String, DestFile As String, FileURL As String
    
    Set Utility = ThisDrawing.Utility   ' Connect to Utility object
    
GETURL:
    ' Prompt user for a URL to download.  This should be a URL to an AutoCAD drawing file.
    URL = InputBox("Enter the complete URL of the file you wish to download. " & _
                    "Enter BROWSER to select the URL from a web browser", _
                    "Enter URL To Download", URL)
    
    URL = Trim(URL)                     ' Get rid of blank spaces
    
    If URL = "" Then Exit Sub           ' Did user cancel

    ' Does the user want to select from a browser
    If StrComp(URL, "BROWSER", vbTextCompare) = 0 Then
        Utility.LaunchBrowserDialog _
        URL, "AutoCAD Browser", "Open", "http://www.autodesk.com", "ACADBROWSER", True
        
        GoTo GETURL     ' Return to display chosen URL and allow modifications
    End If

    ' Determine if user entered a valid URL, if not prompt again
    If Not (Utility.IsURL(URL)) Then
        MsgBox "The URL you entered is not valid.  Make sure the syntax is a valid URL."
        GoTo GETURL
    End If
        
    ' Download URL
    Utility.GetRemoteFile URL, DestFile, True
    
    ' Display download file information
    MsgBox URL & " was downloaded to: " & DestFile & vbCrLf & vbCrLf & _
           "Press any key to attempt to load the new file as a drawing."

    ' Attempt to load file as drawing, if an error occurs, this was probably not a drawing
    ' file, but rather the text from a web page.
    ' Try loading the downloaded file into a text editor to view the contents.
    On Error Resume Next
    ThisDrawing.Application.Documents.Open DestFile
    If Err.Number <> 0 Then
        MsgBox "Error loading downloaded file as a drawing: " & Err.Description & vbCrLf & vbCrLf & _
               "This is probably not a valid drawing file!"
    End If
    On Error GoTo 0
    
    ' Use IsRemoteFile to determine is this file was downloaded from a URL.
    ' If it was, display the URL it was downloaded from
    '
    ' * Note: Although we already know the results IsRemoteFile will return
    ' since we just downloaded the file, it is important to know how this
    ' method can be used.
    If Utility.IsRemoteFile(DestFile, FileURL) Then
        MsgBox "The file: " & DestFile & " is a downloaded file and was downloaded from: " & FileURL
    Else
        MsgBox "The file: " & DestFile & " is not a downloaded file."
    End If

End Sub

Sub Example_LaunchBrowserDialog()
    ' This example will prompt the user for a URL to download and will verify that
    ' a proper URL was entered.  After downloading, the example will attempt load
    ' the downloaded URL as a drawing.
    '
    ' * Note: Remember to delete the downloaded file from your disk drive when finished.
    
    Dim Utility As AcadUtility
    Dim URL As String, DestFile As String, FileURL As String
    
    Set Utility = ThisDrawing.Utility   ' Connect to Utility object
    
GETURL:
    ' Prompt user for a URL to download.  This should be a URL to an AutoCAD drawing file.
    URL = InputBox("Enter the complete URL of the file you wish to download. " & _
                    "Enter BROWSER to select the URL from a web browser", _
                    "Enter URL To Download", URL)
    
    URL = Trim(URL)                     ' Get rid of blank spaces
    
    If URL = "" Then Exit Sub           ' Did user cancel

    ' Does the user want to select from a browser
    If StrComp(URL, "BROWSER", vbTextCompare) = 0 Then
        Utility.LaunchBrowserDialog _
        URL, "AutoCAD Browser", "Open", "http://www.autodesk.com", "ACADBROWSER", True
        
        GoTo GETURL     ' Return to display chosen URL and allow modifications
    End If

    ' Determine if user entered a valid URL, if not prompt again
    If Not (Utility.IsURL(URL)) Then
        MsgBox "The URL you entered is not valid.  Make sure the syntax is a valid URL."
        GoTo GETURL
    End If
        
    ' Download URL
    Utility.GetRemoteFile URL, DestFile, True
    
    ' Display download file information
    MsgBox URL & " was downloaded to: " & DestFile & vbCrLf & vbCrLf & _
           "Press any key to attempt to load the new file as a drawing."

    ' Attempt to load file as drawing, if an error occurs, this was probably not a drawing
    ' file, but rather the text from a web page.
    ' Try loading the downloaded file into a text editor to view the contents.
    On Error Resume Next
    ThisDrawing.Application.Documents.Open DestFile
    If Err.Number <> 0 Then
        MsgBox "Error loading downloaded file as a drawing: " & Err.Description & vbCrLf & vbCrLf & _
               "This is probably not a valid drawing file!"
    End If
    On Error GoTo 0
    
    ' Use IsRemoteFile to determine is this file was downloaded from a URL.
    ' If it was, display the URL it was downloaded from
    '
    ' * Note: Although we already know the results IsRemoteFile will return
    ' since we just downloaded the file, it is important to know how this
    ' method can be used.
    If Utility.IsRemoteFile(DestFile, FileURL) Then
        MsgBox "The file: " & DestFile & " is a downloaded file and was downloaded from: " & FileURL
    Else
        MsgBox "The file: " & DestFile & " is not a downloaded file."
    End If

End Sub

Sub Example_IsRemoteFile()
    ' This example will prompt the user for a URL to download and will verify that
    ' a proper URL was entered.  After downloading, the example will attempt load
    ' the downloaded URL as a drawing.
    '
    ' * Note: Remember to delete the downloaded file from your disk drive when finished.
    
    Dim Utility As AcadUtility
    Dim URL As String, DestFile As String, FileURL As String
    
    Set Utility = ThisDrawing.Utility   ' Connect to Utility object
    
GETURL:
    ' Prompt user for a URL to download.  This should be a URL to an AutoCAD drawing file.
    URL = InputBox("Enter the complete URL of the file you wish to download. " & _
                    "Enter BROWSER to select the URL from a web browser", _
                    "Enter URL To Download", URL)
    
    URL = Trim(URL)                     ' Get rid of blank spaces
    
    If URL = "" Then Exit Sub           ' Did user cancel

    ' Does the user want to select from a browser
    If StrComp(URL, "BROWSER", vbTextCompare) = 0 Then
        Utility.LaunchBrowserDialog _
        URL, "AutoCAD Browser", "Open", "http://www.autodesk.com", "ACADBROWSER", True
        
        GoTo GETURL     ' Return to display chosen URL and allow modifications
    End If

    ' Determine if user entered a valid URL, if not prompt again
    If Not (Utility.IsURL(URL)) Then
        MsgBox "The URL you entered is not valid.  Make sure the syntax is a valid URL."
        GoTo GETURL
    End If
        
    ' Download URL
    Utility.GetRemoteFile URL, DestFile, True
    
    ' Display download file information
    MsgBox URL & " was downloaded to: " & DestFile & vbCrLf & vbCrLf & _
           "Press any key to attempt to load the new file as a drawing."

    ' Attempt to load file as drawing, if an error occurs, this was probably not a drawing
    ' file, but rather the text from a web page.
    ' Try loading the downloaded file into a text editor to view the contents.
    On Error Resume Next
    ThisDrawing.Application.Documents.Open DestFile
    If Err.Number <> 0 Then
        MsgBox "Error loading downloaded file as a drawing: " & Err.Description & vbCrLf & vbCrLf & _
               "This is probably not a valid drawing file!"
    End If
    On Error GoTo 0
    
    ' Use IsRemoteFile to determine is this file was downloaded from a URL.
    ' If it was, display the URL it was downloaded from
    '
    ' * Note: Although we already know the results IsRemoteFile will return
    ' since we just downloaded the file, it is important to know how this
    ' method can be used.
    If Utility.IsRemoteFile(DestFile, FileURL) Then
        MsgBox "The file: " & DestFile & " is a downloaded file and was downloaded from: " & FileURL
    Else
        MsgBox "The file: " & DestFile & " is not a downloaded file."
    End If

End Sub

Sub Example_Prompt()
    ' This example will use the Utility object to post a prompt to the
    ' AutoCAD command line.  To see the results after running the example,
    ' switch to AutoCAD and look at the command line.
    
    ThisDrawing.Utility.prompt "Press any key..."
End Sub

Sub Example_PutRemoteFile()
    ' This example transfers a local file to a remote URL.  Since this example
    ' relies on both a remote server name and a local file, you will have to
    ' modify both the DestURL and LocalFile variables below to run this example.
    
    Dim DestURL As String, LocalFile As String
    
    ' Define source and destination
    DestURL = "ftp://www.myserver.com/autocadfiles/"
    LocalFile = "c:\program files\Autocad\sample\downtown.jpg"
    
    ' Transfer local file to remote location
    ThisDrawing.Utility.PutRemoteFile DestURL, LocalFile
    
    MsgBox LocalFile & " was just transfered to: " & DestURL
End Sub

Sub Example_GetSubEntity()
    ' This example prompts the user to select on object on the screen with a mouse click,
    ' and returns some information about the selected object.
    
    Dim Object As Object
    Dim PickedPoint As Variant, TransMatrix As Variant, ContextData As Variant
    Dim HasContextData As String
    
    On Error GoTo NOT_ENTITY
        
TRYAGAIN:
        
    MsgBox "Use the mouse to click on an entity in the current drawing after dismissing this dialog box."
        
    ' Get information about selected object
    ThisDrawing.Utility.GetSubEntity Object, PickedPoint, TransMatrix, ContextData
    
    ' Process and display selected object properties
    HasContextData = IIf(VarType(ContextData) = vbEmpty, " does not ", " does ")
    
    MsgBox "The object you chose was an: " & TypeName(Object) & vbCrLf & _
            "Your point of selection was: " & PickedPoint(0) & ", " & _
                                              PickedPoint(1) & ", " & _
                                              PickedPoint(2) & vbCrLf & _
            "This object" & HasContextData & "have nested objects."
    
    Exit Sub
    
NOT_ENTITY:
    ' If you click on empty space or do not select an entity,
    ' this error will be generated
    If MsgBox("You have not selected an entity.  Press OK to try again.", _
               vbOKCancel & vbInformation) = vbOK Then
        Resume TRYAGAIN
    End If
End Sub

Sub Example_PaperUnits()
    ' This example will access the Layouts collection for the current drawing
    ' and list basic information about the paper units used for each Layout.

    Dim Layouts As AcadLayouts, Layout As ACADLayout
    Dim msg As String
    Dim Measurement As String
    
    ' Get layouts collection from document object
    Set Layouts = ThisDrawing.Layouts
    
    msg = vbCrLf & vbCrLf   ' Start with a space
    
    ' Get the paper units information of every layout in this drawing
    For Each Layout In Layouts
        ' Are we using inches or millimeters?
        Measurement = IIf(Layout.PaperUnits = acInches, " inches", " millimeters")
        
        ' Format for display
        msg = msg & Layout.name & " is using" & Measurement & vbCrLf
    Next
    
    ' Display paper units information
    MsgBox "The paper units used in the current drawing are: " & msg
End Sub
Sub Example_UseStandardScale()
    ' This example will access the Layouts collection for the current drawing
    ' and list the status of UseStandardScale for each Layout.

    Dim Layouts As AcadLayouts, Layout As ACADLayout
    Dim msg As String
    
    ' Get layouts collection from document object
    Set Layouts = ThisDrawing.Layouts
    
    msg = ""
    
    ' Get the UseStandardScale information of every layout in this drawing
    For Each Layout In Layouts
        If Layout.UseStandardScale Then
            msg = msg & Layout.name & " uses the standard scale." & vbCrLf
        Else
            msg = msg & Layout.name & " uses a custom scale." & vbCrLf
        End If
    Next
    
    ' Display the information
    MsgBox msg
End Sub
Sub Example_StandardScale()
    ' This example will access the active layout for the current drawing
    ' and list the standard scale for that Layout.
    ' It then changes the standard scale for the layout, and finally
    ' resets the scale back to its original value.

    Dim Layout As ACADLayout
    Dim currScale As Integer
    
    ' Get the activeLayout
    Set Layout = ThisDrawing.ActiveLayout
    
    ' Find the current standard scale
    currScale = Layout.StandardScale
    MsgBox "The current standard scale is : " & Layout.StandardScale
    
    ' Change the standard scale to 100:1
    Layout.StandardScale = ac100_1
    MsgBox "The new standard scale is : " & Layout.StandardScale
    
    ' Reset the original standard scale
    Layout.StandardScale = currScale
    MsgBox "The new standard scale is : " & Layout.StandardScale
    
End Sub
Sub Example_PlotHidden()
    ' This example will access the Layouts collection for the current drawing
    ' and display whether the objects for each layout are to be hidden during a plot.
    ' It will then toggle the state of PlotHidden for "Layout1" and re-display the
    ' PlotHidden state for each Layout.

    Dim Layouts As AcadLayouts, Layout As ACADLayout
    Dim msg As String
    Dim IsHidden As String
    
    ' Get layouts collection from document object
    Set Layouts = ThisDrawing.Layouts
    
    ' Display current hidden information
    GoSub DISPLAY
    
    ' Toggle object hidden state for Layout1
    Layouts("Layout1").PlotHidden = Not (Layouts("Layout1").PlotHidden)
    
    ' Display new hidden information
    GoSub DISPLAY
    
    Exit Sub
    
DISPLAY:
    msg = ""    ' Clear message
    
    ' Determine whether the objects for each layout are hidden during a plot
    For Each Layout In Layouts
        ' Are these objects hidden?
        IsHidden = IIf(Layout.PlotHidden, " are hidden ", " are not hidden ")
        
        ' Format for display
        msg = msg & "Objects for " & Layout.name & IsHidden & "during a plot." & vbCrLf
    Next
    
    ' Display layout information
    MsgBox msg
    
    Return
End Sub


Sub Example_Annotation()
    ' This example creates a leader in model space with an associated
    ' annotation and then checks for the existence of an
    ' Annotation object for the new Leader
   
    Dim leaderObj As AcadLeader, MTextObj As AcadMText
    Dim points(0 To 8) As Double, insertionPoint(0 To 2) As Double, width As Double
    Dim leaderType As Integer
    Dim annotationObject As Object
    Dim textString As String, msg As String
    
    ' Define the new MText object
    textString = "Hello, World."
    insertionPoint(0) = 5: insertionPoint(1) = 5: insertionPoint(2) = 0
    width = 2
    
    ' Create the MText object in model space
    Set MTextObj = ThisDrawing.ModelSpace.AddMText(insertionPoint, width, textString)
    
    ' Data for Leader
    points(0) = 0: points(1) = 0: points(2) = 0
    points(3) = 4: points(4) = 4: points(5) = 0
    points(6) = 4: points(7) = 5: points(8) = 0
    leaderType = acLineWithArrow
       
    ' Create the Leader object in model space and Associate new MText object
    ' with new Leader by making the MText object the annotation for the Leader
    Set annotationObject = MTextObj
    Set leaderObj = ThisDrawing.ModelSpace.AddLeader(points, annotationObject, leaderType)
    ThisDrawing.Application.ZoomAll

    ' Display whether or not this particular Leader has an associated Annotation
    msg = IIf(leaderObj.Annotation Is Nothing, "does not have", "has")
    MsgBox "The new Leader object " & msg & " an associated Annotation object."
End Sub

Sub Example_ConfigName()
    ' This example will add a new plot configuration to the current drawing.
    ' It will then list the plotter configuration file name for each Layout
    ' in the current drawing, change the configuration for Layout1 to "DWF Classic.pc3"
    ' and re-display the configuration information for the drawing.
    '
    ' * Note: File names may differ on your system, so be prepared to change
    ' the configuration file name we use in the example to a file that exists
    ' on your system.

    Dim Layouts As AcadLayouts, Layout As ACADLayout
    Dim msg As String
    Dim ACADPref As AcadPreferencesFiles
    Dim originalValue As Variant
    
    ' Get the files preferences object
    Set ACADPref = ThisDrawing.Application.preferences.Files

    ' Read and display the original value
    originalValue = ACADPref.PrinterConfigPath
    
    ' Get layouts collection from document object
    Set Layouts = ThisDrawing.Layouts
    
    ' Display current plotter configuration information
    GoSub DISPLAY_CONFIG
    
    ' Change plotter configuration file for "Layout1"
    Layouts("Layout1").ConfigName = "DWF Classic.pc3"
    
    ' Display new plotter configuration information
    GoSub DISPLAY_CONFIG
    
    Exit Sub
        
DISPLAY_CONFIG:
    msg = vbCrLf & vbCrLf   ' Start with a space
    
    ' Format and display current directory for configuration files
    msg = msg & vbTab & "Directories that will be scanned for the plotter configuration files are: " _
                & vbCrLf & vbTab & vbTab & originalValue & vbCrLf & vbCrLf
    
    ' Get the plotter configuration name of every layout in this drawing
    For Each Layout In Layouts
        ' Format for display
        msg = msg & vbTab & Layout.name & " is using configuration: " & Layout.ConfigName & vbCrLf
    Next
    
    ' Display paper units information
    MsgBox "The plotter configuration information used in the current drawing is listed below." & msg
    
    Return
End Sub
Sub Example_ShowRotation()
    ' This example adds a raster image in model space and rotates the image.
    ' One rotation is done without angle limits, one is done with ShowRotation
    ' which limits rotations to 90 degrees
    
    ' This example uses the "downtown.jpg" found in the sample
    ' directory. If you do not have this image, or it is located
    ' in a different directory, insert a valid path and filename
    ' for the imageName variable below.
    
    Dim insertionPoint(0 To 2) As Double
    Dim scalefactor As Double, rotationAngle As Double
    Dim imageName As String
    Dim rasterObj As AcadRasterImage
    
    imageName = "c:\Autocad\sample\downtown.jpg"
    
    ' Define Raster object
    insertionPoint(0) = 5: insertionPoint(1) = 5: insertionPoint(2) = 0
    scalefactor = 1#: rotationAngle = 0
    
    On Error GoTo ERRORTRAP
    
    ' Loads a raster image into model space
    Set rasterObj = ThisDrawing.ModelSpace.AddRaster(imageName, insertionPoint, scalefactor, rotationAngle)
        
    ' Limit the raster image rotations to 90 degrees
    rasterObj.ShowRotation = True
    
    ' Rotate the raster image 180 degrees
    rasterObj.Rotate insertionPoint, 180
    ThisDrawing.Application.ZoomAll
    
    Exit Sub
    
    ' If we ran into an error (most likely a problem with the file path),
    ' then display error message
ERRORTRAP:
    If Err.Description <> "" Then
        MsgBox Err.Description
    End If
End Sub
Sub Example_ActiveDimStyle()
    ' This example returns the current dimension style
    ' and then sets a new style.
    ' Finally, it returns the style to the previous setting.
    Dim newDimStyle As AcadDimStyle
    Dim currDimStyle As AcadDimStyle
    
    ' Return current dimension style of active document
    Set currDimStyle = ThisDrawing.ActiveDimStyle
    MsgBox "The current dimension style is " & currDimStyle.name, vbInformation, "ActiveDimStyle Example"
    
    ' Create a dimension style and makes it current
    Set newDimStyle = ThisDrawing.DimStyles.Add("TestDimStyle")
    ThisDrawing.ActiveDimStyle = newDimStyle    ' set current dimension style to newDimStyle
    MsgBox "The new dimension style is " & newDimStyle.name, vbInformation, "ActiveDimStyle Example"
    
    ' Reset the dimension style to its previous setting
    ThisDrawing.ActiveDimStyle = currDimStyle
    MsgBox "The dimension style is reset to " & currDimStyle.name, vbInformation, "ActiveDimStyle Example"
End Sub
Sub Example_Application()
    ' This example creates a line and then uses the
    ' Application property of the line to return the
    ' application name.
    Dim lineObj As AcadLine
    Dim startPoint(0 To 2) As Double
    Dim endPoint(0 To 2) As Double
    Dim myApp As AcadApplication
    
    ' Create a new line reference
    startPoint(0) = 0: startPoint(1) = 0: startPoint(2) = 0
    endPoint(0) = 2: endPoint(1) = 2: endPoint(2) = 0
    Set lineObj = ThisDrawing.ModelSpace.AddLine(startPoint, endPoint)
    lineObj.Update

    ' Return the application for the object
    Set myApp = lineObj.Application
    
    ' Display the name of the application
    MsgBox "The application name is: " & myApp.name, vbInformation, "Application Example"
End Sub

Sub Example_ActiveDocument()
    Dim activeDoc As AcadDocument
    ' Returns current document in AutoCAD
    Set activeDoc = ThisDrawing.Application.ActiveDocument
    MsgBox "The active document is: " & activeDoc.name, vbInformation, "ActiveDocument Example"
End Sub

Sub Example_ActiveLayer()
    ' This example returns the current layer
    ' and then adds a new layer.
    ' Finally, it returns the layer to the previous setting.
    Dim currLayer As AcadLayer
    Dim newLayer As AcadLayer
    
    ' Return the current layer of the active document
    Set currLayer = ThisDrawing.ActiveLayer
    MsgBox "The current layer is " & currLayer.name, vbInformation, "ActiveLayer Example"
    
    ' Create a Layer and make it the active layer
    Set newLayer = ThisDrawing.Layers.Add("TestLayer")
    ThisDrawing.ActiveLayer = newLayer
    MsgBox "The new layer is " & newLayer.name, vbInformation, "ActiveLayer Example"

    ' Reset the layer to its previous setting
    ThisDrawing.ActiveLayer = currLayer
    MsgBox "The active layer is reset to " & currLayer.name, vbInformation, "ActiveLayer Example"
End Sub

Sub Example_ActiveLinetype()
    ' This example finds the current linetype. It then sets
    ' the new linetype to be the first entry in the linetype
    ' collection that is not equal to the current linetype.
    ' Finally, it resets the active linetype to the original
    ' setting.
    
    Dim currLineType As AcadLineType
    Dim newLineType As AcadLineType
    
    ' Find the current LineType of the active document
    Set currLineType = ThisDrawing.ActiveLinetype
    MsgBox "The current linetype is " & currLineType.name, vbInformation, "ActiveLinetype Example"
    
    ' Set the current Linetype to anything else in the collection
    Dim entry
    Dim found As Boolean
    For Each entry In ThisDrawing.Linetypes
        If StrComp(entry.name, currLineType.name, 1) <> 0 Then
            Set newLineType = entry
            found = True
            Exit For
        End If
    Next
    If found Then
        ThisDrawing.ActiveLinetype = newLineType
        MsgBox "The new linetype is " & newLineType.name, vbInformation, "ActiveLinetype Example"
        ' Reset the linetype to the previous setting
        ThisDrawing.ActiveLinetype = currLineType
        MsgBox "The active linetype is reset to " & currLineType.name, vbInformation, "ActiveLinetype Example"
    End If
End Sub

Sub Example_ActivePViewport()
   
    Dim newPViewport As AcadPViewport
    Dim centerPoint(0 To 2) As Double
    Dim height As Double
    Dim width As Double
    height = 5#
    width = 5#
    centerPoint(0) = 5#: centerPoint(1) = 5#: centerPoint(2) = 0#
    
    ' Create a paperspace Viewport object
    ThisDrawing.ActiveSpace = acPaperSpace
    Set newPViewport = ThisDrawing.PaperSpace.AddPViewport(centerPoint, width, height)
    ZoomAll
    newPViewport.DISPLAY (True)
    
    ' Before making a pViewport active,
    ' the mspace property needs to be True
    ThisDrawing.mspace = True
    ThisDrawing.ActivePViewport = newPViewport
End Sub
Sub Example_ActiveTextStyle()
    ' This example returns the current text style
    ' and then sets a new style.
    ' Finally, it returns the style to the previous setting.
    Dim newTextStyle As AcadTextStyle
    Dim currTextStyle As AcadTextStyle
    
    ' Return current text style of active document
    Set currTextStyle = ThisDrawing.ActiveTextStyle
    MsgBox "The current text style is " & currTextStyle.name, vbInformation, "ActiveTextStyle Example"
    
    ' Create a text style and makes it current
    Set newTextStyle = ThisDrawing.TextStyles.Add("TestTextStyle")
    ThisDrawing.ActiveTextStyle = newTextStyle
    MsgBox "The new text style is " & newTextStyle.name, vbInformation, "ActiveTextStyle Example"
    
    ' Reset the text style to its previous setting
    ThisDrawing.ActiveTextStyle = currTextStyle
    MsgBox "The text style is reset to " & currTextStyle.name, vbInformation, "ActiveTextStyle Example"
End Sub

Sub Example_ActiveUCS()
    ' This example returns the current UCS
    ' and then sets a new UCS.
    ' Finally, it returns the UCS to the previous setting.
    
    Dim newUCS As AcadUCS
    Dim currUCS As AcadUCS
    Dim origin(0 To 2) As Double
    Dim xAxis(0 To 2) As Double
    Dim yAxis(0 To 2) As Double
    
    ' Return current UCS of active document
    Set currUCS = ThisDrawing.ActiveUCS
    MsgBox "The current UCS is " & currUCS.name, vbInformation, "ActiveUCS Example"
    
    ' Create a UCS and makes it current
    origin(0) = 0: origin(1) = 0: origin(2) = 0
    xAxis(0) = 1: xAxis(1) = 1: xAxis(2) = 0
    yAxis(0) = -1: yAxis(1) = 1: yAxis(2) = 0
    Set newUCS = ThisDrawing.UserCoordinateSystems.Add(origin, xAxis, yAxis, "_TestUCS")
    ThisDrawing.ActiveUCS = newUCS
    MsgBox "The new UCS is " & newUCS.name, vbInformation, "ActiveUCS Example"
    
    ' Reset the UCS to its previous setting
    ThisDrawing.ActiveUCS = currUCS
    MsgBox "The UCS is reset to " & currUCS.name, vbInformation, "ActiveUCS Example"
End Sub

Sub Example_ActiveViewport()
    ' This example returns the current viewport.
    ' It then creates a new viewport and makes it active.
    ' Then it splits the viewport into 4 windows.
    ' It then takes one of the 4 windows, and splits that
    ' window into half horizontally.
    Dim currViewport As AcadViewport
    Dim newViewport As AcadViewport
    
    ' Returns current viewport of active document
    Set currViewport = ThisDrawing.ActiveViewport
    MsgBox "The current viewport is " & currViewport.name, vbInformation, "ActiveViewport Example"
    
    ' Create a new viewport and make it active
    Set newViewport = ThisDrawing.Viewports.Add("TESTVIEWPORT")
    ThisDrawing.ActiveViewport = newViewport
    MsgBox "The new active viewport is " & newViewport.name, vbInformation, "ActiveViewport Example"
    
    ' Split the viewport in 4 windows
    newViewport.Split acViewport4
    
    ' Make the newly split viewport active
    ThisDrawing.ActiveViewport = newViewport
    
    ' Note that current drawing layout will show 4 windows.
    ' However, only one of the windows will be active.
    ' The following code sets the lower left corner window
    ' to be the active window and then splits that
    ' window into 2 horizontal windows.
    Dim entry
    For Each entry In ThisDrawing.Viewports
        If entry.name = "TESTVIEWPORT" Then
            Dim lowerLeft
            lowerLeft = entry.LowerLeftCorner
            If lowerLeft(0) = 0 And lowerLeft(1) = 0 Then
                Set newViewport = entry
                Exit For
            End If
        End If
    Next
    newViewport.Split acViewport2Horizontal
    ThisDrawing.ActiveViewport = newViewport
End Sub
Sub Example_Area()
    ' This example creates a polyline object and
    ' then uses the area property to find the
    ' area of that polyline.
    
    Dim plineObj As AcadLWPolyline
    Dim points(0 To 5) As Double
    Dim plineArea As Double

    ' Establish the points for the Polyline
    points(0) = 3: points(1) = 7
    points(2) = 9: points(3) = 2
    points(4) = 3: points(5) = 5
    
    ' Create the polyline in modelspace
    Set plineObj = ThisDrawing.ModelSpace.AddLightWeightPolyline(points)
    
    ' Close the polyline and update display of it
    plineObj.Closed = True
    plineObj.Update
    ZoomAll
    
    ' Get the area of the polyline
    plineArea = plineObj.Area
    
    MsgBox "The area of the new Polyline is: " & plineArea, vbInformation, "Area Example"
End Sub
Sub Example_ActiveSpace()
    ' This example toggles the ActiveSpace property from
    ' paperspace to model space.
    ' Display the current setting for TILEMODE
    MsgBox "TILEMODE = " & ThisDrawing.ActiveSpace, vbInformation, "ActiveSpace Example"
     
    ' Changes active document to paper space
    ThisDrawing.ActiveSpace = acPaperSpace
    MsgBox "TILEMODE = " & ThisDrawing.ActiveSpace, vbInformation, "ActiveSpace Example"
   
    ' Changes active document to model space
    ThisDrawing.ActiveSpace = acModelSpace
    MsgBox "TILEMODE = " & ThisDrawing.ActiveSpace, vbInformation, "ActiveSpace Example"
End Sub

Sub Example_Split()
    ' This example creates a new viewport and makes it active.
    ' Then it splits the viewport into 4 windows.
    ' It then takes one of the 4 windows, and splits that
    ' window into half horizontally.
    Dim newViewport As AcadViewport
       
    ' Create a new viewport and make it active
    Set newViewport = ThisDrawing.Viewports.Add("TESTVIEWPORT")
    ThisDrawing.ActiveViewport = newViewport
    
    ' Split the viewport in 4 windows
    newViewport.Split acViewport4
    
    ' Make the newly split viewport active
    ThisDrawing.ActiveViewport = newViewport
    
    ' Note that current drawing layout will show 4 windows.
    ' However, only one of the windows will be active.
    ' The following code sets the lower left corner window
    ' to be the active window and then splits that
    ' window into 2 horizontal windows.
    Dim entry
    For Each entry In ThisDrawing.Viewports
        If entry.name = "TESTVIEWPORT" Then
            Dim lowerLeft
            lowerLeft = entry.LowerLeftCorner
            If lowerLeft(0) = 0 And lowerLeft(1) = 0 Then
                Set newViewport = entry
                Exit For
            End If
        End If
    Next
    newViewport.Split acViewport2Horizontal
    ThisDrawing.ActiveViewport = newViewport
End Sub

Sub Example_AttachmentPoint()
    Dim MTextObj As AcadMText
    Dim width As Double
    Dim text As String
    Dim count As Integer
    Dim attachPoint As String
    Dim corner(0 To 2) As Double
        
    corner(0) = 3#: corner(1) = 3#: corner(2) = 0#
    width = 10
    text = "Hello, World."
    ' Creates a MText object in model space
    Set MTextObj = ThisDrawing.ModelSpace.AddMText(corner, width, text)

    For count = 1 To 9
        MTextObj.AttachmentPoint = count
    
        ' Gets the attachment point of an MText object
        attachPoint = Choose(MTextObj.AttachmentPoint, "TopLeft", "TopCenter", "TopRight", "MiddleLeft", "MiddleCenter", "MiddleRight", "BottomLeft", "BottomCenter", "BottomRight")
    
        ThisDrawing.Regen True
        MsgBox "The attachment point of the MText is now: " & attachPoint, vbInformation, "AttachmentPoint Example"
    Next
End Sub

Sub Example_AutoAudit()
    ' This example returns the current setting of
    ' AutoAudit. It then changes the value, and finally
    ' it resets the value back to the original setting.
    
    Dim preferences As AcadPreferences
    Dim currAutoAudit As Boolean
    Dim newAutoAudit As Boolean
    
    Set preferences = ThisDrawing.Application.preferences
    
    ' Retrieve the current AutoAudit value
    currAutoAudit = preferences.OpenSave.AutoAudit
    MsgBox "The current value for AutoAudit is " & currAutoAudit, vbInformation, "AutoAudit Example"
    
    ' Toggle the value for AutoAudit
    newAutoAudit = Not (currAutoAudit)
    preferences.OpenSave.AutoAudit = newAutoAudit
    MsgBox "The new value for AutoAudit is " & newAutoAudit, vbInformation, "AutoAudit Example"
    
    ' Reset AutoAudit to its original value
    preferences.OpenSave.AutoAudit = currAutoAudit
    MsgBox "The AutoAudit value is reset to " & currAutoAudit, vbInformation, "AutoAudit Example"
End Sub

Sub Example_AutoSaveInterval()
    ' This example returns the current setting of
    ' AutoSaveInterval. It then changes the value, and finally
    ' it resets the value back to the original setting.
    
    Dim preferences As AcadPreferences
    Dim currAutoSaveInterval As Integer
    Dim newAutoSaveInterval As Integer
    
    Set preferences = ThisDrawing.Application.preferences
    
    ' Retrieve the current AutoSaveInterval value
    currAutoSaveInterval = preferences.OpenSave.AutoSaveInterval
    MsgBox "The current value for AutoSaveInterval is " & currAutoSaveInterval, vbInformation, "AutoSaveInterval Example"
    
    ' Change the value for AutoSaveInterval
    If currAutoSaveInterval = 0 Then
        newAutoSaveInterval = 10
    Else
        newAutoSaveInterval = 0
    End If
    preferences.OpenSave.AutoSaveInterval = newAutoSaveInterval
    MsgBox "The new value for AutoSaveInterval is " & newAutoSaveInterval, vbInformation, "AutoSaveInterval Example"
    
    ' Reset AutoSaveInterval to its original value
    preferences.OpenSave.AutoSaveInterval = currAutoSaveInterval
    MsgBox "The AutoSaveInterval value is reset to " & currAutoSaveInterval, vbInformation, "AutoSaveInterval Example"
 End Sub
Sub Example_AltFontFile()
    ' This example returns the current setting of
    ' AltFontFile. It then changes the value, and finally
    ' it resets the value back to the original setting.
    
    Dim preferences As AcadPreferences
    Dim currAltFontFile As String
    Dim newAltFontFile As String
    
    Set preferences = ThisDrawing.Application.preferences
    
    ' Retrieve the current AltFontFile value
    currAltFontFile = preferences.Files.AltFontFile
    MsgBox "The current value for AltFontFile is " & currAltFontFile, vbInformation, "AltFontFile Example"
    
    ' Change the value for AltFontFile
    newAltFontFile = "C:/AutoCAD/Fonts/gothice.shx"
    preferences.Files.AltFontFile = newAltFontFile
    MsgBox "The new value for AltFontFile is " & newAltFontFile, vbInformation, "AltFontFile Example"
    
    ' Reset AltFontFile to its original value
    preferences.Files.AltFontFile = currAltFontFile
    MsgBox "The AltFontFile value is reset to " & currAltFontFile, vbInformation, "AltFontFile Example"
 End Sub
Sub Example_AltTabletMenuFile()
    ' This example returns the current setting of
    ' AltTabletMenuFile. It then changes the value, and finally
    ' it resets the value back to the original setting.
    
    Dim preferences As AcadPreferences
    Dim currAltTabletMenuFile As String
    Dim newAltTabletMenuFile As String
    
    Set preferences = ThisDrawing.Application.preferences
    
    ' Retrieve the current AltTabletMenuFile value
    currAltTabletMenuFile = preferences.Files.AltTabletMenuFile
    If currAltTabletMenuFile = "" Then
        MsgBox "AltTabletMenuFile is not currently set.", vbInformation, "AltTabletMenuFile Example"
    Else
        MsgBox "The current value for AltTabletMenuFile is " & currAltTabletMenuFile, vbInformation, "AltTabletMenuFile Example"
    End If
    
    ' Change the value for AltTabletMenuFile
    newAltTabletMenuFile = "d:\acad\support\acad"
    preferences.Files.AltTabletMenuFile = newAltTabletMenuFile
    MsgBox "The new value for AltTabletMenuFile is " & newAltTabletMenuFile, vbInformation, "AltTabletMenuFile Example"
    
    ' Reset AltTabletMenuFile to its original value
    preferences.Files.AltTabletMenuFile = currAltTabletMenuFile
    If currAltTabletMenuFile = "" Then
        MsgBox "AltTabletMenuFile is reset to Null.", vbInformation, "AltTabletMenuFile Example"
    Else
        MsgBox "The AltTabletMenuFile value is reset to " & currAltTabletMenuFile, vbInformation, "AltTabletMenuFile Example"
    End If
 End Sub

Sub Example_ConfigFile()
    ' This example returns the current setting of ConfigFile.
    
    Dim preferences As AcadPreferences
    Dim currConfigFile As String
    
    Set preferences = ThisDrawing.Application.preferences
    
    ' Retrieve the current ConfigFile value
    currConfigFile = preferences.Files.ConfigFile
    If currConfigFile = "" Then
        MsgBox "ConfigFile is not currently set.", vbInformation, "ConfigFile Example"
    Else
        MsgBox "The current value for ConfigFile is " & currConfigFile, vbInformation, "ConfigFile Example"
    End If
End Sub
Sub Example_CustomDictionary()
    ' This example returns the current setting of
    ' CustomDictionary. It then changes the value, and finally
    ' it resets the value back to the original setting.
    
    Dim preferences As AcadPreferences
    Dim currCustomDictionary As String
    Dim newCustomDictionary As String
    
    Set preferences = ThisDrawing.Application.preferences
    
    ' Retrieve the current CustomDictionary value
    currCustomDictionary = preferences.Files.CustomDictionary
    MsgBox "The current value for CustomDictionary is " & currCustomDictionary, vbInformation, "CustomDictionary Example"
    
    ' Change the value for CustomDictionary
    newCustomDictionary = "TestCustomDictionary.cus"
    preferences.Files.CustomDictionary = newCustomDictionary
    MsgBox "The new value for CustomDictionary is " & newCustomDictionary, vbInformation, "CustomDictionary Example"
    
    ' Reset CustomDictionary to its original value
    preferences.Files.CustomDictionary = currCustomDictionary
    MsgBox "The CustomDictionary value is reset to " & currCustomDictionary, vbInformation, "CustomDictionary Example"
End Sub
Sub Example_DefaultInternetURL()
    ' This example returns the current setting of
    ' DefaultInternetURL. It then changes the value, and finally
    ' it resets the value back to the original setting.
    
    Dim preferences As AcadPreferences
    Dim currDefaultInternetURL As String
    Dim newDefaultInternetURL As String
    
    Set preferences = ThisDrawing.Application.preferences
    
    ' Retrieve the current DefaultInternetURL value
    currDefaultInternetURL = preferences.Files.DefaultInternetURL
    MsgBox "The current value for DefaultInternetURL is " & currDefaultInternetURL, vbInformation, "DefaultInternetURL Example"
    
    ' Change the value for DefaultInternetURL
    newDefaultInternetURL = "TestDefaultInternetURL"
    preferences.Files.DefaultInternetURL = newDefaultInternetURL
    MsgBox "The new value for DefaultInternetURL is " & newDefaultInternetURL, vbInformation, "DefaultInternetURL Example"
    
    ' Reset DefaultInternetURL to its original value
    preferences.Files.DefaultInternetURL = currDefaultInternetURL
    MsgBox "The DefaultInternetURL value is reset to " & currDefaultInternetURL, vbInformation, "DefaultInternetURL Example"
End Sub
Sub Example_DriversPath()
    ' This example returns the current setting of
    ' DriversPath. It then changes the value, and finally
    ' it resets the value back to the original setting.
    
    Dim preferences As AcadPreferences
    Dim currDriversPath As String
    Dim newDriversPath As String
    
    Set preferences = ThisDrawing.Application.preferences
    
    ' Retrieve the current DriversPath value
    currDriversPath = preferences.Files.DriversPath
    MsgBox "The current value for DriversPath is " & currDriversPath, vbInformation, "DriversPath Example"
    
    ' Change the value for DriversPath
    newDriversPath = "TestDriversPath"
    preferences.Files.DriversPath = newDriversPath
    MsgBox "The new value for DriversPath is " & newDriversPath, vbInformation, "DriversPath Example"
    
    ' Reset DriversPath to its original value
    preferences.Files.DriversPath = currDriversPath
    MsgBox "The DriversPath value is reset to " & currDriversPath, vbInformation, "DriversPath Example"
End Sub
Sub Example_FontFileMap()
    ' This example returns the current setting of
    ' FontFileMap. It then changes the value, and finally
    ' it resets the value back to the original setting.
    
    Dim preferences As AcadPreferences
    Dim currFontFileMap As String
    Dim newFontFileMap As String
    
    Set preferences = ThisDrawing.Application.preferences
    
    ' Retrieve the current FontFileMap value
    currFontFileMap = preferences.Files.FontFileMap
    MsgBox "The current value for FontFileMap is " & currFontFileMap, vbInformation, "FontFileMap Example"
    
    ' Change the value for FontFileMap
    newFontFileMap = "TestFontFileMap.fmp"
    preferences.Files.FontFileMap = newFontFileMap
    MsgBox "The new value for FontFileMap is " & newFontFileMap, vbInformation, "FontFileMap Example"
    
    ' Reset FontFileMap to its original value
    preferences.Files.FontFileMap = currFontFileMap
    MsgBox "The FontFileMap value is reset to " & currFontFileMap, vbInformation, "FontFileMap Example"
End Sub
Sub Example_FontFile()
    ' This example returns the current setting of
    ' the FontFile property. It then changes the value, and
    ' finally resets the value back to the original setting.
    
    Dim textStyle1 As AcadTextStyle
    Dim currFontFile As String
    Dim newFontFile As String
    
    Set textStyle1 = ThisDrawing.ActiveTextStyle
    
    ' Retrieve the current FontFile value
    currFontFile = textStyle1.fontFile
    MsgBox "The current value for FontFile is " & currFontFile, vbInformation, "FontFile Example"
    
    ' Change the value for FontFile
    newFontFile = "C:/AutoCAD/Fonts/italic.shx"
    textStyle1.fontFile = newFontFile
    MsgBox "The new value for FontFile is " & textStyle1.fontFile, vbInformation, "FontFile Example"
        
    ' reset font file
    textStyle1.fontFile = currFontFile
    MsgBox "The value for FontFile has been reset to " & textStyle1.fontFile, vbInformation, "FontFile Example"
End Sub
Sub Example_HelpFilePath()
    ' This example returns the current setting of
    ' HelpFilePath. It then changes the value, and finally
    ' it resets the value back to the original setting.
    
    Dim preferences As AcadPreferences
    Dim currHelpFilePath As String
    Dim newHelpFilePath As String
    Set preferences = ThisDrawing.Application.preferences
    
    ' Retrieve the current HelpFilePath value
    currHelpFilePath = preferences.Files.HelpFilePath
    MsgBox "The current value for HelpFilePath is " & currHelpFilePath, vbInformation, "HelpFilePath Example"
    
    ' Change the value for HelpFilePath
    newHelpFilePath = "C:/AutoCAD/Help"
    preferences.Files.HelpFilePath = newHelpFilePath
    MsgBox "The new value for HelpFilePath is " & newHelpFilePath, vbInformation, "HelpFilePath Example"
    
    ' Reset HelpFilePath to its original value
    preferences.Files.HelpFilePath = currHelpFilePath
    MsgBox "The HelpFilePath value is reset to " & currHelpFilePath, vbInformation, "HelpFilePath Example"
End Sub
Sub Example_LicenseServer()
    ' This example returns the current setting of
    ' LicenseServer. It then changes the value, and finally
    ' it resets the value back to the original setting.
    
    Dim preferences As AcadPreferences
    Dim currLicenseServer As String
    
    Set preferences = ThisDrawing.Application.preferences
    
    ' Retrieve the current LicenseServer value
    currLicenseServer = preferences.Files.LicenseServer
    If currLicenseServer = "" Then
        MsgBox "LicenseServer is not currently set.", vbInformation, "LicenseServer Example"
    Else
        MsgBox "The current value for LicenseServer is " & currLicenseServer, vbInformation, "LicenseServer Example"
    End If
End Sub
Sub Example_ActiveSelectionSet()
    Dim sset As AcadSelectionSet
    ' The following example returns current selection set from current drawing
    Set sset = ThisDrawing.ActiveSelectionSet
End Sub
Sub Example_LogFilePath()
    ' This example returns the current setting of
    ' LogFilePath. It then changes the value, and finally
    ' it resets the value back to the original setting.
    
    Dim preferences As AcadPreferences
    Dim currLogFilePath As String
    Dim newLogFilePath As String
    
    Set preferences = ThisDrawing.Application.preferences
    
    ' Retrieve the current LogFilePath value
    currLogFilePath = preferences.Files.LogFilePath
    MsgBox "The current value for LogFilePath is " & currLogFilePath, vbInformation, "LogFilePath Example"
    
    ' Change the value for LogFilePath
    newLogFilePath = "C:/AutoCAD/"
    preferences.Files.LogFilePath = newLogFilePath
    MsgBox "The new value for LogFilePath is " & newLogFilePath, vbInformation, "LogFilePath Example"
    
    ' Reset LogFilePath to its original value
    preferences.Files.LogFilePath = currLogFilePath
    MsgBox "The LogFilePath value is reset to " & currLogFilePath, vbInformation, "LogFilePath Example"
End Sub
Sub Example_MainDictionary()
    ' This example returns the current setting of
    ' MainDictionary. It then changes the value, and finally
    ' it resets the value back to the original setting.
    
    Dim preferences As AcadPreferences
    Dim currMainDictionary As String
    Dim newMainDictionary As String
    
    Set preferences = ThisDrawing.Application.preferences
    
    ' Retrieve the current MainDictionary value
    currMainDictionary = preferences.Files.MainDictionary
    MsgBox "The current value for MainDictionary is " & currMainDictionary, vbInformation, "MainDictionary Example"
    
    ' Change the value for MainDictionary
    newMainDictionary = "TestMainDictionary"
    preferences.Files.MainDictionary = newMainDictionary
    MsgBox "The new value for MainDictionary is " & newMainDictionary, vbInformation, "MainDictionary Example"
    
    ' Reset MainDictionary to its original value
    preferences.Files.MainDictionary = currMainDictionary
    MsgBox "The MainDictionary value is reset to " & currMainDictionary, vbInformation, "MainDictionary Example"
End Sub
Sub Example_MenuFile()
    ' This example returns the current setting of
    ' MenuFile.
    
    Dim preferences As AcadPreferences
    Dim currMenuFile As String
    
    Set preferences = ThisDrawing.Application.preferences
    
    ' Retrieve the current MenuFile value
    currMenuFile = preferences.Files.MenuFile
    MsgBox "The current value for MenuFile is " & currMenuFile, vbInformation, "MenuFile Example"
    
End Sub
Sub Example_PostScriptPrologFile()
    ' This example returns the current setting of
    ' PostScriptPrologFile. It then changes the value, and finally
    ' it resets the value back to the original setting.
    
    Dim preferences As AcadPreferences
    Dim currPostScriptPrologFile As String
    Dim newPostScriptPrologFile As String
    
    Set preferences = ThisDrawing.Application.preferences
    
    ' Retrieve the current PostScriptPrologFile value
    currPostScriptPrologFile = preferences.Files.PostScriptPrologFile
    If currPostScriptPrologFile = "" Then
        MsgBox "PostScriptPrologFile is not currently set.", vbInformation, "PostScriptPrologFile Example"
    Else
        MsgBox "The current value for PostScriptPrologFile is " & currPostScriptPrologFile, vbInformation, "PostScriptPrologFile Example"
    End If
    
    ' Change the value for PostScriptPrologFile
    newPostScriptPrologFile = "TestPostScriptPrologFile"
    preferences.Files.PostScriptPrologFile = newPostScriptPrologFile
    MsgBox "The new value for PostScriptPrologFile is " & newPostScriptPrologFile, vbInformation, "PostScriptPrologFile Example"
    
    ' Reset PostScriptPrologFile to its original value
    preferences.Files.PostScriptPrologFile = currPostScriptPrologFile
    If currPostScriptPrologFile = "" Then
        MsgBox "PostScriptPrologFile is reset to NULL.", vbInformation, "PostScriptPrologFile Example"
    Else
        MsgBox "The PostScriptPrologFile value is reset to " & currPostScriptPrologFile, vbInformation, "PostScriptPrologFile Example"
    End If
End Sub
Sub Example_PrintFile()
    ' This example returns the current setting of
    ' PrintFile. It then changes the value, and finally
    ' it resets the value back to the original setting.
    
    Dim preferences As AcadPreferences
    Dim currPrintFile As String
    Dim newPrintFile As String
    
    Set preferences = ThisDrawing.Application.preferences
    
    ' Retrieve the current PrintFile value
    currPrintFile = preferences.Files.PrintFile
    MsgBox "The current value for PrintFile is " & currPrintFile, vbInformation, "PrintFile Example"
    
    ' Change the value for PrintFile
    newPrintFile = "TestPrintFile.plt"
    preferences.Files.PrintFile = newPrintFile
    MsgBox "The new value for PrintFile is " & newPrintFile, vbInformation, "PrintFile Example"
    
    ' Reset PrintFile to its original value
    preferences.Files.PrintFile = currPrintFile
    MsgBox "The PrintFile value is reset to " & currPrintFile, vbInformation, "PrintFile Example"
End Sub
Sub Example_PrintSpoolerPath()
    ' This example returns the current setting of
    ' PrintSpoolerPath. It then changes the value, and finally
    ' it resets the value back to the original setting.
    
    Dim preferences As AcadPreferences
    Dim currPrintSpoolerPath As String
    Dim newPrintSpoolerPath As String
    
    Set preferences = ThisDrawing.Application.preferences
    
    ' Retrieve the current PrintSpoolerPath value
    currPrintSpoolerPath = preferences.Files.PrintSpoolerPath
    MsgBox "The current value for PrintSpoolerPath is " & currPrintSpoolerPath, vbInformation, "PrintSpoolerPath Example"
    
    ' Change the value for PrintSpoolerPath
    newPrintSpoolerPath = "TestPrintSpoolerPath"
    preferences.Files.PrintSpoolerPath = newPrintSpoolerPath
    MsgBox "The new value for PrintSpoolerPath is " & newPrintSpoolerPath, vbInformation, "PrintSpoolerPath Example"
    
    ' Reset PrintSpoolerPath to its original value
    preferences.Files.PrintSpoolerPath = currPrintSpoolerPath
    MsgBox "The PrintSpoolerPath value is reset to " & currPrintSpoolerPath, vbInformation, "PrintSpoolerPath Example"
End Sub
Sub Example_PrintSpoolExecutable()
    ' This example returns the current setting of
    ' PrintSpoolExecutable. It then changes the value, and finally
    ' it resets the value back to the original setting.
    
    Dim preferences As AcadPreferences
    Dim currPrintSpoolExecutable As String
    Dim newPrintSpoolExecutable As String
    
    Set preferences = ThisDrawing.Application.preferences
    
    ' Retrieve the current PrintSpoolExecutable value
    currPrintSpoolExecutable = preferences.Files.PrintSpoolExecutable
    MsgBox "The current value for PrintSpoolExecutable is " & currPrintSpoolExecutable, vbInformation, "PrintSpoolExecutable Example"
    
    ' Change the value for PrintSpoolExecutable
    newPrintSpoolExecutable = "TestPrintSpoolExecutable"
    preferences.Files.PrintSpoolExecutable = newPrintSpoolExecutable
    MsgBox "The new value for PrintSpoolExecutable is " & newPrintSpoolExecutable, vbInformation, "PrintSpoolExecutable Example"
    
    ' Reset PrintSpoolExecutable to its original value
    preferences.Files.PrintSpoolExecutable = currPrintSpoolExecutable
    MsgBox "The PrintSpoolExecutable value is reset to " & currPrintSpoolExecutable, vbInformation, "PrintSpoolExecutable Example"
End Sub
Sub Example_SupportPath()
    ' This example returns the current setting of
    ' SupportPath. It then changes the value, and finally
    ' it resets the value back to the original setting.
    
    Dim preferences As AcadPreferences
    Dim currSupportPath As String
    Dim newSupportPath As String
    
    Set preferences = ThisDrawing.Application.preferences
    
    ' Retrieve the current SupportPath value
    currSupportPath = preferences.Files.SupportPath
    MsgBox "The current value for SupportPath is " & currSupportPath, vbInformation, "SupportPath Example"
    
    ' Change the value for SupportPath
    newSupportPath = "TestSupportPath"
    preferences.Files.SupportPath = newSupportPath
    MsgBox "The new value for SupportPath is " & newSupportPath, vbInformation, "SupportPath Example"
    
    ' Reset SupportPath to its original value
    preferences.Files.SupportPath = currSupportPath
    MsgBox "The SupportPath value is reset to " & currSupportPath, vbInformation, "SupportPath Example"
End Sub
Sub Example_TempFilePath()
    ' This example returns the current setting of
    ' TempFilePath. It then changes the value, and finally
    ' it resets the value back to the original setting.
    
    Dim preferences As AcadPreferences
    Dim currTempFilePath As String
    Dim newTempFilePath As String
    
    Set preferences = ThisDrawing.Application.preferences
    
    ' Retrieve the current TempFilePath value
    currTempFilePath = preferences.Files.TempFilePath
    MsgBox "The current value for TempFilePath is " & currTempFilePath, vbInformation, "TempFilePath Example"
    
    ' Change the value for TempFilePath
    newTempFilePath = "C:\AutoCAD\"
    preferences.Files.TempFilePath = newTempFilePath
    MsgBox "The new value for TempFilePath is " & newTempFilePath, vbInformation, "TempFilePath Example"
    
    ' Reset TempFilePath to its original value
    preferences.Files.TempFilePath = currTempFilePath
    MsgBox "The TempFilePath value is reset to " & currTempFilePath, vbInformation, "TempFilePath Example"
End Sub

Sub Example_TemplateDWGPath()
    ' This example returns the current setting of
    ' TemplateDWGPath. It then changes the value, and finally
    ' it resets the value back to the original setting.
    
    Dim preferences As AcadPreferences
    Dim currTemplateDWGPath As String
    Dim newTemplateDWGPath As String
    
    Set preferences = ThisDrawing.Application.preferences
    
    ' Retrieve the current TemplateDWGPath value
    currTemplateDWGPath = preferences.Files.TemplateDwgPath
    MsgBox "The current value for TemplateDWGPath is " & currTemplateDWGPath, vbInformation, "TemplateDWGPath Example"
    
    ' Change the value for TemplateDWGPath
    newTemplateDWGPath = "TestTemplateDWGPath"
    preferences.Files.TemplateDwgPath = newTemplateDWGPath
    MsgBox "The new value for TemplateDWGPath is " & newTemplateDWGPath, vbInformation, "TemplateDWGPath Example"
    
    ' Reset TemplateDWGPath to its original value
    preferences.Files.TemplateDwgPath = currTemplateDWGPath
    MsgBox "The TemplateDWGPath value is reset to " & currTemplateDWGPath, vbInformation, "TemplateDWGPath Example"
End Sub
Sub Example_TempXRefPath()
    ' This example returns the current setting of
    ' TempXRefPath. It then changes the value, and finally
    ' it resets the value back to the original setting.
    
    Dim preferences As AcadPreferences
    Dim currTempXRefPath As String
    Dim newTempXRefPath As String
    
    Set preferences = ThisDrawing.Application.preferences
    
    ' Retrieve the current TempXRefPath value
    currTempXRefPath = preferences.Files.TempXrefPath
    MsgBox "The current value for TempXRefPath is " & currTempXRefPath, vbInformation, "TempXRefPath Example"
    
    ' Change the value for TempXRefPath
    newTempXRefPath = "TestTempXRefPath"
    preferences.Files.TempXrefPath = newTempXRefPath
    MsgBox "The new value for TempXRefPath is " & newTempXRefPath, vbInformation, "TempXRefPath Example"
    
    ' Reset TempXRefPath to its original value
    preferences.Files.TempXrefPath = currTempXRefPath
    MsgBox "The TempXRefPath value is reset to " & currTempXRefPath, vbInformation, "TempXRefPath Example"
End Sub
Sub Example_TextEditor()
    ' This example returns the current setting of
    ' TextEditor. It then changes the value, and finally
    ' it resets the value back to the original setting.
    
    Dim preferences As AcadPreferences
    Dim currTextEditor As String
    Dim newTextEditor As String
    
    Set preferences = ThisDrawing.Application.preferences
    
    ' Retrieve the current TextEditor value
    currTextEditor = preferences.Files.TextEditor
    MsgBox "The current value for TextEditor is " & currTextEditor, vbInformation, "TextEditor Example"
    
    ' Change the value for TextEditor
    newTextEditor = "TestTextEditor"
    preferences.Files.TextEditor = newTextEditor
    MsgBox "The new value for TextEditor is " & newTextEditor, vbInformation, "TextEditor Example"
    
    ' Reset TextEditor to its original value
    preferences.Files.TextEditor = currTextEditor
    MsgBox "The TextEditor value is reset to " & currTextEditor, vbInformation, "TextEditor Example"
End Sub
Sub Example_TextureMapPath()
    ' This example returns the current setting of
    ' TextureMapPath. It then changes the value, and finally
    ' it resets the value back to the original setting.
    
    Dim preferences As AcadPreferences
    Dim currTextureMapPath As String
    Dim newTextureMapPath As String
    
    Set preferences = ThisDrawing.Application.preferences
    
    ' Retrieve the current TextureMapPath value
    currTextureMapPath = preferences.Files.TextureMapPath
    MsgBox "The current value for TextureMapPath is " & currTextureMapPath, vbInformation, "TextureMapPath Example"
    
    ' Change the value for TextureMapPath
    newTextureMapPath = "TestTextureMapPath"
    preferences.Files.TextureMapPath = newTextureMapPath
    MsgBox "The new value for TextureMapPath is " & newTextureMapPath, vbInformation, "TextureMapPath Example"
    
    ' Reset TextureMapPath to its original value
    preferences.Files.TextureMapPath = currTextureMapPath
    MsgBox "The TextureMapPath value is reset to " & currTextureMapPath, vbInformation, "TextureMapPath Example"
End Sub
Sub Example_ArcSmoothness()
    ' This example returns the current setting of
    ' ArcSmoothness. It then changes the value, and finally
    ' it resets the value back to the original setting.
    
    Dim currArcSmoothness As Integer
    Dim newArcSmoothness As Integer
        
    ' Retrieve the current ArcSmoothness value
    currArcSmoothness = ThisDrawing.ActiveViewport.ArcSmoothness
    MsgBox "The current value for ArcSmoothness is " & currArcSmoothness, vbInformation, "ArcSmoothness Example"
    
    ' Change the value for ArcSmoothness
    newArcSmoothness = 2001
    ThisDrawing.ActiveViewport.ArcSmoothness = newArcSmoothness
    MsgBox "The new value for ArcSmoothness is " & newArcSmoothness, vbInformation, "ArcSmoothness Example"
    
    ' Reset ArcSmoothness to its original value
    ThisDrawing.ActiveViewport.ArcSmoothness = currArcSmoothness
    MsgBox "The ArcSmoothness value is reset to " & currArcSmoothness, vbInformation, "ArcSmoothness Example"
End Sub
Sub Example_ContourLinesPerSurface()
    ' This example returns the current setting of
    ' ContourLinesPerSurface. It then changes the value, and finally
    ' it resets the value back to the original setting.
    
    Dim currContourLinesPerSurface As Integer
    Dim newContourLinesPerSurface As Integer
        
    ' Retrieve the current ContourLinesPerSurface value
    currContourLinesPerSurface = ThisDrawing.preferences.ContourLinesPerSurface
    MsgBox "The current value for ContourLinesPerSurface is " & currContourLinesPerSurface, vbInformation, "ContourLinesPerSurface Example"
    
    ' Change the value for ContourLinesPerSurface
    newContourLinesPerSurface = 2001
    ThisDrawing.preferences.ContourLinesPerSurface = newContourLinesPerSurface
    MsgBox "The new value for ContourLinesPerSurface is " & newContourLinesPerSurface, vbInformation, "ContourLinesPerSurface Example"
    
    ' Reset ContourLinesPerSurface to its original value
    ThisDrawing.preferences.ContourLinesPerSurface = currContourLinesPerSurface
    MsgBox "The ContourLinesPerSurface value is reset to " & currContourLinesPerSurface, vbInformation, "ContourLinesPerSurface Example"
End Sub
Sub Example_DisplaySilhouette()
    ' This example returns the current setting of
    ' DisplaySilhouette. It then changes the value, and finally
    ' it resets the value back to the original setting.
    
    Dim currDisplaySilhouette As Boolean
    
    
    ' Retrieve the current DisplaySilhouette value
    currDisplaySilhouette = ThisDrawing.preferences.DisplaySilhouette
    MsgBox "The current value for DisplaySilhouette is " & preferences.DisplaySilhouette, vbInformation, "DisplaySilhouette Example"
    
    ' Change the value for DisplaySilhouette
    ThisDrawing.preferences.DisplaySilhouette = Not (currDisplaySilhouette)
    MsgBox "The new value for DisplaySilhouette is " & preferences.DisplaySilhouette, vbInformation, "DisplaySilhouette Example"
    
    ' Reset DisplaySilhouette to its original value
    ThisDrawing.preferences.DisplaySilhouette = currDisplaySilhouette
    MsgBox "The DisplaySilhouette value is reset to " & preferences.DisplaySilhouette, vbInformation, "DisplaySilhouette Example"
End Sub
Sub Example_IncrementalSavePercent()
    ' This example returns the current setting of
    ' IncrementalSavePercent. It then changes the value, and finally
    ' it resets the value back to the original setting.
    
    Dim preferences As AcadPreferences
    Dim currIncrementalSavePercent As Integer
    Dim newIncrementalSavePercent As Integer
    
    Set preferences = ThisDrawing.Application.preferences
    
    ' Retrieve the current IncrementalSavePercent value
    currIncrementalSavePercent = preferences.OpenSave.IncrementalSavePercent
    MsgBox "The current value for IncrementalSavePercent is " & currIncrementalSavePercent, vbInformation, "IncrementalSavePercent Example"
    
    ' Change the value for IncrementalSavePercent
    newIncrementalSavePercent = 20
    preferences.OpenSave.IncrementalSavePercent = newIncrementalSavePercent
    MsgBox "The new value for IncrementalSavePercent is " & newIncrementalSavePercent, vbInformation, "IncrementalSavePercent Example"
    
    ' Reset IncrementalSavePercent to its original value
    preferences.OpenSave.IncrementalSavePercent = currIncrementalSavePercent
    MsgBox "The IncrementalSavePercent value is reset to " & currIncrementalSavePercent, vbInformation, "IncrementalSavePercent Example"
End Sub
Sub Example_MaxActiveViewports()
    ' This example returns the current setting of
    ' MaxActiveViewports. It then changes the value, and finally
    ' it resets the value back to the original setting.
    
    Dim currMaxActiveViewports As Integer
    Dim newMaxActiveViewports As Integer
    
    ' Retrieve the current MaxActiveViewports value
    currMaxActiveViewports = ThisDrawing.preferences.MaxActiveViewports
    MsgBox "The current value for MaxActiveViewports is " & currMaxActiveViewports, vbInformation, "MaxActiveViewports Example"
    
    ' Change the value for MaxActiveViewports
    newMaxActiveViewports = 20
    ThisDrawing.preferences.MaxActiveViewports = newMaxActiveViewports
    MsgBox "The new value for MaxActiveViewports is " & newMaxActiveViewports, vbInformation, "MaxActiveViewports Example"
    
    ' Reset MaxActiveViewports to its original value
    ThisDrawing.preferences.MaxActiveViewports = currMaxActiveViewports
    MsgBox "The MaxActiveViewports value is reset to " & currMaxActiveViewports, vbInformation, "MaxActiveViewports Example"
End Sub
Sub Example_RenderSmoothness()
    ' This example returns the current setting of
    ' RenderSmoothness. It then changes the value, and finally
    ' it resets the value back to the original setting.
    
    Dim currRenderSmoothness As Double
    Dim newRenderSmoothness As Double
    
    ' Retrieve the current RenderSmoothness value
    currRenderSmoothness = ThisDrawing.preferences.RenderSmoothness
    MsgBox "The current value for RenderSmoothness is " & currRenderSmoothness, vbInformation, "RenderSmoothness Example"
    
    ' Change the value for RenderSmoothness
    newRenderSmoothness = 2.5
    ThisDrawing.preferences.RenderSmoothness = newRenderSmoothness
    MsgBox "The new value for RenderSmoothness is " & newRenderSmoothness, vbInformation, "RenderSmoothness Example"
    
    ' Reset RenderSmoothness to its original value
    ThisDrawing.preferences.RenderSmoothness = currRenderSmoothness
    MsgBox "The RenderSmoothness value is reset to " & currRenderSmoothness, vbInformation, "RenderSmoothness Example"
End Sub
Sub Example_SegmentPerPolyline()
    ' This example returns the current setting of
    ' SegmentPerPolyline. It then changes the value, and finally
    ' it resets the value back to the original setting.
    
    Dim currSegmentPerPolyline As Integer
    Dim newSegmentPerPolyline As Integer
    
    ' Retrieve the current SegmentPerPolyline value
    currSegmentPerPolyline = ThisDrawing.preferences.SegmentPerPolyline
    MsgBox "The current value for SegmentPerPolyline is " & currSegmentPerPolyline, vbInformation, "SegmentPerPolyline Example"
    
    ' Change the value for SegmentPerPolyline
    newSegmentPerPolyline = 2001
    ThisDrawing.preferences.SegmentPerPolyline = newSegmentPerPolyline
    MsgBox "The new value for SegmentPerPolyline is " & newSegmentPerPolyline, vbInformation, "SegmentPerPolyline Example"
    
    ' Reset SegmentPerPolyline to its original value
    ThisDrawing.preferences.SegmentPerPolyline = currSegmentPerPolyline
    MsgBox "The SegmentPerPolyline value is reset to " & currSegmentPerPolyline, vbInformation, "SegmentPerPolyline Example"
End Sub
Sub Example_ShowRasterImage()
    ' This example returns the current setting of
    ' ShowRasterImage. It then changes the value, and finally
    ' it resets the value back to the original setting.
    
    Dim preferences As AcadPreferences
    Dim currShowRasterImage As Boolean
    
    Set preferences = ThisDrawing.Application.preferences
    
    ' Retrieve the current ShowRasterImage value
    currShowRasterImage = preferences.DISPLAY.ShowRasterImage
    MsgBox "The current value for ShowRasterImage is " & preferences.DISPLAY.ShowRasterImage, vbInformation, "ShowRasterImage Example"
    
    ' Change the value for ShowRasterImage
    preferences.DISPLAY.ShowRasterImage = Not (currShowRasterImage)
    MsgBox "The new value for ShowRasterImage is " & preferences.DISPLAY.ShowRasterImage, vbInformation, "ShowRasterImage Example"
    
    ' Reset ShowRasterImage to its original value
    preferences.DISPLAY.ShowRasterImage = currShowRasterImage
    MsgBox "The ShowRasterImage value is reset to " & preferences.DISPLAY.ShowRasterImage, vbInformation, "ShowRasterImage Example"
End Sub
Sub Example_TextFrameDisplay()
    ' This example returns the current setting of
    ' TextFrameDisplay. It then changes the value, and finally
    ' it resets the value back to the original setting.
    
    Dim currTextFrameDisplay As Boolean
    
    ' Retrieve the current TextFrameDisplay value
    currTextFrameDisplay = ThisDrawing.preferences.TextFrameDisplay
    MsgBox "The current value for TextFrameDisplay is " & preferences.TextFrameDisplay, vbInformation, "TextFrameDisplay Example"
    
    ' Change the value for TextFrameDisplay
    ThisDrawing.preferences.TextFrameDisplay = Not (currTextFrameDisplay)
    MsgBox "The new value for TextFrameDisplay is " & preferences.TextFrameDisplay, vbInformation, "TextFrameDisplay Example"
    
    ' Reset TextFrameDisplay to its original value
    ThisDrawing.preferences.TextFrameDisplay = currTextFrameDisplay
    MsgBox "The TextFrameDisplay value is reset to " & preferences.TextFrameDisplay, vbInformation, "TextFrameDisplay Example"
End Sub
Sub Example_XRefDemandLoad()
    ' This example returns the current setting of
    ' XRefDemandLoad. It then changes the value, and finally
    ' it resets the value back to the original setting.
    
    Dim preferences As AcadPreferences
    Dim currXRefDemandLoad As Integer
    Dim constant As String
    Dim newConstant As String
    
    Set preferences = ThisDrawing.Application.preferences
    
    ' Retrieve the current XRefDemandLoad value
    currXRefDemandLoad = preferences.OpenSave.XrefDemandLoad
    constant = Choose(currXRefDemandLoad + 1, "acDemandLoadDisabled", "acDemandLoadEnabled", "acDemandLoadEnabledWithCopy")
    MsgBox "The current value for XRefDemandLoad is " & constant, vbInformation, "XRefDemandLoad Example"
    
    ' Change the value for XRefDemandLoad
    newConstant = "acDemandLoadEnabledWithCopy"
    preferences.OpenSave.XrefDemandLoad = acDemandLoadEnabledWithCopy
    MsgBox "The new value for XRefDemandLoad is " & newConstant, vbInformation, "XRefDemandLoad Example"
    
    ' Reset XRefDemandLoad to its original value
    preferences.OpenSave.XrefDemandLoad = currXRefDemandLoad
    MsgBox "The XRefDemandLoad value is reset to " & constant, vbInformation, "XRefDemandLoad Example"
End Sub
Sub Example_DemandLoadARXApp()
    ' This example returns the current setting of
    ' DemandLoadARXApp. It then changes the value, and finally
    ' it resets the value back to the original setting.
    
    Dim preferences As AcadPreferences
    Dim currDemandLoadARXApp As Integer
    Dim constant As String
    Dim newConstant As String
    
    Set preferences = ThisDrawing.Application.preferences
    
    ' Retrieve the current DemandLoadARXApp value
    currDemandLoadARXApp = preferences.OpenSave.DemandLoadARXApp
    MsgBox "The current value for DemandLoadARXApp is " & currDemandLoadARXApp, vbInformation, "DemandLoadARXApp Example"
    
    ' Change the value for DemandLoadARXApp
    newConstant = acDemandLoadCmdInvoke
    preferences.OpenSave.DemandLoadARXApp = acDemandLoadCmdInvoke
    MsgBox "The new value for DemandLoadARXApp is " & newConstant, vbInformation, "DemandLoadARXApp Example"
    
    ' Reset DemandLoadARXApp to its original value
    preferences.OpenSave.DemandLoadARXApp = currDemandLoadARXApp
    MsgBox "The DemandLoadARXApp value is reset to " & currDemandLoadARXApp, vbInformation, "DemandLoadARXApp Example"
End Sub
Sub Example_EnableStartupDialog()
    ' This example returns the current setting of
    ' EnableStartupDialog. It then changes the value, and finally
    ' it resets the value back to the original setting.
    
    Dim preferences As AcadPreferences
    Dim currEnableStartupDialog As Boolean
    
    Set preferences = ThisDrawing.Application.preferences
    
    ' Retrieve the current EnableStartupDialog value
    currEnableStartupDialog = preferences.System.EnableStartupDialog
    MsgBox "The current value for EnableStartupDialog is " & preferences.System.EnableStartupDialog, vbInformation, "EnableStartupDialog Example"
    
    ' Change the value for EnableStartupDialog
    preferences.System.EnableStartupDialog = Not (currEnableStartupDialog)
    MsgBox "The new value for EnableStartupDialog is " & preferences.System.EnableStartupDialog, vbInformation, "EnableStartupDialog Example"
    
    ' Reset EnableStartupDialog to its original value
    preferences.System.EnableStartupDialog = currEnableStartupDialog
    MsgBox "The EnableStartupDialog value is reset to " & preferences.System.EnableStartupDialog, vbInformation, "EnableStartupDialog Example"
End Sub
Sub Example_KeyboardAccelerator()
    ' This example returns the current setting of
    ' KeyboardAccelerator. It then changes the value, and finally
    ' it resets the value back to the original setting.
    
    Dim preferences As AcadPreferences
    Dim currKeyboardAccelerator As Integer
    
    Set preferences = ThisDrawing.Application.preferences
    
    ' Retrieve the current KeyboardAccelerator value
    currKeyboardAccelerator = preferences.User.KeyboardAccelerator
    MsgBox "The current value for KeyboardAccelerator is " & currKeyboardAccelerator, vbInformation, "KeyboardAccelerator Example"
    
    ' Change the value for KeyboardAccelerator
    If currKeyboardAccelerator = acPreferenceClassic Then
        preferences.User.KeyboardAccelerator = acPreferenceCustom
    Else
        preferences.User.KeyboardAccelerator = acPreferenceClassic
    End If
    MsgBox "The new value for KeyboardAccelerator is " & preferences.User.KeyboardAccelerator, vbInformation, "KeyboardAccelerator Example"
    
    ' Reset KeyboardAccelerator to its original value
    preferences.User.KeyboardAccelerator = currKeyboardAccelerator
    MsgBox "The KeyboardAccelerator value is reset to " & preferences.User.KeyboardAccelerator, vbInformation, "KeyboardAccelerator Example"
End Sub
Sub Example_KeyboardPriority()
    ' This example returns the current setting of
    ' KeyboardPriority. It then changes the value, and finally
    ' it resets the value back to the original setting.
    
    Dim preferences As AcadPreferences
    Dim currKeyboardPriority As Integer
    Dim constant As String
    Dim newConstant As String
    
    Set preferences = ThisDrawing.Application.preferences
    
    ' Retrieve the current KeyboardPriority value
    currKeyboardPriority = preferences.User.KeyboardPriority
    constant = Choose(currKeyboardPriority + 1, "acKeyboardRunningObjSnap", "acKeyboardEntry", "acKeyboardEntryExceptScripts")
    MsgBox "The current value for KeyboardPriority is " & constant, vbInformation, "KeyboardPriority Example"
    
    ' Change the value for KeyboardPriority
    newConstant = "acKeyboardEntry"
    preferences.User.KeyboardPriority = acKeyboardEntry
    MsgBox "The new value for KeyboardPriority is " & newConstant, vbInformation, "KeyboardPriority Example"
    
    ' Reset KeyboardPriority to its original value
    preferences.User.KeyboardPriority = currKeyboardPriority
    MsgBox "The KeyboardPriority value is reset to " & constant, vbInformation, "KeyboardPriority Example"
End Sub

Sub Example_ProxyImage()
    ' This example returns the current setting of
    ' ProxyImage. It then changes the value, and finally
    ' it resets the value back to the original setting.
    
    Dim preferences As AcadPreferences
    Dim currProxyImage As Integer
    Dim constant As String
    Dim newConstant As String
    
    Set preferences = ThisDrawing.Application.preferences
    
    ' Retrieve the current ProxyImage value
    currProxyImage = preferences.OpenSave.ProxyImage
    constant = Choose(currProxyImage + 1, "acProxyNotShow", "acProxyShow", "acProxyBoundingBox")
    MsgBox "The current value for ProxyImage is " & constant, vbInformation, "ProxyImage Example"
    
    ' Change the value for ProxyImage
    newConstant = "acProxyBoundingBox"
    preferences.OpenSave.ProxyImage = acProxyBoundingBox
    MsgBox "The new value for ProxyImage is " & newConstant, vbInformation, "ProxyImage Example"
    
    ' Reset ProxyImage to its original value
    preferences.OpenSave.ProxyImage = currProxyImage
    MsgBox "The ProxyImage value is reset to " & constant, vbInformation, "ProxyImage Example"
End Sub
Sub Example_ShowProxyDialogBox()
    ' This example returns the current setting of
    ' ShowProxyDialogBox. It then changes the value, and finally
    ' it resets the value back to the original setting.
    
    Dim preferences As AcadPreferences
    Dim currShowProxyDialogBox As Boolean
    
    Set preferences = ThisDrawing.Application.preferences
    
    ' Retrieve the current ShowProxyDialogBox value
    currShowProxyDialogBox = preferences.OpenSave.ShowProxyDialogBox
    MsgBox "The current value for ShowProxyDialogBox is " & preferences.OpenSave.ShowProxyDialogBox, vbInformation, "ShowProxyDialogBox Example"
    
    ' Change the value for ShowProxyDialogBox
    preferences.OpenSave.ShowProxyDialogBox = Not (currShowProxyDialogBox)
    MsgBox "The new value for ShowProxyDialogBox is " & preferences.OpenSave.ShowProxyDialogBox, vbInformation, "ShowProxyDialogBox Example"
    
    ' Reset ShowProxyDialogBox to its original value
    preferences.OpenSave.ShowProxyDialogBox = currShowProxyDialogBox
    MsgBox "The ShowProxyDialogBox value is reset to " & preferences.OpenSave.ShowProxyDialogBox, vbInformation, "ShowProxyDialogBox Example"
End Sub
Sub Example_BeepOnError()
    ' This example returns the current setting of
    ' BeepOnError. It then changes the value, and finally
    ' it resets the value back to the original setting.
    
    Dim preferences As AcadPreferences
    Dim currBeepOnError As Boolean
    
    Set preferences = ThisDrawing.Application.preferences
    
    ' Retrieve the current BeepOnError value
    currBeepOnError = preferences.System.BeepOnError
    MsgBox "The current value for BeepOnError is " & preferences.System.BeepOnError, vbInformation, "BeepOnError Example"
    
    ' Change the value for BeepOnError
    preferences.System.BeepOnError = Not (currBeepOnError)
    MsgBox "The new value for BeepOnError is " & preferences.System.BeepOnError, vbInformation, "BeepOnError Example"
    
    ' Reset BeepOnError to its original value
    preferences.System.BeepOnError = currBeepOnError
    MsgBox "The BeepOnError value is reset to " & preferences.System.BeepOnError, vbInformation, "BeepOnError Example"
End Sub

Sub Example_CreateBackup()
    ' This example returns the current setting of
    ' CreateBackup. It then changes the value, and finally
    ' it resets the value back to the original setting.
    
    Dim preferences As AcadPreferences
    Dim currCreateBackup As Boolean
    
    Set preferences = ThisDrawing.Application.preferences
    
    ' Retrieve the current CreateBackup value
    currCreateBackup = preferences.OpenSave.CreateBackup
    MsgBox "The current value for CreateBackup is " & preferences.OpenSave.CreateBackup, vbInformation, "CreateBackup Example"
    
    ' Change the value for CreateBackup
    preferences.OpenSave.CreateBackup = Not (currCreateBackup)
    MsgBox "The new value for CreateBackup is " & preferences.OpenSave.CreateBackup, vbInformation, "CreateBackup Example"
    
    ' Reset CreateBackup to its original value
    preferences.OpenSave.CreateBackup = currCreateBackup
    MsgBox "The CreateBackup value is reset to " & preferences.OpenSave.CreateBackup, vbInformation, "CreateBackup Example"
End Sub

Sub Example_FullCRCValidation()
    ' This example returns the current setting of
    ' FullCRCValidation. It then changes the value, and finally
    ' it resets the value back to the original setting.
    
    Dim preferences As AcadPreferences
    Dim currFullCRCValidation As Boolean
    
    Set preferences = ThisDrawing.Application.preferences
    
    ' Retrieve the current FullCRCValidation value
    currFullCRCValidation = preferences.OpenSave.FullCRCValidation
    MsgBox "The current value for FullCRCValidation is " & preferences.OpenSave.FullCRCValidation, vbInformation, "FullCRCValidation Example"
    
    ' Change the value for FullCRCValidation
    preferences.OpenSave.FullCRCValidation = Not (currFullCRCValidation)
    MsgBox "The new value for FullCRCValidation is " & preferences.OpenSave.FullCRCValidation, vbInformation, "FullCRCValidation Example"
    
    ' Reset FullCRCValidation to its original value
    preferences.OpenSave.FullCRCValidation = currFullCRCValidation
    MsgBox "The FullCRCValidation value is reset to " & preferences.OpenSave.FullCRCValidation, vbInformation, "FullCRCValidation Example"
End Sub

Sub Example_LogFileOn()
    ' This example returns the current setting of
    ' LogFileOn. It then changes the value, and finally
    ' it resets the value back to the original setting.
    
    Dim preferences As AcadPreferences
    Dim currLogFileOn As Boolean
    
    Set preferences = ThisDrawing.Application.preferences
    
    ' Retrieve the current LogFileOn value
    currLogFileOn = preferences.OpenSave.LogFileOn
    MsgBox "The current value for LogFileOn is " & preferences.OpenSave.LogFileOn, vbInformation, "LogFileOn Example"
    
    ' Change the value for LogFileOn
    preferences.OpenSave.LogFileOn = Not (currLogFileOn)
    MsgBox "The new value for LogFileOn is " & preferences.OpenSave.LogFileOn, vbInformation, "LogFileOn Example"
    
    ' Reset LogFileOn to its original value
    preferences.OpenSave.LogFileOn = currLogFileOn
    MsgBox "The LogFileOn value is reset to " & preferences.OpenSave.LogFileOn, vbInformation, "LogFileOn Example"
End Sub





Sub Example_SavePreviewThumbnail()
    ' This example returns the current setting of
    ' SavePreviewThumbnail. It then changes the value, and finally
    ' it resets the value back to the original setting.
    
    Dim preferences As AcadPreferences
    Dim currSavePreviewThumbnail As Boolean
    
    Set preferences = ThisDrawing.Application.preferences
    
    ' Retrieve the current SavePreviewThumbnail value
    currSavePreviewThumbnail = preferences.OpenSave.SavePreviewThumbnail
    MsgBox "The current value for SavePreviewThumbnail is " & preferences.OpenSave.SavePreviewThumbnail, vbInformation, "SavePreviewThumbnail Example"
    
    ' Change the value for SavePreviewThumbnail
    preferences.OpenSave.SavePreviewThumbnail = Not (currSavePreviewThumbnail)
    MsgBox "The new value for SavePreviewThumbnail is " & preferences.OpenSave.SavePreviewThumbnail, vbInformation, "SavePreviewThumbnail Example"
    
    ' Reset SavePreviewThumbnail to its original value
    preferences.OpenSave.SavePreviewThumbnail = currSavePreviewThumbnail
    MsgBox "The SavePreviewThumbnail value is reset to " & currSavePreviewThumbnail, vbInformation, "SavePreviewThumbnail Example"
End Sub

Sub Example_TempFileExtension()
    ' This example returns the current setting of
    ' TempFileExtension. It then changes the value, and finally
    ' it resets the value back to the original setting.
    
    Dim preferences As AcadPreferences
    Dim currTempFileExtension As String
    
    Set preferences = ThisDrawing.Application.preferences
    
    ' Retrieve the current TempFileExtension value
    currTempFileExtension = preferences.OpenSave.TempFileExtension
    MsgBox "The current value for TempFileExtension is " & preferences.OpenSave.TempFileExtension, vbInformation, "TempFileExtension Example"
    
    ' Change the value for TempFileExtension
    preferences.OpenSave.TempFileExtension = "@@@"
    MsgBox "The new value for TempFileExtension is " & preferences.OpenSave.TempFileExtension, vbInformation, "TempFileExtension Example"
    
    ' Reset TempFileExtension to its original value
    preferences.OpenSave.TempFileExtension = currTempFileExtension
    MsgBox "The TempFileExtension value is reset to " & preferences.OpenSave.TempFileExtension, vbInformation, "TempFileExtension Example"
End Sub

Sub Example_ModelCrossHairColor()
    ' This example returns the current setting of
    ' Model space CrossHairColor. It then changes the value, and
    ' finally resets the value back to the original setting.
    
    Dim preferences As AcadPreferences
    Dim currCrossHairColor As OLE_COLOR
    
    Set preferences = ThisDrawing.Application.preferences
    
    ' Retrieve the current CrossHairColor value
    currCrossHairColor = preferences.DISPLAY.ModelCrosshairColor
    MsgBox "The current value for the model space CrossHairColor is " & preferences.DISPLAY.ModelCrosshairColor, vbInformation, "CrossHairColor Example"
    
    ' Change the value for CrossHairColor
    preferences.DISPLAY.ModelCrosshairColor = vbGreen
    MsgBox "The new value for CrossHairColor is " & preferences.DISPLAY.ModelCrosshairColor, vbInformation, "CrossHairColor Example"
    
    ' Reset CrossHairColor to its original value
    preferences.DISPLAY.ModelCrosshairColor = currCrossHairColor
    MsgBox "The CrossHairColor value is reset to " & preferences.DISPLAY.ModelCrosshairColor, vbInformation, "CrossHairColor Example"
        
End Function



Sub Example_DisplayScreenMenu()
    ' This example returns the current setting of
    ' DisplayScreenMenu. It then changes the value, and finally
    ' it resets the value back to the original setting.
    
    Dim preferences As AcadPreferences
    Dim currDisplayScreenMenu As Boolean
    
    Set preferences = ThisDrawing.Application.preferences
    
    ' Retrieve the current DisplayScreenMenu value
    currDisplayScreenMenu = preferences.DISPLAY.DisplayScreenMenu
    MsgBox "The current value for DisplayScreenMenu is " & preferences.DISPLAY.DisplayScreenMenu, vbInformation, "DisplayScreenMenu Example"
    
    ' Change the value for DisplayScreenMenu
    preferences.DISPLAY.DisplayScreenMenu = Not (currDisplayScreenMenu)
    MsgBox "The new value for DisplayScreenMenu is " & preferences.DISPLAY.DisplayScreenMenu, vbInformation, "DisplayScreenMenu Example"
    
    ' Reset DisplayScreenMenu to its original value
    preferences.DISPLAY.DisplayScreenMenu = currDisplayScreenMenu
    MsgBox "The DisplayScreenMenu value is reset to " & preferences.DISPLAY.DisplayScreenMenu, vbInformation, "DisplayScreenMenu Example"
End Sub
Sub Example_DisplayScrollBars()
    ' This example returns the current setting of
    ' DisplayScrollBars. It then changes the value, and finally
    ' it resets the value back to the original setting.
    
    Dim preferences As AcadPreferences
    Dim currDisplayScrollBars As Boolean
    
    Set preferences = ThisDrawing.Application.preferences
    
    ' Retrieve the current DisplayScrollBars value
    currDisplayScrollBars = preferences.DISPLAY.DisplayScrollBars
    MsgBox "The current value for DisplayScrollBars is " & preferences.DISPLAY.DisplayScrollBars, vbInformation, "DisplayScrollBars Example"
    
    ' Change the value for DisplayScrollBars
    preferences.DISPLAY.DisplayScrollBars = Not (currDisplayScrollBars)
    MsgBox "The new value for DisplayScrollBars is " & preferences.DISPLAY.DisplayScrollBars, vbInformation, "DisplayScrollBars Example"
    
    ' Reset DisplayScrollBars to its original value
    preferences.DISPLAY.DisplayScrollBars = currDisplayScrollBars
    MsgBox "The DisplayScrollBars value is reset to " & preferences.DISPLAY.DisplayScrollBars, vbInformation, "DisplayScrollBars Example"
End Sub
Sub Example_DockedVisibleLines()
    ' This example returns the current setting of
    ' DockedVisibleLines. It then changes the value, and finally
    ' it resets the value back to the original setting.
    
    Dim preferences As AcadPreferences
    Dim currDockedVisibleLines As Integer
    
    Set preferences = ThisDrawing.Application.preferences
    
    ' Retrieve the current DockedVisibleLines value
    currDockedVisibleLines = preferences.DISPLAY.DockedVisibleLines
    MsgBox "The current value for DockedVisibleLines is " & preferences.DISPLAY.DockedVisibleLines, vbInformation, "DockedVisibleLines Example"
    
    ' Change the value for DockedVisibleLines
    preferences.DISPLAY.DockedVisibleLines = 15
    MsgBox "The new value for DockedVisibleLines is " & preferences.DISPLAY.DockedVisibleLines, vbInformation, "DockedVisibleLines Example"
    
    ' Reset DockedVisibleLines to its original value
    preferences.DISPLAY.DockedVisibleLines = currDockedVisibleLines
    MsgBox "The DockedVisibleLines value is reset to " & preferences.DISPLAY.DockedVisibleLines, vbInformation, "DockedVisibleLines Example"
End Sub
Sub Example_HistoryLines()
    ' This example returns the current setting of
    ' HistoryLines. It then changes the value, and finally
    ' it resets the value back to the original setting.
    
    Dim preferences As AcadPreferences
    Dim currHistoryLines As Integer
    
    Set preferences = ThisDrawing.Application.preferences
    
    ' Retrieve the current HistoryLines value
    currHistoryLines = preferences.DISPLAY.HistoryLines
    MsgBox "The current value for HistoryLines is " & preferences.DISPLAY.HistoryLines, vbInformation, "HistoryLines Example"
    
    ' Change the value for HistoryLines
    preferences.DISPLAY.HistoryLines = 42
    MsgBox "The new value for HistoryLines is " & preferences.DISPLAY.HistoryLines, vbInformation, "HistoryLines Example"
    
    ' Reset HistoryLines to its original value
    preferences.DISPLAY.HistoryLines = currHistoryLines
    MsgBox "The HistoryLines value is reset to " & preferences.DISPLAY.HistoryLines, vbInformation, "HistoryLines Example"
End Sub



Sub Example_GraphicsWinModelBackgrndColor()
    ' This example returns the current setting of
    ' GraphicsWinModelBackgrndColor. It then changes the value, and finally
    ' it resets the value back to the original setting.
    
    Dim preferences As AcadPreferences
    Dim currGraphicsWinModelBackgrndColor As OLE_COLOR
    
    Set preferences = ThisDrawing.Application.preferences
    
    ' Retrieve the current GraphicsWinModelBackgrndColor value
    currGraphicsWinModelBackgrndColor = preferences.DISPLAY.GraphicsWinModelBackgrndColor
    MsgBox "The current value for GraphicsWinModelBackgrndColor is " _
            & preferences.DISPLAY.GraphicsWinModelBackgrndColor, vbInformation, "GraphicsWinModelBackgrndColor Example"
    
    ' Change the value for GraphicsWinModelBackgrndColor
    preferences.DISPLAY.GraphicsWinModelBackgrndColor = 16
    MsgBox "The new value for GraphicsWinModelBackgrndColor is " _
            & preferences.DISPLAY.GraphicsWinModelBackgrndColor, vbInformation, "GraphicsWinModelBackgrndColor Example"
    
    ' Reset GraphicsWinModelBackgrndColor to its original value
    preferences.DISPLAY.GraphicsWinModelBackgrndColor = currGraphicsWinModelBackgrndColor
    MsgBox "The GraphicsWinModelBackgrndColor value is reset to " _
            & preferences.DISPLAY.GraphicsWinModelBackgrndColor, vbInformation, "GraphicsWinModelBackgrndColor Example"
End Sub
Sub Example_GraphicsWinLayoutBackgrndColor()
    ' This example returns the current setting of
    ' GraphicsWinLayoutBackgrndColor. It then changes the value, and finally
    ' it resets the value back to the original setting.
    
    Dim preferences As AcadPreferences
    Dim currGraphicsWinLayoutBackgrndColor As OLE_COLOR
    
    Set preferences = ThisDrawing.Application.preferences
    
    ' Retrieve the current GraphicsWinLayoutBackgrndColor value
    currGraphicsWinLayoutBackgrndColor = preferences.DISPLAY.GraphicsWinLayoutBackgrndColor
    MsgBox "The current value for GraphicsWinLayoutBackgrndColor is " _
            & preferences.DISPLAY.GraphicsWinLayoutBackgrndColor, vbInformation, "GraphicsWinLayoutBackgrndColor Example"
    
    ' Change the value for GraphicsWinLayoutBackgrndColor
    preferences.DISPLAY.GraphicsWinLayoutBackgrndColor = 16
    MsgBox "The new value for GraphicsWinLayoutBackgrndColor is " _
            & preferences.DISPLAY.GraphicsWinLayoutBackgrndColor, vbInformation, "GraphicsWinLayoutBackgrndColor Example"
    
    ' Reset GraphicsWinLayoutBackgrndColor to its original value
    preferences.DISPLAY.GraphicsWinLayoutBackgrndColor = currGraphicsWinLayoutBackgrndColor
    MsgBox "The GraphicsWinLayoutBackgrndColor value is reset to " _
            & preferences.DISPLAY.GraphicsWinLayoutBackgrndColor, vbInformation, "GraphicsWinLayoutBackgrndColor Example"
End Sub
Sub Example_MaxAutoCADWindow()
    ' This example returns the current setting of
    ' MaxAutoCADWindow. It then changes the value, and finally
    ' it resets the value back to the original setting.
    
    Dim preferences As AcadPreferences
    Dim currMaxAutoCADWindow As Boolean
    
    Set preferences = ThisDrawing.Application.preferences
    
    ' Retrieve the current MaxAutoCADWindow value
    currMaxAutoCADWindow = preferences.DISPLAY.MaxAutoCADWindow
    MsgBox "The current value for MaxAutoCADWindow is " & preferences.DISPLAY.MaxAutoCADWindow, vbInformation, "MaxAutoCADWindow Example"
    
    ' Change the value for MaxAutoCADWindow
    preferences.DISPLAY.MaxAutoCADWindow = Not (currMaxAutoCADWindow)
    MsgBox "The new value for MaxAutoCADWindow is " & preferences.DISPLAY.MaxAutoCADWindow, vbInformation, "MaxAutoCADWindow Example"
    
    ' Reset MaxAutoCADWindow to its original value
    preferences.DISPLAY.MaxAutoCADWindow = currMaxAutoCADWindow
    MsgBox "The MaxAutoCADWindow value is reset to " & preferences.DISPLAY.MaxAutoCADWindow, vbInformation, "MaxAutoCADWindow Example"
End Sub

Sub Example_TextFont()
    ' This example returns the current setting of
    ' TextFont. It then changes the value, and finally
    ' it resets the value back to the original setting.
    
    Dim preferences As AcadPreferences
    Dim currTextFont As String
    
    Set preferences = ThisDrawing.Application.preferences
    
    ' Retrieve the current TextFont value
    currTextFont = preferences.DISPLAY.TextFont
    MsgBox "The current value for TextFont is " & preferences.DISPLAY.TextFont, vbInformation, "TextFont Example"
    
    ' Change the value for TextFont
    preferences.DISPLAY.TextFont = "TestTextFont"
    MsgBox "The new value for TextFont is " & preferences.DISPLAY.TextFont, vbInformation, "TextFont Example"
    
    ' Reset TextFont to its original value
    preferences.DISPLAY.TextFont = currTextFont
    MsgBox "The TextFont value is reset to " & preferences.DISPLAY.TextFont, vbInformation, "TextFont Example"
End Sub
Sub Example_TextFontSize()
    ' This example returns the current setting of
    ' TextFontSize. It then changes the value, and finally
    ' it resets the value back to the original setting.
    
    Dim preferences As AcadPreferences
    Dim currTextFontSize As Integer
    
    Set preferences = ThisDrawing.Application.preferences
    
    ' Retrieve the current TextFontSize value
    currTextFontSize = preferences.DISPLAY.TextFontSize
    MsgBox "The current value for TextFontSize is " & preferences.DISPLAY.TextFontSize, vbInformation, "TextFontSize Example"
    
    ' Change the value for TextFontSize
    preferences.DISPLAY.TextFontSize = 12
    MsgBox "The new value for TextFontSize is " & preferences.DISPLAY.TextFontSize, vbInformation, "TextFontSize Example"
    
    ' Reset TextFontSize to its original value
    preferences.DISPLAY.TextFontSize = currTextFontSize
    MsgBox "The TextFontSize value is reset to " & preferences.DISPLAY.TextFontSize, vbInformation, "TextFontSize Example"
End Sub
Sub Example_TextFontStyle()
    ' This example returns the current setting of
    ' TextFontStyle. It then changes the value, and finally
    ' it resets the value back to the original setting.
    
    Dim preferences As AcadPreferences
    Dim currTextFontStyle As Integer
    Dim constant As String
    Dim newConstant As String
    
    Set preferences = ThisDrawing.Application.preferences
    
    ' Retrieve the current TextFontStyle value
    currTextFontStyle = preferences.DISPLAY.TextFontStyle
    constant = Choose(currTextFontStyle + 1, "acFontRegular", "acFontItalic", "acFontBold", "acFontBoldItalic")
    MsgBox "The current value for TextFontStyle is " & constant, vbInformation, "TextFontStyle Example"
    
    ' Change the value for TextFontStyle
    newConstant = "acFontBoldItalic"
    preferences.DISPLAY.TextFontStyle = acFontBoldItalic
    MsgBox "The new value for TextFontStyle is " & newConstant, vbInformation, "TextFontStyle Example"
    
    ' Reset TextFontStyle to its original value
    preferences.DISPLAY.TextFontStyle = currTextFontStyle
    MsgBox "The TextFontStyle value is reset to " & constant, vbInformation, "TextFontStyle Example"
End Sub
Sub Example_TextWinBackgrndColor()
    ' This example returns the current setting of
    ' TextWinBackgrndColor. It then changes the value, and finally
    ' it resets the value back to the original setting.
    
    Dim preferences As AcadPreferences
    Dim currTextWinBackgrndColor As OLE_COLOR
    
    Set preferences = ThisDrawing.Application.preferences
    
    ' Retrieve the current TextWinBackgrndColor value
    currTextWinBackgrndColor = preferences.DISPLAY.TextWinBackgrndColor
    MsgBox "The current value for TextWinBackgrndColor is " _
            & preferences.DISPLAY.TextWinBackgrndColor, vbInformation, "TextWinBackgrndColor Example"
    
    ' Change the value for TextWinBackgrndColor
    preferences.DISPLAY.TextWinBackgrndColor = vbBlue
    MsgBox "The new value for TextWinBackgrndColor is " _
            & preferences.DISPLAY.TextWinBackgrndColor, vbInformation, "TextWinBackgrndColor Example"
    
    ' Reset TextWinBackgrndColor to its original value
    preferences.DISPLAY.TextWinBackgrndColor = currTextWinBackgrndColor
    MsgBox "The TextWinBackgrndColor value is reset to " _
            & preferences.DISPLAY.TextWinBackgrndColor, vbInformation, "TextWinBackgrndColor Example"
End Sub
Sub Example_TextWinTextColor()
    ' This example returns the current setting of
    ' TextWinTextColor. It then changes the value, and finally
    ' it resets the value back to the original setting.
    
    Dim preferences As AcadPreferences
    Dim currTextWinTextColor As Long
    
    Set preferences = ThisDrawing.Application.preferences
    
    ' Retrieve the current TextWinTextColor value
    currTextWinTextColor = preferences.DISPLAY.TextWinTextColor
    MsgBox "The current value for TextWinTextColor is " _
            & preferences.DISPLAY.TextWinTextColor, vbInformation, "TextWinTextColor Example"
    
    ' Change the value for TextWinTextColor
    preferences.DISPLAY.TextWinTextColor = vbGreen
    MsgBox "The new value for TextWinTextColor is " _
            & preferences.DISPLAY.TextWinTextColor, vbInformation, "TextWinTextColor Example"
    
    ' Reset TextWinTextColor to its original value
    preferences.DISPLAY.TextWinTextColor = currTextWinTextColor
    MsgBox "The TextWinTextColor value is reset to " _
            & preferences.DISPLAY.TextWinTextColor, vbInformation, "TextWinTextColor Example"
End Sub
Sub Example_CursorSize()
    ' This example returns the current setting of
    ' CursorSize. It then changes the value, and finally
    ' it resets the value back to the original setting.
    
    Dim preferences As AcadPreferences
    Dim currCursorSize As Integer
    Dim newCursorSize As Integer
    
    Set preferences = ThisDrawing.Application.preferences
    
    ' Retrieve the current CursorSize value
    currCursorSize = preferences.DISPLAY.CursorSize
    MsgBox "The current value for CursorSize is " & currCursorSize, vbInformation, "CursorSize Example"
    
    ' Change the value for CursorSize
    newCursorSize = 10
    preferences.DISPLAY.CursorSize = newCursorSize
    MsgBox "The new value for CursorSize is " & newCursorSize, vbInformation, "CursorSize Example"
    
    ' Reset CursorSize to its original value
    preferences.DISPLAY.CursorSize = currCursorSize
    MsgBox "The CursorSize value is reset to " & currCursorSize, vbInformation, "CursorSize Example"
End Sub
Sub Example_ActiveProfile()
    ' This example returns the current setting of
    ' ActiveProfile.
    
    Dim preferences As AcadPreferences
    Dim currActiveProfile As String
    
    Set preferences = ThisDrawing.Application.preferences
    
    ' Retrieve the current ActiveProfile value
    currActiveProfile = preferences.Profiles.ActiveProfile
    MsgBox "The current value for ActiveProfile is " & currActiveProfile, vbInformation, "ActiveProfile Example"
End Sub
Sub Example_BasePoint()
    ' This example creates a ray object. It then finds the
    ' base point of the ray, changes the base point, and
    ' queries the new base point.
    Dim basePoint(0 To 2) As Double
    Dim directionVec(0 To 2) As Double
    Dim rayObj As AcadRay
    
    ' Establish the base point and directional vector for the ray
    basePoint(0) = 3#: basePoint(1) = 3#: basePoint(2) = 0#
    directionVec(0) = 1#: directionVec(1) = 1#: directionVec(2) = 0#
    
    ' Create a Ray object in model space
    Set rayObj = ThisDrawing.ModelSpace.AddRay(basePoint, directionVec)
    
    ThisDrawing.Regen True
    MsgBox "A new Ray has been added.", vbInformation
    
    ' Define a new base point
    Dim newBase(0 To 2) As Double
    newBase(0) = 4#: newBase(1) = 2#: newBase(2) = 0#
    
    ' Update the ray using the new base point
    rayObj.basePoint = newBase
            
    ' Query the new basepoint for the Ray
    Dim currBase As Variant      ' Note that return from basepoint property is Variant and not a SafeArray
    Dim msg As String
    currBase = rayObj.basePoint
    msg = currBase(0) & ", " & currBase(1) & ", " & currBase(2)
    
    ThisDrawing.Regen True
    MsgBox "We've just changed the basepoint of the new Ray to: " & msg, vbInformation
End Sub

Sub Example_BigFontFile()
    ' This example returns the current setting of
    ' BigFontFile. It then changes the value.
    
    Dim textStyle1 As AcadTextStyle
    Dim currBigFontFile As String
    Dim newBigFontFile As String
    
    Set textStyle1 = ThisDrawing.ActiveTextStyle
    
    ' Retrieve the current BigFontFile value
    currBigFontFile = textStyle1.BigFontFile
    MsgBox "The current value for BigFontFile is " & currBigFontFile, vbInformation, "BigFontFile Example"
    
    ' Change the value for BigFontFile
    newBigFontFile = "C:/AutoCAD/Fonts/bigfont.shx"
    textStyle1.BigFontFile = newBigFontFile
    MsgBox "The new value for BigFontFile is " & newBigFontFile, vbInformation, "BigFontFile Example"

End Sub
Sub Example_Blocks()
    ' This example first finds the blocks collection
    ' using the Blocks property. It then adds a new
    ' block to the block collection.
    
    Dim blkColl As AcadBlocks
    Dim newBlock As AcadBlock
    Dim insertionPnt(0 To 2) As Double
    
    ' Get the Blocks collection
    Set blkColl = ThisDrawing.Blocks
    
    ' Define the insertion point for the new block
    insertionPnt(0) = 0#: insertionPnt(1) = 0#: insertionPnt(2) = 0#
    
    ' Add the new block into the blocks collection
    Set newBlock = blkColl.Add(insertionPnt, "TEST")
    MsgBox "A block called " & newBlock.name & " has been added to the blocks collection", vbInformation, "Blocks Example"
End Sub
Sub Example_Brightness()
    ' This example inserts a raster image and finds the current
    ' brightness of the image. It then changes the brightness
    ' of the image.
    
    ' This example uses the "downtown.jpg" found in the sample
    ' directory. If you do not have this image, or it is located
    ' in a different directory, insert a valid path and filename
    ' for the imageName variable below.
    Dim insertionPoint(0 To 2) As Double
    Dim scalefactor As Double
    Dim rotAngleInDegree As Double, rotAngle As Double
    Dim imageName As String
    Dim raster As AcadRasterImage
    imageName = "C:/AutoCAD/sample/downtown.jpg"
    
    insertionPoint(0) = 2#: insertionPoint(1) = 2#: insertionPoint(2) = 0#
    scalefactor = 1#
    rotAngleInDegree = 0#
    rotAngle = rotAngleInDegree * 3.141592 / 180#
    
    On Error Resume Next
    
    ' Creates a raster image in model space
    Set raster = ThisDrawing.ModelSpace.AddRaster(imageName, insertionPoint, scalefactor, rotAngle)
    If Err.Description = "File error" Then
        MsgBox imageName & " could not be found."
        Exit Sub
    End If

    ' Find the current brightness
    ThisDrawing.Regen True
    MsgBox "The brightness is currently set to: " & raster.Brightness, vbInformation
    
    ' Change the brightness to 5
    raster.Brightness = 5
    ThisDrawing.Regen True
    MsgBox "The brightness is now set to: " & raster.Brightness, vbInformation
End Sub
Sub Example_Center()
    
    Dim circObj As AcadCircle
    Dim currCenterPt(0 To 2) As Double
    Dim newCenterPt(0 To 2) As Double
    Dim radius As Double
    
    ' Define the initial center point and radius for the circle
    currCenterPt(0) = 20: currCenterPt(1) = 30: currCenterPt(2) = 0
    radius = 3
    
    ' Create the circle in modelspace
    Set circObj = ThisDrawing.ModelSpace.AddCircle(currCenterPt, radius)
    ZoomAll
    MsgBox "The center point of the circle is " & currCenterPt(0) & ", " & currCenterPt(1) & ", " & currCenterPt(2), vbInformation, "Center Example"

    ' Change the center point of the circle
    newCenterPt(0) = 25: newCenterPt(1) = 25: newCenterPt(2) = 0
    circObj.center = newCenterPt
    circObj.Update
    
    ' Query the results of the new center position
    ' Notice the output from the center property is a variant
    Dim centerPoint As Variant
    centerPoint = circObj.center
    MsgBox "The center point of the circle is " & centerPoint(0) & ", " & centerPoint(1) & ", " & centerPoint(2), vbInformation, "Center Example"
End Sub
Sub Example_Contrast()
    ' This example inserts a raster image and finds the current
    ' Contrast of the image. It then changes the Contrast
    ' of the image.
    
    ' This example uses the "downtown.jpg" found in the sample
    ' directory. If you do not have the image, or it is located
    ' in a different directory, insert a valid path and name for the
    ' imageName variable below.
    Dim insertionPoint(0 To 2) As Double
    Dim scalefactor As Double
    Dim rotAngleInDegree As Double
    Dim rotAngle As Double
    Dim imageName As String
    Dim raster As AcadRasterImage
    imageName = "C:\AutoCAD\sample\downtown.jpg"
    insertionPoint(0) = 2#: insertionPoint(1) = 2#: insertionPoint(2) = 0#
    scalefactor = 1#
    rotAngleInDegree = 0#
    rotAngle = rotAngleInDegree * 3.141592 / 180#
    
    On Error Resume Next
    
    ' Creates a raster image in model space
    Set raster = ThisDrawing.ModelSpace.AddRaster(imageName, insertionPoint, scalefactor, rotAngle)
    If Err.Description = "File error" Then
        MsgBox imageName & " could not be found."
        Exit Sub
    End If

    ' Find the current Contrast
    ThisDrawing.Regen True
    MsgBox "The Contrast is currently set to: " & raster.Contrast, vbInformation
    
    ' Change the Contrast to 5
    raster.Contrast = 5
    ThisDrawing.Regen True
    MsgBox "The Contrast is now set to: " & raster.Contrast, vbInformation
End Sub
Sub Example_Fade()
    ' This example inserts a raster image and finds the current
    ' Fade value of the image. It then changes the Fade value
    ' of the image.
    
    ' This example uses the "downtown.jpg" found in the sample
    ' directory. If you do not have the image, or it is located
    ' in a different directory, insert a valid path and name for the
    ' imageName variable below.
    Dim insertionPoint(0 To 2) As Double
    Dim scalefactor As Double
    Dim rotAngleInDegree As Double
    Dim rotAngle As Double
    Dim imageName As String
    Dim raster As AcadRasterImage
    imageName = "C:\AutoCAD\sample\downtown.jpg"
    insertionPoint(0) = 2#: insertionPoint(1) = 2#: insertionPoint(2) = 0#
    scalefactor = 1#
    rotAngleInDegree = 0#
    rotAngle = rotAngleInDegree * 3.141592 / 180#
    
    On Error Resume Next
    
    ' Creates a raster image in model space
    Set raster = ThisDrawing.ModelSpace.AddRaster(imageName, insertionPoint, scalefactor, rotAngle)
    If Err.Description = "Filer error" Then
        MsgBox imageName & " could not be found."
        Exit Sub
    End If

    ' Find the current Fade
    ThisDrawing.Regen True
    MsgBox "The Fade is currently set to: " & raster.Fade, vbInformation
    
    ' Change the Fade to 5
    raster.Fade = 50
    ThisDrawing.Regen True
    MsgBox "The Fade is now set to: " & raster.Fade, vbInformation
End Sub
Sub Example_ImageFile()
    ' This example inserts a raster image and then finds the
    ' ImageFile for the image.
    
    ' This example uses the "downtown.jpg" found in the sample
    ' directory. If you do not have the image, or it is located
    ' in a different directory, insert a valid path and name for the
    ' imageName variable below.
    Dim insertionPoint(0 To 2) As Double
    Dim scalefactor As Double
    Dim rotAngleInDegree As Double, rotAngle As Double
    Dim imageName As String
    Dim raster As AcadRasterImage
    imageName = "C:\AutoCAD\sample\downtown.jpg"
    insertionPoint(0) = 2#: insertionPoint(1) = 2#: insertionPoint(2) = 0#
    scalefactor = 1#
    rotAngleInDegree = 0#
    rotAngle = rotAngleInDegree * 3.141592 / 180#
    
    On Error Resume Next
    
    ' Creates a raster image in model space
    Set raster = ThisDrawing.ModelSpace.AddRaster(imageName, insertionPoint, scalefactor, rotAngle)
    If Err.Description = "File error" Then
        MsgBox imageName & " could not be found."
        Exit Sub
    End If

    ' Find the current ImageFile
    ThisDrawing.Regen True
    MsgBox "The ImageFile is currently set to: " & raster.ImageFile, vbInformation
End Sub
Sub Example_ImageVisibility()
    ' This example inserts a raster image and finds the current status
    ' of ImageVisibility for the image. It then changes the ImageVisibility
    ' status of the image.
    
    ' This example uses the "downtown.jpg" found in the sample
    ' directory. If you do not have the image, or it is located
    ' in a different directory, insert a valid path and name for the
    ' imageName variable below.
    Dim insertionPoint(0 To 2) As Double
    Dim scalefactor As Double
    Dim rotAngleInDegree As Double, rotAngle As Double
    Dim imageName As String
    Dim raster As AcadRasterImage
    imageName = "C:\AutoCAD\sample\downtown.jpg"
    insertionPoint(0) = 2#: insertionPoint(1) = 2#: insertionPoint(2) = 0#
    scalefactor = 1#
    rotAngleInDegree = 0#
    rotAngle = rotAngleInDegree * 3.141592 / 180#
    
    On Error Resume Next
    
    ' Creates a raster image in model space
    Set raster = ThisDrawing.ModelSpace.AddRaster(imageName, insertionPoint, scalefactor, rotAngle)
    If Err.Description = "File error" Then
        MsgBox imageName & " could not be found."
        Exit Sub
    End If

    ' Find the current ImageVisibility
    ThisDrawing.Regen True
    MsgBox "The ImageVisibility is currently set to: " & raster.ImageVisibility, vbInformation
    
    ' Change the ImageVisibility
    If (raster.ImageVisibility) Then
        raster.ImageVisibility = False
    Else
        raster.ImageVisibility = True
    End If
    ThisDrawing.Regen True
    MsgBox "The ImageVisibility is now set to: " & raster.ImageVisibility, vbInformation
End Sub
Sub Example_Transparency()
    ' This example inserts a raster image and finds the current status
    ' of Transparency for the image. It then changes the Transparency
    ' status of the image.
    
    ' This example uses the "downtown.jpg" found in the sample
    ' directory. If you do not have the image, or it is located
    ' in a different directory, insert a valid path and name for the
    ' imageName variable below.
    Dim insertionPoint(0 To 2) As Double
    Dim scalefactor As Double
    Dim rotAngleInDegree As Double, rotAngle As Double
    Dim imageName As String
    Dim raster As AcadRasterImage
    imageName = "C:\AutoCAD\sample\downtown.jpg"
    insertionPoint(0) = 2#: insertionPoint(1) = 2#: insertionPoint(2) = 0#
    scalefactor = 1#
    rotAngleInDegree = 0#
    rotAngle = rotAngleInDegree * 3.141592 / 180#
    
    On Error Resume Next
    
    ' Creates a raster image in model space
    Set raster = ThisDrawing.ModelSpace.AddRaster(imageName, insertionPoint, scalefactor, rotAngle)
    If Err.Description = "Filer error" Then
        MsgBox imageName & " could not be found."
        Exit Sub
    End If

    ' Find the current Transparency
    ThisDrawing.Regen True
    MsgBox "The Transparency is currently set to: " & raster.Transparency, vbInformation
    
    ' Change the Transparency
    If (raster.Transparency) Then
        raster.Transparency = False
    Else
        raster.Transparency = True
    End If
    ThisDrawing.Regen True
    MsgBox "The Transparency is now set to: " & raster.Transparency, vbInformation
End Sub
Sub Example_Closed()
    ' This example creates a polyline and then toggles the
    ' setting for Closed.
    Dim plineObj As AcadPolyline
    Dim closedState As String

    ' Create the polyline
    Dim points(8) As Double
    points(0) = 3: points(1) = 7: points(2) = 0
    points(3) = 9: points(4) = 2: points(5) = 0
    points(6) = 3: points(7) = 5: points(8) = 0
    Set plineObj = ThisDrawing.ModelSpace.AddPolyline(points)

    ' Set the closed property to True
    plineObj.Closed = True      ' Close Polyline
    ThisDrawing.Regen (True)
    GoSub DISPLAY

    ' Open the PolyLine by setting the closed property to False
    plineObj.Closed = False      ' Open Polyline
    ThisDrawing.Regen (True)
    GoSub DISPLAY

    Exit Sub

DISPLAY:
    ' Retreive and display the Closed property
    closedState = IIf(plineObj.Closed, "Closed", "Open")
    MsgBox "The new Polyline is: " & closedState, vbInformation, "Closed Example"
    Return
End Sub
Sub Example_Color()
    ' This example creates a polyline and colors it red.
    ' It then displays the current color setting for the polyline.
    Dim plineObj As AcadPolyline
    Dim currentcolor As Variant

    ' Create Polyline
    Dim points(8) As Double
    points(0) = 3: points(1) = 7: points(2) = 0
    points(3) = 9: points(4) = 2: points(5) = 0
    points(6) = 3: points(7) = 5: points(8) = 0

    Set plineObj = ThisDrawing.ModelSpace.AddPolyline(points)
    
    ' First set the color of the object to Red
    plineObj.Color = acRed
    ThisDrawing.Regen (True)
    
    ' Now we will retieve and display the Color property
    currentcolor = plineObj.Color

    ' Translate the color from a number into text
    If currentcolor = 256 Then
        currentcolor = "By Layer"
    Else
        currentcolor = Choose(currentcolor + 1, "By Block", "Red", "Yellow", "Green", "Cyan", "Blue", "Magenta", "White")
    End If
        
    ' Display
    MsgBox "The Polyline color is: " & currentcolor, vbInformation, "Color Example"
End Sub

Sub Example_Coordinates()
    ' This example creates a polyline. It then uses the coordinates
    ' property to return all the coordinates  in the polyline. It then
    ' resets one of the vertices using the coordinates property.
    
    Dim plineObj As AcadPolyline

    ' Create Polyline
    Dim points(5) As Double
    points(0) = 3: points(1) = 7: points(2) = 0
    points(3) = 9: points(4) = 2: points(5) = 0
    Set plineObj = ThisDrawing.ModelSpace.AddPolyline(points)
    ThisDrawing.Regen True

    ' Return all the coordinates of the polyline
    Dim retCoord As Variant
    retCoord = plineObj.Coordinates

    ' Display current coordinates for the first vertex
    MsgBox "The current coordinates of the second vertex are: " & points(3) & ", " & points(4) & ", " & points(5), vbInformation, "Coordinates Example"

    ' Modify the coordinate of the second vertex to (5,5,0). Note that in
    ' case of light weight Polyline, indices will be different because the points are 2D only.
    points(3) = 5
    points(4) = 5
    points(5) = 0
    plineObj.Coordinates = points

    ' Update display
    ThisDrawing.Regen True

    MsgBox "The new coordinates have been set to " & points(3) & ", " & points(4) & ", " & points(5), vbInformation, "Coordinates Example"
End Sub
Sub Example_Count()
    ' Use count to retreive the number of entities in a collection
    ' You might use this value in a loop structure to iterate through the collection
    
    MsgBox "There are " & ThisDrawing.Layers.count & " layer(s) in the drawing."
    MsgBox "There are " & ThisDrawing.ModelSpace.count & " object(s) in ModelSpace."

    Dim objCount As Integer
    Dim I As Integer
    objCount = ThisDrawing.ModelSpace.count
    
    Dim mspaceObj As AcadObject
    For I = 0 To objCount - 1
     Set mspaceObj = ThisDrawing.ModelSpace.Item(I)
    MsgBox "The objects in ModelSpace include: " & mspaceObj.ObjectName, vbInformation, "Count Example"
    Next
    
End Sub
Sub Example_Degree()
    ' This example creates a spline and returns the degree
    ' of the spline's polynomial representation.
    
    Dim noOfPoints As Integer
    Dim splineObj As AcadSpline
    Dim startTan(0 To 2) As Double
    Dim endTan(0 To 2) As Double
    Dim fitPoints(0 To 8) As Double
    
    noOfPoints = 3
    startTan(0) = 0.5: startTan(1) = 0.5: startTan(2) = 0
    endTan(0) = 0.5: endTan(1) = 0.5: endTan(2) = 0
    fitPoints(0) = 0: fitPoints(1) = 0: fitPoints(2) = 0
    fitPoints(3) = 5: fitPoints(4) = 5: fitPoints(5) = 0
    fitPoints(6) = 10: fitPoints(7) = 0: fitPoints(8) = 0
    Set splineObj = ThisDrawing.ModelSpace.AddSpline(fitPoints, startTan, endTan)
    
    ThisDrawing.Regen True
    MsgBox "The degree of this Spline's polynomial representation is: " & splineObj.Degree, vbInformation
End Sub

Sub Example_Description()
    ' This example returns the description of the active linetype.
    ' It then changes the description of the active linetype.
    
    Dim currDescription As String
    
    ' This example modifies the description of a linetype
    currDescription = ThisDrawing.ActiveLinetype.Description
    MsgBox "The description of the active LineType is: " & currDescription, vbInformation, "Description Example"

    ' Change the description of the active linetype
    ThisDrawing.ActiveLinetype.Description = "My favorite LineType"
    MsgBox "The new description of the active LineType is: " & ThisDrawing.ActiveLinetype.Description, vbInformation, "Description Example"
    
    ' Reset the description of the active linetype
    ThisDrawing.ActiveLinetype.Description = currDescription
    MsgBox "The description of the active LineType is reset to: " & ThisDrawing.ActiveLinetype.Description, vbInformation, "Description Example"
End Sub
Sub Example_Dictionaries()
    ' This example finds the current dictionary collection and
    ' adds a new dictionary to that collection.
    
    Dim dict As AcadDictionary
    Set dict = ThisDrawing.Dictionaries.Add("TEST")
    MsgBox "A new dictionary called " & dict.name & " has been added to the dictionaries collection.", vbInformation, "Dictionaries Example"
End Sub

Sub Example_DimStyles()
    ' This example adds a new dimension style.
    Dim dimStyle As AcadDimStyle
    Set dimStyle = ThisDrawing.DimStyles.Add("TEST")
    MsgBox "A new dimension style called " & dimStyle.name & " has been added to the Dimstyles collection.", vbInformation, "Dimstyles Example"
End Sub
Sub Example_Groups()
    ' This example finds the current Groups collection and
    ' adds a new group to that collection.
    
    Dim groupColl As AcadGroups
    Set groupColl = ThisDrawing.Groups
    
    ' Create a dimension style named "TEST" in current drawing
    Dim testGroup As AcadGroup
    Set testGroup = groupColl.Add("TEST")
    MsgBox "A new group called " & testGroup.name & " has been added to the Groups collection.", vbInformation, "Groups Example"
End Sub
Sub Example_Layers()
    ' This example finds the current Layers collection and
    ' adds a new layer to that collection.
    
    Dim layerColl As AcadLayers
    Set layerColl = ThisDrawing.Layers
    
    ' Create a dimension style named "TEST" in current drawing
    Dim testlayer As AcadLayer
    Set testlayer = layerColl.Add("TEST")
    MsgBox "A new layer called " & testlayer.name & " has been added to the Layers collection.", vbInformation, "Layers Example"
End Sub

Sub Example_Linetypes()
    ' This example finds the linetypes collection and
    ' lists all the available linetypes in the collection.
    
    Dim linetypeColl As AcadLineTypes
    Dim entry As AcadLineType
    Dim msg As String
    
    ' Return the linetype collection object of the active document
    Set linetypeColl = ThisDrawing.Linetypes
    ' List all available linetypes
    For Each entry In linetypeColl
        msg = msg & entry.name & vbCrLf
    Next
    MsgBox "The linetypes available in this drawing are:" & vbCrLf & msg, vbInformation, "Linetypes Example"
End Sub
Sub Example_LinetypeScale()
    ' This example creates a line and finds the linetype scale
    ' for the line. It then changes the linetype scale, and finally
    ' resets the linetype scale back to the original value.
    Dim startPoint(0 To 2) As Double
    Dim endPoint(0 To 2) As Double
    Dim lineObj As AcadLine
    Dim currLTScale As Double

    ' Create a Line object in model space
    startPoint(0) = 2#: startPoint(1) = 2#: startPoint(2) = 0#
    endPoint(0) = 4#: endPoint(1) = 4#: endPoint(2) = 0#
    Set lineObj = ThisDrawing.ModelSpace.AddLine(startPoint, endPoint)
    lineObj.Update
    currLTScale = lineObj.LinetypeScale
    MsgBox "The linetype scale for the line is:" & lineObj.LinetypeScale, vbInformation, "Linetypes Example"


    ' Set the linetype scale of a Line to .5
    lineObj.LinetypeScale = 0.5
    lineObj.Update
    MsgBox "The new linetype scale for the line is:" & lineObj.LinetypeScale, vbInformation, "Linetypes Example"
    
    ' Reset the linetype scale of a Line to what is was before
    lineObj.LinetypeScale = currLTScale
    lineObj.Update
    MsgBox "The linetype scale for the line is reset to:" & lineObj.LinetypeScale, vbInformation, "Linetypes Example"
End Sub
Sub Example_MajorAxis()
    ' This example creates an ellipse and finds the major axis
    ' for that ellipse. It then changes the major axis for the ellipse.
    Dim ellObj As AcadEllipse
    Dim majAxis(0 To 2) As Double
    Dim center(0 To 2) As Double
    Dim radRatio As Double
    
    ' Create an ellipse in model space
    center(0) = 5#: center(1) = 5#: center(2) = 0#
    majAxis(0) = 10: majAxis(1) = 20#: majAxis(2) = 0#
    radRatio = 0.3
    Set ellObj = ThisDrawing.ModelSpace.AddEllipse(center, majAxis, radRatio)
    ellObj.Update
    MsgBox "The ellipse has a major axis of " & majAxis(0) & ", " & majAxis(1) & ", " & majAxis(2), vbInformation, "MajorAxis Example"

    
    ' Change the major axis of the ellipse
    majAxis(0) = 5: majAxis(1) = 5: majAxis(2) = 0
    ellObj.MajorAxis = majAxis
    ellObj.Update
    
    ' Query the major axis of an Ellipse
    Dim retMajAxis As Variant
    retMajAxis = ellObj.MajorAxis
    MsgBox "The ellipse has been udpated with the major axis " & retMajAxis(0) & ", " & retMajAxis(1) & ", " & retMajAxis(2), vbInformation, "MajorAxis Example"
End Sub

Sub Example_AddEllipse()
    ' This example creates an ellipse in model space.
    
    Dim ellObj As AcadEllipse
    Dim majAxis(0 To 2) As Double
    Dim center(0 To 2) As Double
    Dim radRatio As Double
    
    ' Create an ellipse in model space
    center(0) = 5#: center(1) = 5#: center(2) = 0#
    majAxis(0) = 10: majAxis(1) = 20#: majAxis(2) = 0#
    radRatio = 0.3
    Set ellObj = ThisDrawing.ModelSpace.AddEllipse(center, majAxis, radRatio)
    ZoomAll
    
End Sub
Sub Example_RadiusRatio()
    ' This example creates an ellipse and finds the radius ratio
    ' for that ellipse. It then changes the radius ratio to 0.75.
    Dim ellObj As AcadEllipse
    Dim majAxis(0 To 2) As Double
    Dim center(0 To 2) As Double
    Dim radRatio As Double
    
    ' Create an ellipse in model space
    center(0) = 5#: center(1) = 5#: center(2) = 0#
    majAxis(0) = 10: majAxis(1) = 20#: majAxis(2) = 0#
    radRatio = 0.3
    Set ellObj = ThisDrawing.ModelSpace.AddEllipse(center, majAxis, radRatio)
    ZoomAll
    MsgBox "This ellipse has a radius ratio of " & ellObj.RadiusRatio, vbInformation, "RadiusRatio Example"

    
    ' Change the radius ratio of the ellipse
    radRatio = 0.75
    ellObj.RadiusRatio = radRatio
    ellObj.Update
    MsgBox "The ellipse has been udpated with the radius ratio of " & ellObj.RadiusRatio, vbInformation, "RadiusRatio Example"
End Sub
Sub Example_StartAngle()
    ' This example creates an ellipse and enters the start and
    ' end angles to create an elliptical arc.
    Dim ellObj As AcadEllipse
    Dim majAxis(0 To 2) As Double
    Dim center(0 To 2) As Double
    Dim radRatio As Double
    
    ' Create an ellipse in model space
    center(0) = 5#: center(1) = 5#: center(2) = 0#
    majAxis(0) = 10: majAxis(1) = 20#: majAxis(2) = 0#
    radRatio = 0.3
    Set ellObj = ThisDrawing.ModelSpace.AddEllipse(center, majAxis, radRatio)
    
    'Enter a start angle of 45 degrees, and an end angle of 270 degrees
    ellObj.startAngle = 45 * (3.14 / 180)
    ellObj.endAngle = 270 * (3.14 / 180)
    ZoomAll
    MsgBox "The ellipse has a start angle of " & ellObj.startAngle * (180 / 3.14) & " and the end angle of " & ellObj.endAngle * (180 / 3.14) & " degrees.", vbInformation, "StartAngle Example"
End Sub
Sub Example_EndAngle()
    ' This example creates an ellipse and enters the start and
    ' end angles to create an elliptical arc.
    Dim ellObj As AcadEllipse
    Dim majAxis(0 To 2) As Double
    Dim center(0 To 2) As Double
    Dim radRatio As Double
    
    ' Create an ellipse in model space
    center(0) = 5#: center(1) = 5#: center(2) = 0#
    majAxis(0) = 10: majAxis(1) = 20#: majAxis(2) = 0#
    radRatio = 0.3
    Set ellObj = ThisDrawing.ModelSpace.AddEllipse(center, majAxis, radRatio)
    
    'Enter a start angle of 45 degrees, and an end angle of 270 degrees
    ellObj.startAngle = 45 * (3.14 / 180)
    ellObj.endAngle = 270 * (3.14 / 180)
    ZoomAll
    MsgBox "This ellipse has a start angle of " & ellObj.startAngle * (180 / 3.14) & " and the end angle of " & ellObj.endAngle * (180 / 3.14) & " degrees.", vbInformation, "EndAngle Example"
End Sub
Sub Example_StartPoint()
    ' This example creates an elliptical arc and then
    ' finds the coordinates of its start and end points.
    Dim ellObj As AcadEllipse
    Dim majAxis(0 To 2) As Double
    Dim center(0 To 2) As Double
    Dim radRatio As Double
    Dim startPoint As Variant
    Dim endPoint As Variant
    
    ' Create an ellipse in model space
    center(0) = 5#: center(1) = 5#: center(2) = 0#
    majAxis(0) = 10: majAxis(1) = 20#: majAxis(2) = 0#
    radRatio = 0.3
    Set ellObj = ThisDrawing.ModelSpace.AddEllipse(center, majAxis, radRatio)
    
    ' Enter a start angle of 45 degrees, and an end angle of 270 degrees
    ellObj.startAngle = 45 * (3.14 / 180)
    ellObj.endAngle = 270 * (3.14 / 180)
    ZoomAll
    
    ' Find the start and endpoints for the ellipse
    startPoint = ellObj.startPoint
    endPoint = ellObj.endPoint
    MsgBox "This ellipse has a start point of " & startPoint(0) & ", " & startPoint(1) & ", " & startPoint(2) & " and an endpoint of " & endPoint(0) & ", " & endPoint(1) & ", " & endPoint(2), vbInformation, "StartPoint Example"
End Sub
Sub Example_EndPoint()
    ' This example creates an elliptical arc and then
    ' finds the coordinates of its start and end points.
    Dim ellObj As AcadEllipse
    Dim majAxis(0 To 2) As Double
    Dim center(0 To 2) As Double
    Dim radRatio As Double
    Dim startPoint As Variant
    Dim endPoint As Variant
    
    ' Create an ellipse in model space
    center(0) = 5#: center(1) = 5#: center(2) = 0#
    majAxis(0) = 10: majAxis(1) = 20#: majAxis(2) = 0#
    radRatio = 0.3
    Set ellObj = ThisDrawing.ModelSpace.AddEllipse(center, majAxis, radRatio)
    
    ' Enter a start angle of 45 degrees, and an end angle of 270 degrees
    ellObj.startAngle = 45 * (3.14 / 180)
    ellObj.endAngle = 270 * (3.14 / 180)
    ZoomAll
    
    ' Find the start and endpoints for the ellipse
    startPoint = ellObj.startPoint
    endPoint = ellObj.endPoint
    MsgBox "This ellipse has a start point of " & startPoint(0) & ", " & startPoint(1) & ", " & startPoint(2) & " and an endpoint of " & endPoint(0) & ", " & endPoint(1) & ", " & endPoint(2), vbInformation, "EndPoint Example"
End Sub
Sub Example_StartParameter()
    ' This example creates an ellipse and enters the start and
    ' end parameters to create an elliptical arc.
    Dim ellObj As AcadEllipse
    Dim majAxis(0 To 2) As Double
    Dim center(0 To 2) As Double
    Dim radRatio As Double
    
    ' Create an ellipse in model space
    center(0) = 5#: center(1) = 5#: center(2) = 0#
    majAxis(0) = 10: majAxis(1) = 20#: majAxis(2) = 0#
    radRatio = 0.3
    Set ellObj = ThisDrawing.ModelSpace.AddEllipse(center, majAxis, radRatio)
    
    ' Enter a start parameter of 1.57, and an end parameter of 6.28
    ellObj.StartParameter = 1.57
    ellObj.EndParameter = 6.28
    ZoomAll
    
    ' Find the start and end parameters for the ellipse
    MsgBox "The ellipse has a start parameter of " & ellObj.StartParameter & " and an end parameter of " & ellObj.EndParameter, vbInformation, "StartParameter Example"
End Sub
Sub Example_EndParameter()
    ' This example creates an ellipse and enters the start and
    ' end parameters to create an elliptical arc.
    Dim ellObj As AcadEllipse
    Dim majAxis(0 To 2) As Double
    Dim center(0 To 2) As Double
    Dim radRatio As Double
    
    ' Create an ellipse in model space
    center(0) = 5#: center(1) = 5#: center(2) = 0#
    majAxis(0) = 10: majAxis(1) = 20#: majAxis(2) = 0#
    radRatio = 0.3
    Set ellObj = ThisDrawing.ModelSpace.AddEllipse(center, majAxis, radRatio)
    
    ' Enter a start parameter of 1.57, and an end parameter of 6.28
    ellObj.StartParameter = 1.57
    ellObj.EndParameter = 6.28
    ZoomAll
    
    ' Find the start and end parameters for the ellipse
    MsgBox "The ellipse has a start parameter of " & ellObj.StartParameter & " and an end parameter of " & ellObj.EndParameter, vbInformation, "EndParameter Example"
End Sub
Sub Example_MinorAxis()
    ' This example creates an ellipse and returns the minor
    ' axis for that ellipse.
    Dim ellObj As AcadEllipse
    Dim majAxis(0 To 2) As Double
    Dim center(0 To 2) As Double
    Dim radRatio As Double
    
    ' Create an ellipse in model space
    center(0) = 5#: center(1) = 5#: center(2) = 0#
    majAxis(0) = 10: majAxis(1) = 20#: majAxis(2) = 0#
    radRatio = 0.3
    Set ellObj = ThisDrawing.ModelSpace.AddEllipse(center, majAxis, radRatio)
    ZoomAll
    
    ' Find the minor axis for the ellipse
    Dim minorAxis As Variant
    minorAxis = ellObj.minorAxis
    MsgBox "The ellipse has a minor axis of " & minorAxis(0) & ", " & minorAxis(1) & ", " & minorAxis(2), vbInformation, "MinorAxis Example"
End Sub
Sub Example_DirectionVector()
    ' This example creates a ray then changes the direction vector
    ' for the ray.
    
    Dim rayObj As AcadRay
    Dim basePoint(0 To 2) As Double
    Dim SecondPoint(0 To 2) As Double
    Dim newDirectionVec(0 To 2) As Double
    
    basePoint(0) = 3#: basePoint(1) = 3#: basePoint(2) = 0#
    SecondPoint(0) = 1#: SecondPoint(1) = 3#: SecondPoint(2) = 0#
    
    ' Create a Ray object in model space
    Set rayObj = ThisDrawing.ModelSpace.AddRay(basePoint, SecondPoint)
    ZoomAll
    MsgBox "The ray has a direction vector of " & rayObj.DirectionVector(0) & ", " & rayObj.DirectionVector(1) & ", " & rayObj.DirectionVector(2), vbInformation, "DirectionVector Example"
    
    ' Change the direction vector
    newDirectionVec(0) = 3#: newDirectionVec(1) = 1#: newDirectionVec(2) = 0#
    rayObj.DirectionVector = newDirectionVec
            
    ' Query the new direction vector for the Ray
    Dim retDir As Variant            ' Note that return from DirectionVector property is Variant and not a SafeArray
    retDir = rayObj.DirectionVector
    
    ThisDrawing.Regen True
    MsgBox "The direction vector of the ray has been changed to " & rayObj.DirectionVector(0) & ", " & rayObj.DirectionVector(1) & ", " & rayObj.DirectionVector(2), vbInformation, "DirectionVector Example"
    
End Sub
Sub Example_ObjectName()
    ' This example creates several objects in model space.
    ' It then iterates through model space and displays the
    ' Object Name for each object found.
    
    ' Create a Ray object in model space
    Dim rayObj As AcadRay
    Dim basePoint(0 To 2) As Double
    Dim SecondPoint(0 To 2) As Double
    basePoint(0) = 3#: basePoint(1) = 3#: basePoint(2) = 0#
    SecondPoint(0) = 1#: SecondPoint(1) = 3#: SecondPoint(2) = 0#
    Set rayObj = ThisDrawing.ModelSpace.AddRay(basePoint, SecondPoint)
    
    ' Create a polyline object in model space
    Dim plineObj As AcadLWPolyline
    Dim points(0 To 5) As Double
    points(0) = 3: points(1) = 7
    points(2) = 9: points(3) = 2
    points(4) = 3: points(5) = 5
    Set plineObj = ThisDrawing.ModelSpace.AddLightWeightPolyline(points)
    plineObj.Closed = True

    ' Create a line object in model space
    Dim lineObj As AcadLine
    Dim startPoint(0 To 2) As Double
    Dim endPoint(0 To 2) As Double
    startPoint(0) = 0: startPoint(1) = 0: startPoint(2) = 0
    endPoint(0) = 2: endPoint(1) = 2: endPoint(2) = 0
    Set lineObj = ThisDrawing.ModelSpace.AddLine(startPoint, endPoint)
    
    ' Create a circle object in model space
    Dim circObj As AcadCircle
    Dim centerPt(0 To 2) As Double
    Dim radius As Double
    centerPt(0) = 20: centerPt(1) = 30: centerPt(2) = 0
    radius = 3
    Set circObj = ThisDrawing.ModelSpace.AddCircle(centerPt, radius)

    ' Create an ellipse object in model space
    Dim ellObj As AcadEllipse
    Dim majAxis(0 To 2) As Double
    Dim center(0 To 2) As Double
    Dim radRatio As Double
    center(0) = 5#: center(1) = 5#: center(2) = 0#
    majAxis(0) = 10: majAxis(1) = 20#: majAxis(2) = 0#
    radRatio = 0.3
    Set ellObj = ThisDrawing.ModelSpace.AddEllipse(center, majAxis, radRatio)

    ZoomAll
    
    ' Iterate through the model space collection and display
    ' the object name of each entity found.
    
    Dim objName As String
    Dim entry As AcadEntity
    For Each entry In ThisDrawing.ModelSpace
        objName = entry.ObjectName
        entry.Highlight (True)
        MsgBox "The name of this object is " & objName, vbInformation, "ObjectName Example"
        entry.Highlight (False)
    Next
End Sub

Sub Example_Handle()
    ' This example creates several objects in model space.
    ' It then iterates through model space and displays the
    ' Handle for each object found.
    
    ' Create a Ray object in model space
    Dim rayObj As AcadRay
    Dim basePoint(0 To 2) As Double
    Dim SecondPoint(0 To 2) As Double
    basePoint(0) = 3#: basePoint(1) = 3#: basePoint(2) = 0#
    SecondPoint(0) = 1#: SecondPoint(1) = 3#: SecondPoint(2) = 0#
    Set rayObj = ThisDrawing.ModelSpace.AddRay(basePoint, SecondPoint)
    
    ' Create a polyline object in model space
    Dim plineObj As AcadLWPolyline
    Dim points(0 To 5) As Double
    points(0) = 3: points(1) = 7
    points(2) = 9: points(3) = 2
    points(4) = 3: points(5) = 5
    Set plineObj = ThisDrawing.ModelSpace.AddLightWeightPolyline(points)
    plineObj.Closed = True

    ' Create a line object in model space
    Dim lineObj As AcadLine
    Dim startPoint(0 To 2) As Double
    Dim endPoint(0 To 2) As Double
    startPoint(0) = 0: startPoint(1) = 0: startPoint(2) = 0
    endPoint(0) = 2: endPoint(1) = 2: endPoint(2) = 0
    Set lineObj = ThisDrawing.ModelSpace.AddLine(startPoint, endPoint)
    
    ' Create a circle object in model space
    Dim circObj As AcadCircle
    Dim centerPt(0 To 2) As Double
    Dim radius As Double
    centerPt(0) = 5: centerPt(1) = 3: centerPt(2) = 0
    radius = 3
    Set circObj = ThisDrawing.ModelSpace.AddCircle(centerPt, radius)

    ' Create an ellipse object in model space
    Dim ellObj As AcadEllipse
    Dim majAxis(0 To 2) As Double
    Dim center(0 To 2) As Double
    Dim radRatio As Double
    center(0) = 5#: center(1) = 5#: center(2) = 0#
    majAxis(0) = 10: majAxis(1) = 20#: majAxis(2) = 0#
    radRatio = 0.3
    Set ellObj = ThisDrawing.ModelSpace.AddEllipse(center, majAxis, radRatio)


    ZoomAll
    
    ' Iterate through the model space collection and display
    ' the handle of each entity found.
    
    Dim entHandle As String
    Dim entry As AcadEntity
    For Each entry In ThisDrawing.ModelSpace
        entHandle = entry.handle
        entry.Highlight (True)
        MsgBox "The handle of this object is " & entHandle, vbInformation, "Handle Example"
        entry.Highlight (False)
    Next
End Sub
Sub Example_HandleToObject()
    ' This example creates a spline in model space. It then returns the
    ' handle for the spline. The spline is returned from the handle, and
    ' then colored.
    
    ' Create the spline
    Dim splineObj As AcadSpline
    Dim noOfPoints As Integer
    Dim startTan(0 To 2) As Double
    Dim endTan(0 To 2) As Double
    Dim fitPoints(0 To 8) As Double
    
    noOfPoints = 3
    startTan(0) = 0.5: startTan(1) = 0.5: startTan(2) = 0
    endTan(0) = 0.5: endTan(1) = 0.5: endTan(2) = 0
    fitPoints(0) = 1: fitPoints(1) = 1: fitPoints(2) = 0
    fitPoints(3) = 5: fitPoints(4) = 5: fitPoints(5) = 0
    fitPoints(6) = 10: fitPoints(7) = 0: fitPoints(8) = 0
    Set splineObj = ThisDrawing.ModelSpace.AddSpline(fitPoints, startTan, endTan)
    
    ZoomAll
    
    ' Find the handle of the spline
    Dim handle As Integer
    handle = splineObj.handle
    MsgBox "The handle of the Spline is: " & splineObj.handle, , "HandleToObject Example"
        
    ' Find an object from a given handle
    Dim tempObj As AcadObject
    Set tempObj = ThisDrawing.HandleToObject(handle)

    ' Now use the newly initialized object variable to color the object red
    tempObj.Color = acRed
    
    ThisDrawing.Regen True
    MsgBox "The Spline is now red.", , "HandleToObject Example"
    
End Sub
Sub Example_ObjectIDToObject()
    ' This example creates a spline in model space. It then returns the
    ' handle for the spline. The spline is returned from the handle, and
    ' then colored.
    
    ' Create the spline
    Dim splineObj As AcadSpline
    Dim noOfPoints As Integer
    Dim startTan(0 To 2) As Double
    Dim endTan(0 To 2) As Double
    Dim fitPoints(0 To 8) As Double
    
    noOfPoints = 3
    startTan(0) = 0.5: startTan(1) = 0.5: startTan(2) = 0
    endTan(0) = 0.5: endTan(1) = 0.5: endTan(2) = 0
    fitPoints(0) = 1: fitPoints(1) = 1: fitPoints(2) = 0
    fitPoints(3) = 5: fitPoints(4) = 5: fitPoints(5) = 0
    fitPoints(6) = 10: fitPoints(7) = 0: fitPoints(8) = 0
    Set splineObj = ThisDrawing.ModelSpace.AddSpline(fitPoints, startTan, endTan)
    
    ZoomAll
    
    ' Find the objectID of the spline
    Dim objectID As Long
    objectID = splineObj.objectID
    MsgBox "The objectID of the Spline is: " & splineObj.objectID, , "ObjectIDToObject Example"
        
    ' Find an object from a given objectID
    Dim tempObj As AcadObject
    Set tempObj = ThisDrawing.ObjectIdToObject(objectID)

    ' Now use the newly initialized object variable to color the object red
    tempObj.Color = acRed
    
    ThisDrawing.Regen True
    MsgBox "The Spline is now red.", , "ObjectIDToObject Example"
    
End Sub

Sub Example_ObjectID()
    ' This example creates several objects in model space.
    ' It then iterates through model space and displays the
    ' ObjectID for each object found.
    
    ' Create a Ray object in model space
    Dim rayObj As AcadRay
    Dim basePoint(0 To 2) As Double
    Dim SecondPoint(0 To 2) As Double
    basePoint(0) = 3#: basePoint(1) = 3#: basePoint(2) = 0#
    SecondPoint(0) = 1#: SecondPoint(1) = 3#: SecondPoint(2) = 0#
    Set rayObj = ThisDrawing.ModelSpace.AddRay(basePoint, SecondPoint)
    
    ' Create a polyline object in model space
    Dim plineObj As AcadLWPolyline
    Dim points(0 To 5) As Double
    points(0) = 3: points(1) = 7
    points(2) = 9: points(3) = 2
    points(4) = 3: points(5) = 5
    Set plineObj = ThisDrawing.ModelSpace.AddLightWeightPolyline(points)
    plineObj.Closed = True

    ' Create a line object in model space
    Dim lineObj As AcadLine
    Dim startPoint(0 To 2) As Double
    Dim endPoint(0 To 2) As Double
    startPoint(0) = 0: startPoint(1) = 0: startPoint(2) = 0
    endPoint(0) = 2: endPoint(1) = 2: endPoint(2) = 0
    Set lineObj = ThisDrawing.ModelSpace.AddLine(startPoint, endPoint)
    
    ' Create a circle object in model space
    Dim circObj As AcadCircle
    Dim centerPt(0 To 2) As Double
    Dim radius As Double
    centerPt(0) = 5: centerPt(1) = 3: centerPt(2) = 0
    radius = 3
    Set circObj = ThisDrawing.ModelSpace.AddCircle(centerPt, radius)

    ' Create an ellipse object in model space
    Dim ellObj As AcadEllipse
    Dim majAxis(0 To 2) As Double
    Dim center(0 To 2) As Double
    Dim radRatio As Double
    center(0) = 5#: center(1) = 5#: center(2) = 0#
    majAxis(0) = 10: majAxis(1) = 20#: majAxis(2) = 0#
    radRatio = 0.3
    Set ellObj = ThisDrawing.ModelSpace.AddEllipse(center, majAxis, radRatio)

    ZoomAll
    
    ' Iterate through the model space collection and display
    ' the ObjectID of each entity found.
    
    Dim entObjectID As Long
    Dim entry As AcadEntity
    For Each entry In ThisDrawing.ModelSpace
        entObjectID = entry.objectID
        entry.Highlight (True)
        MsgBox "The ObjectID of this object is " & entObjectID, vbInformation, "ObjectID Example"
        entry.Highlight (False)
    Next
End Sub
Sub Example_ElevationModelSpace()
    ' This example changes the model space elevation of the current drawing
    ' and then resets it to the original value again.
    
    Dim currElevation As Double
    
    currElevation = ThisDrawing.ElevationModelSpace
    MsgBox "The current model space elevation is " & ThisDrawing.ElevationModelSpace, vbInformation, "ElevationModelSpace Example"
    
    ' Change the elevation
    ThisDrawing.ElevationModelSpace = currElevation + 2
    MsgBox "The new model space elevation is " & ThisDrawing.ElevationModelSpace, vbInformation, "ElevationModelSpace Example"
    
    ' Reset the elevation to its original value
    ThisDrawing.ElevationModelSpace = currElevation
    MsgBox "The model space elevation is reset to " & ThisDrawing.ElevationModelSpace, vbInformation, "ElevationModelSpace Example"

End Sub
Sub Example_ElevationPaperSpace()
    ' This example changes the paperspace elevation of the current drawing
    ' and then resets it to the original value again.
    
    Dim currElevation As Double
    
    currElevation = ThisDrawing.ElevationPaperSpace
    MsgBox "The current paper space elevation is " & ThisDrawing.ElevationPaperSpace, vbInformation, "ElevationpaperSpace Example"
    
    ' Change the elevation
    ThisDrawing.ElevationPaperSpace = currElevation + 2
    MsgBox "The new paperspace elevation is " & ThisDrawing.ElevationPaperSpace, vbInformation, "ElevationpaperSpace Example"
    
    ' Reset the elevation to its original value
    ThisDrawing.ElevationPaperSpace = currElevation
    MsgBox "The paperspace elevation is reset to " & ThisDrawing.ElevationPaperSpace, vbInformation, "ElevationPaperSpace Example"

End Sub
Sub Example_EndTangent()
    ' This example creates a spline. It then queries the current setting for
    ' the EndTangent, and then changes the EndTangent to a new value.

    ' Create the spline
    Dim splineObj As AcadSpline
    Dim noOfPoints As Integer
    Dim startTan(0 To 2) As Double
    Dim endTan(0 To 2) As Double
    Dim fitPoints(0 To 8) As Double
    Dim msg As String
    
    noOfPoints = 3
    startTan(0) = 0.5: startTan(1) = 0.5: startTan(2) = 0
    endTan(0) = 0.5: endTan(1) = 0.5: endTan(2) = 0
    fitPoints(0) = 1: fitPoints(1) = 1: fitPoints(2) = 0
    fitPoints(3) = 5: fitPoints(4) = 5: fitPoints(5) = 0
    fitPoints(6) = 10: fitPoints(7) = 0: fitPoints(8) = 0
    Set splineObj = ThisDrawing.ModelSpace.AddSpline(fitPoints, startTan, endTan)
    
    ZoomAll
    GoSub GETPOINTS
    MsgBox "The EndTangent for the spline is " & msg, vbInformation, "EndTangent Example"

    ' Change the end tangent of Spline to (1.5,0.707,2)
    Dim newTan(0 To 2) As Double
    newTan(0) = 1.5: newTan(1) = 0.707: newTan(2) = 2
    splineObj.EndTangent = newTan

    ThisDrawing.Regen True
    GoSub GETPOINTS
    MsgBox "The EndTangent has been changed to " & msg, vbInformation, "EndTangent Example"

    Exit Sub

GETPOINTS:
    msg = ""
    ' Get the coordinates from the end tangent
    Dim count As Integer
    For count = 0 To 2
        msg = msg & Format(splineObj.EndTangent(count), "0.###") & ", "
    Next
    msg = VBA.Left(msg, Len(msg) - 2)
    Return
End Sub

Sub Example_StartTangent()
    ' This example creates a spline. It then queries the current setting for
    ' the StartTangent, and then changes the StartTangent to a new value.

    ' Create the spline
    Dim splineObj As AcadSpline
    Dim noOfPoints As Integer
    Dim startTan(0 To 2) As Double
    Dim endTan(0 To 2) As Double
    Dim fitPoints(0 To 8) As Double
    Dim msg As String
    
    noOfPoints = 3
    startTan(0) = 0.5: startTan(1) = 0.5: startTan(2) = 0
    endTan(0) = 0.5: endTan(1) = 0.5: endTan(2) = 0
    fitPoints(0) = 1: fitPoints(1) = 1: fitPoints(2) = 0
    fitPoints(3) = 5: fitPoints(4) = 5: fitPoints(5) = 0
    fitPoints(6) = 10: fitPoints(7) = 0: fitPoints(8) = 0
    Set splineObj = ThisDrawing.ModelSpace.AddSpline(fitPoints, startTan, endTan)
    
    ThisDrawing.Regen True
    GoSub GETPOINTS
    MsgBox "The StartTangent for the spline is  " & msg, vbInformation, "StartTangent Example"

    Dim newTan(0 To 2) As Double
    newTan(0) = 1.5: newTan(1) = 0.707: newTan(2) = 2
    
    ' Change the start tangent of Spline to (1.5, 0.707, 2)
    splineObj.EndTangent = newTan
    
    ThisDrawing.Regen True
    GoSub GETPOINTS
    MsgBox "The StartTangent has been changed to " & msg, vbInformation, "StartTangent Example"

    Exit Sub

GETPOINTS:
    Dim count As Integer
    msg = ""
    ' Get the coordinates from the start tangent
    For count = 0 To 2
        msg = msg & Format(splineObj.StartTangent(count), "0.###") & ", "
    Next
    msg = VBA.Left(msg, Len(msg) - 2)
    Return
End Sub
Sub Example_StartUndoMark()
    ' This example creates a series of lines, each one with an undo marker
    ' defined for it. After lines are created you can switch to AutoCAD and type
    ' the Undo command, and only one line at a time will be undone. If StartUndoMark
    ' call is not made, an undo in AutoCAD will undo all the lines at once.
    
    Dim line As AcadLine
    Dim stPnt(0 To 2) As Double
    Dim endPnt(0 To 2) As Double
    stPnt(0) = 1: stPnt(1) = 2: stPnt(2) = 0
    endPnt(0) = 2: stPnt(1) = 1: stPnt(2) = 0
    
    ' Create the lines
    Dim j As Integer
    For j = 0 To 3
        ThisDrawing.StartUndoMark
        Set line = ThisDrawing.ModelSpace.AddLine(stPnt, endPnt)
        stPnt(0) = stPnt(0) + 3
        endPnt(0) = endPnt(0) + 3
        ThisDrawing.EndUndoMark
    Next
    ZoomAll
    
End Sub
Sub Example_EndUndoMark()
    ' This example creates a series of lines, each one with an undo marker
    ' defined for it. After lines are created you can switch to AutoCAD and type
    ' the Undo command, and only one line at a time will be undone. If StartUndoMark
    ' call is not made, an undo in AutoCAD will undo all the lines at once.
    
    Dim line As AcadLine
    Dim stPnt(0 To 2) As Double
    Dim endPnt(0 To 2) As Double
    stPnt(0) = 1: stPnt(1) = 2: stPnt(2) = 0
    endPnt(0) = 2: stPnt(1) = 1: stPnt(2) = 0
    
    ' Create the lines
    Dim j As Integer
    For j = 0 To 3
        ThisDrawing.StartUndoMark
        Set line = ThisDrawing.ModelSpace.AddLine(stPnt, endPnt)
        stPnt(0) = stPnt(0) + 3
        endPnt(0) = endPnt(0) + 3
        ThisDrawing.EndUndoMark
    Next
    ZoomAll
    
End Sub
Sub Example_ExtLine1Point()
    ' This example creates an aligned dimension and then changes the
    ' ExtLine1Point property for that dimension.

    Dim dimObj As AcadDimAligned
    Dim point1(0 To 2) As Double
    Dim point2(0 To 2) As Double
    Dim location(0 To 2) As Double
    
    ' Define the dimension
    point1(0) = 5#: point1(1) = 5#: point1(2) = 0#
    point2(0) = 10#: point2(1) = 5#: point2(2) = 0#
    location(0) = 5#: location(1) = 7#: location(2) = 0#
    
    ' Create an aligned dimension object in model space
    Set dimObj = ThisDrawing.ModelSpace.AddDimAligned(point1, point2, location)
    ZoomAll
    MsgBox "The current value for ExtLine1Point is " & dimObj.ExtLine1Point(0) & ", " & dimObj.ExtLine1Point(1) & ", " & dimObj.ExtLine1Point(2), vbInformation, "ExtLine1Point Example"
    
    ' Change the endpoint of the first extension line
    point1(0) = 2: point1(1) = 5: point1(2) = 0
    dimObj.ExtLine1Point = point1
    dimObj.Update
    
    ' Return the endpoint of the first extension line
    ' Note that the return value is a Variant
    Dim retPnt As Variant
    retPnt = dimObj.ExtLine1Point
    
    MsgBox "The new value for ExtLine1Point is " & dimObj.ExtLine1Point(0) & ", " & dimObj.ExtLine1Point(1) & ", " & dimObj.ExtLine1Point(2), vbInformation, "ExtLine1Point Example"
End Sub
Sub Example_ExtLine2Point()
    ' This example creates an aligned dimension and then changes the
    ' ExtLine2Point property for that dimension.

    Dim dimObj As AcadDimAligned
    Dim point1(0 To 2) As Double
    Dim point2(0 To 2) As Double
    Dim location(0 To 2) As Double
    
    ' Define the dimension
    point1(0) = 5#: point1(1) = 5#: point1(2) = 0#
    point2(0) = 10#: point2(1) = 5#: point2(2) = 0#
    location(0) = 5#: location(1) = 7#: location(2) = 0#
    
    ' Create an aligned dimension object in model space
    Set dimObj = ThisDrawing.ModelSpace.AddDimAligned(point1, point2, location)
    ZoomAll
    MsgBox "The current value for ExtLine2Point is " & dimObj.ExtLine2Point(0) & ", " & dimObj.ExtLine2Point(1) & ", " & dimObj.ExtLine2Point(2), vbInformation, "ExtLine2Point Example"
    
    ' Change the endpoint of the second extension line
    point1(0) = 12: point1(1) = 5: point1(2) = 0
    dimObj.ExtLine2Point = point1
    dimObj.Update
    
    ' Return the endpoint of the second extension line
    ' Note that the return value is a Variant
    Dim retPoint As Variant
    retPoint = dimObj.ExtLine2Point
    
    MsgBox "The new value for ExtLine2Point is " & dimObj.ExtLine2Point(0) & ", " & dimObj.ExtLine2Point(1) & ", " & dimObj.ExtLine2Point(2), vbInformation, "ExtLine2Point Example"
End Sub
Sub Example_AddDimAligned()
    ' This example creates an aligned dimension in model space.

    Dim dimObj As AcadDimAligned
    Dim point1(0 To 2) As Double
    Dim point2(0 To 2) As Double
    Dim location(0 To 2) As Double
    
    ' Define the dimension
    point1(0) = 5#: point1(1) = 5#: point1(2) = 0#
    point2(0) = 10#: point2(1) = 5#: point2(2) = 0#
    location(0) = 5#: location(1) = 7#: location(2) = 0#
    
    ' Create an aligned dimension object in model space
    Set dimObj = ThisDrawing.ModelSpace.AddDimAligned(point1, point2, location)
    ZoomAll
End Sub
Sub Example_TextPosition()
    ' This example creates an aligned dimension and then changes the
    ' TextPosition property for that dimension.
    
    Dim dimObj As AcadDimAligned
    Dim point1(0 To 2) As Double
    Dim point2(0 To 2) As Double
    Dim location(0 To 2) As Double
    
    ' Define the dimension
    point1(0) = 5#: point1(1) = 3#: point1(2) = 0#
    point2(0) = 10#: point2(1) = 3#: point2(2) = 0#
    location(0) = 7.5: location(1) = 5#: location(2) = 0#
    
    ' Create an aligned dimension object in model space
    Set dimObj = ThisDrawing.ModelSpace.AddDimAligned(point1, point2, location)
    ZoomAll
    MsgBox "The current text position for the dimension is " & dimObj.TextPosition(0) & ", " & dimObj.TextPosition(1) & ", " & dimObj.TextPosition(2), vbInformation, "TextPosition Example"
    
    ' Change the text position location
    location(0) = 8.5: location(1) = 7: location(2) = 0
    dimObj.TextPosition = location
    dimObj.Update
    
    ' Return the endpoint of the first extension line
    ' Note that the return value is a Variant
    Dim retPoint As Variant
    retPoint = dimObj.TextPosition
    
    MsgBox "The new text position for the dimension is " & dimObj.TextPosition(0) & ", " & dimObj.TextPosition(1) & ", " & dimObj.TextPosition(2), vbInformation, "TextPosition Example"
End Sub
Sub Example_TextRotation()
    ' This example creates an aligned dimension and then changes the
    ' TextRotation property for that dimension.

    Dim dimObj As AcadDimAligned
    Dim point1(0 To 2) As Double
    Dim point2(0 To 2) As Double
    Dim location(0 To 2) As Double
    
    ' Define the dimension
    point1(0) = 5#: point1(1) = 3#: point1(2) = 0#
    point2(0) = 10#: point2(1) = 3#: point2(2) = 0#
    location(0) = 7.5: location(1) = 5#: location(2) = 0#
    
    ' Create an aligned dimension object in model space
    Set dimObj = ThisDrawing.ModelSpace.AddDimAligned(point1, point2, location)
    ZoomAll
    MsgBox "The current text rotation angle for the dimension is " & dimObj.TextRotation & " radians.", vbInformation, "TextRotation Example"
    
    ' Change the text rotation angle to 45 degrees (.707 radians)
    dimObj.TextRotation = 0.707
    dimObj.Update
        
    MsgBox "The new text rotation angle for the dimension is " & dimObj.TextRotation & " radians.", vbInformation, "TextRotation Example"
End Sub
Sub Example_TextOverride()
    ' This example creates an aligned dimension and then changes the
    ' TextOverride property for that dimension.

    Dim dimObj As AcadDimAligned
    Dim point1(0 To 2) As Double
    Dim point2(0 To 2) As Double
    Dim location(0 To 2) As Double
    
    ' Define the dimension
    point1(0) = 5#: point1(1) = 3#: point1(2) = 0#
    point2(0) = 10#: point2(1) = 3#: point2(2) = 0#
    location(0) = 7.5: location(1) = 5#: location(2) = 0#
    
    ' Create an aligned dimension object in model space
    Set dimObj = ThisDrawing.ModelSpace.AddDimAligned(point1, point2, location)
    ZoomAll
    MsgBox "The initial text string for the dimension contains only the dimension value.", vbInformation, "TextOverride Example"
    
    ' Change the text string for the dimension
    dimObj.TextOverride = "The value is <>"
    dimObj.Update
    MsgBox "The text string for the dimension has been replaced. However, the dimension value is still represented.", vbInformation, "TextOverride Example"
    
    ' Reset the text string for the dimension
    dimObj.TextOverride = ""
    dimObj.Update
        
    MsgBox "The text string for the dimension is reset.", vbInformation, "TextOverride Example"
End Sub
Sub Example_StyleName()
    ' This example creates an aligned dimension and then changes the
    ' StyleName property for that dimension.

    Dim dimObj As AcadDimAligned
    Dim point1(0 To 2) As Double
    Dim point2(0 To 2) As Double
    Dim location(0 To 2) As Double
    Dim currStyleName As String
    
    ' Define the dimension
    point1(0) = 5#: point1(1) = 3#: point1(2) = 0#
    point2(0) = 10#: point2(1) = 3#: point2(2) = 0#
    location(0) = 7.5: location(1) = 5#: location(2) = 0#

    ' Create an aligned dimension object in model space
    Set dimObj = ThisDrawing.ModelSpace.AddDimAligned(point1, point2, location)
    ZoomAll
    currStyleName = dimObj.StyleName
    MsgBox "The initial StyleName for the dimension is " & dimObj.StyleName, vbInformation, "TextString Example"
    
    ' Create a new dimension style
    ThisDrawing.DimStyles.Add ("NewDimensionStyle")
    
    ' Change the text string for the dimension
    dimObj.StyleName = "NewDimensionStyle"
    dimObj.Update
    MsgBox "The new StyleName for the dimension is " & dimObj.StyleName, vbInformation, "TextString Example"
    
    ' Reset the text string for the dimension
    dimObj.StyleName = currStyleName
    dimObj.Update
    MsgBox "The StyleName for the dimension has been reset to " & dimObj.StyleName, vbInformation, "TextString Example"
End Sub
Sub Example_DrawingDirection()
    ' This example changes the drawing direction for an MText object
    ' in model space.
    
    Dim MTextObj As AcadMText
    Dim corner1(0 To 2) As Double
    Dim width As Double
    Dim text As String
    
    ' Define the mtext object
    corner1(0) = 0#: corner1(1) = 6#: corner1(2) = 0#
    width = 7
    text = "This is a text String."

    ' Create the mtext object in model space
    Set MTextObj = ThisDrawing.ModelSpace.AddMText(corner1, width, text)
    ZoomAll
    
    'Change the drawing direction of the mtext object
    MTextObj.DrawingDirection = acLeftToRight
    ZoomAll
    MsgBox "The DrawingDirection of the text is left to right.", vbInformation, "DrawingDirection Example"
        
    MTextObj.DrawingDirection = acTopToBottom
    ZoomAll
    MsgBox "The DrawingDirection of the text is top to bottom.", vbInformation, "DrawingDirection Example"
        
    ' Return the drawing direction
    Dim retDirection As Integer
    retDirection = MTextObj.DrawingDirection
    
End Sub
Sub Example_ExtLine1StartPoint()
    ' This example creates an angular dimension. It then changes
    ' the location of the ExtLine1StartPoint.
    
    Dim dimObj As AcadDimAngular
    Dim angVert(0 To 2) As Double
    Dim FirstPoint(0 To 2) As Double
    Dim SecondPoint(0 To 2) As Double
    Dim TextPoint(0 To 2) As Double
    
    ' Define the dimension
    angVert(0) = 0#: angVert(1) = 5#: angVert(2) = 0#
    FirstPoint(0) = 1#: FirstPoint(1) = 7#: FirstPoint(2) = 0#
    SecondPoint(0) = 1#: SecondPoint(1) = 3#: SecondPoint(2) = 0#
    TextPoint(0) = 3#: TextPoint(1) = 5#: TextPoint(2) = 0#
    
    ' Create the angular dimension in model space
    Set dimObj = ThisDrawing.ModelSpace.AddDimAngular(angVert, FirstPoint, SecondPoint, TextPoint)
    ZoomAll
    MsgBox "The current value of ExtLine1StartPoint is " & dimObj.ExtLine1StartPoint(0) & ", " & dimObj.ExtLine1StartPoint(1) & ", " & dimObj.ExtLine1StartPoint(2), vbInformation, "ExtLine1StartPoint Example"
    
    ' Change the startpoint of the first extension line
    FirstPoint(0) = 0: FirstPoint(1) = 3: FirstPoint(2) = 0
    dimObj.ExtLine1StartPoint = FirstPoint
    dimObj.Update
    
    ' Return the startpoint of the first extension line
    ' Note that the return value is a Variant
    Dim retPnt As Variant
    retPnt = dimObj.ExtLine1StartPoint
    MsgBox "The new value of ExtLine1StartPoint is " & dimObj.ExtLine1StartPoint(0) & ", " & dimObj.ExtLine1StartPoint(1) & ", " & dimObj.ExtLine1StartPoint(2), vbInformation, "ExtLine1StartPoint Example"
End Sub
Sub Example_ExtLine1EndPoint()
    ' This example creates an angular dimension. It then changes
    ' the location of the ExtLine1EndPoint.
    
    Dim dimObj As AcadDimAngular
    Dim angVert(0 To 2) As Double
    Dim FirstPoint(0 To 2) As Double
    Dim SecondPoint(0 To 2) As Double
    Dim TextPoint(0 To 2) As Double
    
    ' Define the dimension
    angVert(0) = 0#: angVert(1) = 5#: angVert(2) = 0#
    FirstPoint(0) = 1#: FirstPoint(1) = 7#: FirstPoint(2) = 0#
    SecondPoint(0) = 1#: SecondPoint(1) = 3#: SecondPoint(2) = 0#
    TextPoint(0) = 3#: TextPoint(1) = 5#: TextPoint(2) = 0#
    
    ' Create the angular dimension in model space
    Set dimObj = ThisDrawing.ModelSpace.AddDimAngular(angVert, FirstPoint, SecondPoint, TextPoint)
    ZoomAll
    MsgBox "The current value of ExtLine1EndPoint is " & dimObj.ExtLine1EndPoint(0) & ", " & dimObj.ExtLine1EndPoint(1) & ", " & dimObj.ExtLine1EndPoint(2), vbInformation, "ExtLine1EndPoint Example"
    
    ' Change the endpoint of the first extension line
    SecondPoint(0) = 0: SecondPoint(1) = 3: SecondPoint(2) = 0
    dimObj.ExtLine1EndPoint = SecondPoint
    dimObj.Update
    
    ' Return the endpoint of the first extension line
    ' Note that the return value is a Variant
    Dim retPnt As Variant
    retPnt = dimObj.ExtLine1EndPoint
    MsgBox "The new value of ExtLine1EndPoint is " & dimObj.ExtLine1EndPoint(0) & ", " & dimObj.ExtLine1EndPoint(1) & ", " & dimObj.ExtLine1EndPoint(2), vbInformation, "ExtLine1EndPoint Example"
End Sub
Sub Example_ExtLine2EndPoint()
    ' This example creates an angular dimension. It then changes
    ' the location of the ExtLine2EndPoint.
    
    Dim dimObj As AcadDimAngular
    Dim angVert(0 To 2) As Double
    Dim FirstPoint(0 To 2) As Double
    Dim SecondPoint(0 To 2) As Double
    Dim TextPoint(0 To 2) As Double
    
    ' Define the dimension
    angVert(0) = 0#: angVert(1) = 5#: angVert(2) = 0#
    FirstPoint(0) = 1#: FirstPoint(1) = 7#: FirstPoint(2) = 0#
    SecondPoint(0) = 1#: SecondPoint(1) = 3#: SecondPoint(2) = 0#
    TextPoint(0) = 3#: TextPoint(1) = 5#: TextPoint(2) = 0#
    
    ' Create the angular dimension in model space
    Set dimObj = ThisDrawing.ModelSpace.AddDimAngular(angVert, FirstPoint, SecondPoint, TextPoint)
    ZoomAll
    MsgBox "The current value of ExtLine2EndPoint is " & dimObj.ExtLine2EndPoint(0) & ", " & dimObj.ExtLine2EndPoint(1) & ", " & dimObj.ExtLine2EndPoint(2), vbInformation, "ExtLine2EndPoint Example"
    
    ' Change the endpoint of the second extension line
    SecondPoint(0) = 1: SecondPoint(1) = 4: SecondPoint(2) = 0
    dimObj.ExtLine2EndPoint = SecondPoint
    dimObj.Update
    
    ' Return the endpoint of the second extension line
    ' Note that the return value is a Variant
    Dim retPnt As Variant
    retPnt = dimObj.ExtLine2EndPoint
    MsgBox "The new value of ExtLine2EndPoint is " & dimObj.ExtLine2EndPoint(0) & ", " & dimObj.ExtLine2EndPoint(1) & ", " & dimObj.ExtLine2EndPoint(2), vbInformation, "ExtLine2EndPoint Example"
End Sub
Sub Example_ExtLine2StartPoint()
    ' This example creates an angular dimension. It then changes
    ' the location of the ExtLine2StartPoint.
    
    Dim dimObj As AcadDimAngular
    Dim angVert(0 To 2) As Double
    Dim FirstPoint(0 To 2) As Double
    Dim SecondPoint(0 To 2) As Double
    Dim TextPoint(0 To 2) As Double
    
    ' Define the dimension
    angVert(0) = 0#: angVert(1) = 5#: angVert(2) = 0#
    FirstPoint(0) = 1#: FirstPoint(1) = 7#: FirstPoint(2) = 0#
    SecondPoint(0) = 1#: SecondPoint(1) = 3#: SecondPoint(2) = 0#
    TextPoint(0) = 3#: TextPoint(1) = 5#: TextPoint(2) = 0#
    
    ' Create the angular dimension in model space
    Set dimObj = ThisDrawing.ModelSpace.AddDimAngular(angVert, FirstPoint, SecondPoint, TextPoint)
    ZoomAll
    MsgBox "The current value of ExtLine2StartPoint is " & dimObj.ExtLine2StartPoint(0) & ", " & dimObj.ExtLine2StartPoint(1) & ", " & dimObj.ExtLine2StartPoint(2), vbInformation, "ExtLine2StartPoint Example"
    
    ' Change the startpoint of the second extension line
    FirstPoint(0) = 1: FirstPoint(1) = 4: FirstPoint(2) = 0
    dimObj.ExtLine2StartPoint = FirstPoint
    dimObj.Update
    
    ' Return the startpoint of the second extension line
    ' Note that the return value is a Variant
    Dim retPnt As Variant
    retPnt = dimObj.ExtLine2StartPoint
    MsgBox "The new value of ExtLine2StartPoint is " & dimObj.ExtLine2StartPoint(0) & ", " & dimObj.ExtLine2StartPoint(1) & ", " & dimObj.ExtLine2StartPoint(2), vbInformation, "ExtLine2StartPoint Example"
End Sub
Sub Example_AddDimAngular()
    ' This example creates an angular dimension in model space.
    
    Dim dimObj As AcadDimAngular
    Dim angVert(0 To 2) As Double
    Dim FirstPoint(0 To 2) As Double
    Dim SecondPoint(0 To 2) As Double
    Dim TextPoint(0 To 2) As Double
    
    ' Define the dimension
    angVert(0) = 0#: angVert(1) = 5#: angVert(2) = 0#
    FirstPoint(0) = 1#: FirstPoint(1) = 7#: FirstPoint(2) = 0#
    SecondPoint(0) = 1#: SecondPoint(1) = 3#: SecondPoint(2) = 0#
    TextPoint(0) = 3#: TextPoint(1) = 5#: TextPoint(2) = 0#
    
    ' Create the angular dimension in model space
    Set dimObj = ThisDrawing.ModelSpace.AddDimAngular(angVert, FirstPoint, SecondPoint, TextPoint)
    ZoomAll
    
End Sub
Sub Example_AddDimDiametric()
    ' This example creates a diametric dimension in model space.
    
    Dim dimObj As AcadDimDiametric
    Dim chordPoint(0 To 2) As Double
    Dim farChordPoint(0 To 2) As Double
    Dim leaderLength As Double
    
    ' Define the dimension
    chordPoint(0) = 5#: chordPoint(1) = 3#: chordPoint(2) = 0#
    farChordPoint(0) = 5#: farChordPoint(1) = 5#: farChordPoint(2) = 0#
    leaderLength = 1#
    
    ' Create the diametric dimension in model space
    Set dimObj = ThisDrawing.ModelSpace.AddDimDiametric(chordPoint, farChordPoint, leaderLength)
    ZoomAll
    
End Sub
Sub Example_LeaderLength()
    ' This example creates a diametric dimension
    ' and returns the LeaderLength for that dimension.
    
    Dim dimObj As AcadDimDiametric
    Dim chordPoint(0 To 2) As Double
    Dim farChordPoint(0 To 2) As Double
    Dim leaderLength As Double
    
    ' Define the dimension
    chordPoint(0) = 5#: chordPoint(1) = 3#: chordPoint(2) = 0#
    farChordPoint(0) = 5#: farChordPoint(1) = 5#: farChordPoint(2) = 0#
    leaderLength = 1#
    
    ' Create the diametric dimension in model space
    Set dimObj = ThisDrawing.ModelSpace.AddDimDiametric(chordPoint, farChordPoint, leaderLength)
    ZoomAll
End Sub
Sub Example_FieldLength()
    ' This example creates an attribute definition in model space.
    ' It then queries the initial value of the FieldLenght property,
    ' changes that value, and finally resets the value.
    
    Dim attributeObj As AcadAttribute
    Dim height As Double
    Dim mode As Long
    Dim prompt As String
    Dim insertionPoint(0 To 2) As Double
    Dim tag As String
    Dim value As String
    
    ' Define the attribute definition
    height = 1#
    mode = acAttributeModeVerify
    prompt = "New Prompt"
    insertionPoint(0) = 5#: insertionPoint(1) = 5#: insertionPoint(2) = 0
    tag = "New Tag"
    value = "New Value"
    
    ' Create the attribute definition object in model space
    Set attributeObj = ThisDrawing.ModelSpace.AddAttribute(height, mode, prompt, insertionPoint, tag, value)
    ZoomAll
    
    ' Return the current field length of the attribute
    Dim currFieldLength As Integer
    currFieldLength = attributeObj.FieldLength
    MsgBox "The FieldLength of the attribute is " & attributeObj.FieldLength, vbInformation, "FieldLength Example"
    
    ' Change the field length
    attributeObj.FieldLength = currFieldLength + 2
    attributeObj.Update
    MsgBox "The new FieldLength of the attribute is " & attributeObj.FieldLength, vbInformation, "FieldLength Example"
    
    ' Reset the field length to the original value
    attributeObj.FieldLength = currFieldLength
    attributeObj.Update
    MsgBox "The FieldLength of the attribute is reset to " & attributeObj.FieldLength, vbInformation, "FieldLength Example"
    
End Sub
Sub Example_AddAttribute()
    ' This example creates an attribute definition in model space.
    
    Dim attributeObj As AcadAttribute
    Dim height As Double
    Dim mode As Long
    Dim prompt As String
    Dim insertionPoint(0 To 2) As Double
    Dim tag As String
    Dim value As String
    
    ' Define the attribute definition
    height = 1#
    mode = acAttributeModeVerify
    prompt = "New Prompt"
    insertionPoint(0) = 5#: insertionPoint(1) = 5#: insertionPoint(2) = 0
    tag = "New Tag"
    value = "New Value"
    
    ' Create the attribute definition object in model space
    Set attributeObj = ThisDrawing.ModelSpace.AddAttribute(height, mode, prompt, insertionPoint, tag, value)
    ZoomAll
    
End Sub
Sub Example_Mode()
    ' This example creates an attribute definition in model space.
    ' It then queries the initial value of the Mode property,
    ' changes that value, and finally resets the value.
    
    Dim attributeObj As AcadAttribute
    Dim height As Double
    Dim mode As Long
    Dim prompt As String
    Dim insertionPoint(0 To 2) As Double
    Dim tag As String
    Dim value As String
    
    ' Define the attribute definition
    height = 1#
    mode = acAttributeModeVerify
    prompt = "New Prompt"
    insertionPoint(0) = 5#: insertionPoint(1) = 5#: insertionPoint(2) = 0
    tag = "New Tag"
    value = "New Value"
    
    ' Create the attribute definition object in model space
    Set attributeObj = ThisDrawing.ModelSpace.AddAttribute(height, mode, prompt, insertionPoint, tag, value)
    ZoomAll
    
    ' Return the current field length of the attribute
    Dim currMode As Integer
    Dim constant As String
    currMode = attributeObj.mode
    GoSub GETCONSTANT
    MsgBox "The Mode of the attribute is " & constant, vbInformation, "Mode Example"
    
    ' Change the field length
    attributeObj.mode = acAttributeModeInvisible
    GoSub GETCONSTANT
    attributeObj.Update
    MsgBox "The new Mode of the attribute is " & constant, vbInformation, "Mode Example"
    
    ' Reset the field length to the original value
    attributeObj.mode = currMode
    GoSub GETCONSTANT
    attributeObj.Update
    MsgBox "The Mode of the attribute is reset to " & constant, vbInformation, "Mode Example"
    Exit Sub
    
GETCONSTANT:
    ' Get the constant that corresponds to the current mode
    constant = Choose(attributeObj.mode, "acAttributeModeInvisible", "acAttributeModeConstant", "", "acAttributeModeVerify", "", "", "", "acAttributeModePreset")
    Return
End Sub
Sub Example_InsertionPoint()
    ' This example creates a text object in model space.
    ' It then changes the insertion point of the text object.

    Dim textObj As AcadText
    Dim textString As String
    Dim insertionPoint(0 To 2) As Double
    Dim height As Double
    
    ' Define the text object
    textString = "Hello, World."
    insertionPoint(0) = 2: insertionPoint(1) = 2: insertionPoint(2) = 0
    height = 0.5
    
    ' Create the text object in model space
    Set textObj = ThisDrawing.ModelSpace.AddText(textString, insertionPoint, height)
    ZoomAll
    
    ' Return the current value of the insertion point
    Dim currInsertionPoint As Variant
    currInsertionPoint = textObj.insertionPoint
    MsgBox "The insertion point of the text is " & currInsertionPoint(0) & ", " & currInsertionPoint(1) & ", " & currInsertionPoint(2), vbInformation, "InsertionPoint Example"
    
    ' Change the insertion point of the text object and
    ' update the display of the text object.
    insertionPoint(0) = 3: insertionPoint(1) = 3: insertionPoint(2) = 0
    textObj.insertionPoint = insertionPoint
    textObj.Update
    MsgBox "The new insertion point of the text is " & textObj.insertionPoint(0) & ", " & textObj.insertionPoint(1) & ", " & textObj.insertionPoint(2), vbInformation, "InsertionPoint Example"
    
End Sub
Sub Example_TextGenerationFlag()
    ' This example creates a text object in model space.
    ' It then changes the TextGenerationFlag of the text object.

    Dim textObj As AcadText
    Dim textString As String
    Dim insertionPoint(0 To 2) As Double
    Dim height As Double
    
    ' Define the text object
    textString = "Hello, World."
    insertionPoint(0) = 3: insertionPoint(1) = 3: insertionPoint(2) = 0
    height = 0.5
    
    ' Create the text object in model space
    Set textObj = ThisDrawing.ModelSpace.AddText(textString, insertionPoint, height)
    ZoomAll
    MsgBox "The TextGenerationFlag has not been set.", vbInformation, "TextGenerationFlag Example"
    
    ' Change the value of the TextGenerationFlag
    textObj.TextGenerationFlag = acTextFlagBackward
    ZoomAll
    MsgBox "The TextGenerationFlag is set to acTextFlagBackward.", vbInformation, "TextGenerationFlag Example"
    
    textObj.TextGenerationFlag = acTextFlagUpsideDown
    ZoomAll
    MsgBox "The TextGenerationFlag is set to acTextFlagUpsideDown.", vbInformation, "TextGenerationFlag Example"
    
    textObj.TextGenerationFlag = acTextFlagBackward & acTextFlagUpsideDown
    ZoomAll
    MsgBox "The TextGenerationFlag is set to acTextFlagBackward & acTextFlagUpsideDown.", vbInformation, "TextGenerationFlag Example"
    
End Sub
Sub Example_AddText()
    ' This example creates a text object in model space.

    Dim textObj As AcadText
    Dim textString As String
    Dim insertionPoint(0 To 2) As Double
    Dim height As Double
    
    ' Define the text object
    textString = "Hello, World."
    insertionPoint(0) = 2: insertionPoint(1) = 2: insertionPoint(2) = 0
    height = 0.5
    
    ' Create the text object in model space
    Set textObj = ThisDrawing.ModelSpace.AddText(textString, insertionPoint, height)
    ZoomAll
    
End Sub
Sub Example_TextAlignmentPoint()
    ' This example creates a text object in model space.
    ' It then changes the TextAlignmentPoint and HorizontalAlignment
    ' properties of the text object.

    Dim textObj As AcadText
    Dim textString As String
    Dim insertionPoint(0 To 2) As Double
    Dim height As Double
    
    ' Define the text object
    textString = "Hello, World."
    insertionPoint(0) = 3: insertionPoint(1) = 3: insertionPoint(2) = 0
    height = 0.5
    
    ' Create the text object in model space
    Set textObj = ThisDrawing.ModelSpace.AddText(textString, insertionPoint, height)
    ZoomAll
    MsgBox "The TextAlignmentPoint is set to the default " & textObj.TextAlignmentPoint(0) & ", " & textObj.TextAlignmentPoint(1) & ", " & textObj.TextAlignmentPoint(2), vbInformation, "TextAlignmentPoint Example"
    
    ' Change the value of the HorizontalAlignment and
    ' TextAlignmentPoint properties.
    ' Note that the HorizontalAlignment property must be changed first,
    ' and to a value that requires the TextAlignmentPoint, before the
    ' TextAlignmentPoint property will allow a value to be set.
    Dim alignmentPoint(0 To 2) As Double
    alignmentPoint(0) = 5: alignmentPoint(1) = 3: alignmentPoint(2) = 0
    textObj.HorizontalAlignment = acHorizontalAlignmentFit
    textObj.TextAlignmentPoint = alignmentPoint
    ZoomAll
    MsgBox "The TextAlignmentPoint is set to " & textObj.TextAlignmentPoint(0) & ", " & textObj.TextAlignmentPoint(1) & ", " & textObj.TextAlignmentPoint(2) & vbCrLf & "The HorizontalAlignment is set to acHorizontalAlignmentFit", vbInformation, "TextAlignmentPoint Example"
    
End Sub
Sub Example_HorizontalAlignment()
    ' This example creates a text object in model space.
    ' It then changes the TextAlignmentPoint and HorizontalAlignment
    ' properties of the text object.
    Dim textObj As AcadText
    Dim textString As String
    Dim insertionPoint(0 To 2) As Double
    Dim height As Double
    
    ' Define the text object
    textString = "Hello, World."
    insertionPoint(0) = 3: insertionPoint(1) = 3: insertionPoint(2) = 0
    height = 0.5
    
    ' Create the text object in model space
    Set textObj = ThisDrawing.ModelSpace.AddText(textString, insertionPoint, height)
    ZoomAll
    MsgBox "The TextAlignmentPoint is set to the default " & textObj.TextAlignmentPoint(0) & ", " & textObj.TextAlignmentPoint(1) & ", " & textObj.TextAlignmentPoint(2), vbInformation, "HorizontalAlignment Example"
    
    ' Change the value of the HorizontalAlignment and
    ' TextAlignmentPoint properties.
    ' Note that the HorizontalAlignment property must be changed first,
    ' and to a value that requires the TextAlignmentPoint, before the
    ' TextAlignmentPoint property will allow a value to be set.
    Dim alignmentPoint(0 To 2) As Double
    alignmentPoint(0) = 5: alignmentPoint(1) = 3: alignmentPoint(2) = 0
    textObj.HorizontalAlignment = acHorizontalAlignmentFit
    textObj.TextAlignmentPoint = alignmentPoint
    ZoomAll
    MsgBox "The TextAlignmentPoint is set to " & textObj.TextAlignmentPoint(0) & ", " & textObj.TextAlignmentPoint(1) & ", " & textObj.TextAlignmentPoint(2) & vbCrLf & "The HorizontalAlignment is set to acHorizontalAlignmentFit", vbInformation, "HorizontalAlignment Example"
        
End Sub
Sub Example_VerticalAlignment()
    ' This example creates a text object in model space.
    ' It then changes the TextAlignmentPoint and VerticalAlignment
    ' properties of the text object.

    Dim textObj As AcadText
    Dim textString As String
    Dim insertionPoint(0 To 2) As Double
    Dim height As Double
    
    ' Define the text object
    textString = "Hello, World."
    insertionPoint(0) = 3: insertionPoint(1) = 3: insertionPoint(2) = 0
    height = 0.5
    
    ' Create the text object in model space
    Set textObj = ThisDrawing.ModelSpace.AddText(textString, insertionPoint, height)
    ZoomAll
    MsgBox "The TextAlignmentPoint is set to the default " & textObj.TextAlignmentPoint(0) & ", " & textObj.TextAlignmentPoint(1) & ", " & textObj.TextAlignmentPoint(2), vbInformation, "VerticalAlignment Example"
    
    ' Change the value of the VerticalAlignment and
    ' TextAlignmentPoint properties.
    ' Note that the VerticalAlignment property must be changed first,
    ' and to a value that requires the TextAlignmentPoint, before the
    ' TextAlignmentPoint property will allow a value to be set.
    Dim alignmentPoint(0 To 2) As Double
    alignmentPoint(0) = 5: alignmentPoint(1) = 5: alignmentPoint(2) = 0
    textObj.VerticalAlignment = acVerticalAlignmentTop
    textObj.TextAlignmentPoint = alignmentPoint
    ZoomAll
    MsgBox "The TextAlignmentPoint is set to " & textObj.TextAlignmentPoint(0) & ", " & textObj.TextAlignmentPoint(1) & ", " & textObj.TextAlignmentPoint(2) & vbCrLf & "The VerticalAlignment is set to acVerticalAlignmentTop", vbInformation, "VerticalAlignment Example"
      
End Sub
Sub Example_ObliqueAngle()
    ' This example creates a text object in model space.
    ' It then changes the ObliqueAngle of the text object.

    Dim textObj As AcadText
    Dim textString As String
    Dim insertionPoint(0 To 2) As Double
    Dim height As Double
    
    ' Define the text object
    textString = "Hello, World."
    insertionPoint(0) = 3: insertionPoint(1) = 3: insertionPoint(2) = 0
    height = 0.5
    
    ' Create the text object in model space
    Set textObj = ThisDrawing.ModelSpace.AddText(textString, insertionPoint, height)
    ZoomAll
    MsgBox "The ObliqueAngle is " & textObj.ObliqueAngle, vbInformation, "ObliqueAngle Example"
    
    ' Change the value of the ObliqueAngle to 45 degrees (.707 radians)
    textObj.ObliqueAngle = 0.707
    ZoomAll
    MsgBox "The ObliqueAngle is set to " & textObj.ObliqueAngle, vbInformation, "ObliqueAngle Example"
    
End Sub
Sub Example_Rotation()
    ' This example creates a text object in model space.
    ' It then changes the Rotation of the text object.

    Dim textObj As AcadText
    Dim textString As String
    Dim insertionPoint(0 To 2) As Double
    Dim height As Double
    
    ' Define the text object
    textString = "Hello, World."
    insertionPoint(0) = 3: insertionPoint(1) = 3: insertionPoint(2) = 0
    height = 0.5
    
    ' Create the text object in model space
    Set textObj = ThisDrawing.ModelSpace.AddText(textString, insertionPoint, height)
    ZoomAll
    MsgBox "The Rotation is " & textObj.rotation, vbInformation, "Rotation Example"
    
    ' Change the value of the Rotation to 45 degrees (.707 radians)
    textObj.rotation = 0.707
    ZoomAll
    MsgBox "The Rotation is set to " & textObj.rotation, vbInformation, "Rotation Example"
    
End Sub
Sub Example_Height()
    ' This example creates a text object in model space.
    ' It then changes the height of the text object.

    Dim textObj As AcadText
    Dim textString As String
    Dim insertionPoint(0 To 2) As Double
    Dim height As Double
    
    ' Define the text object
    textString = "Hello, World."
    insertionPoint(0) = 3: insertionPoint(1) = 3: insertionPoint(2) = 0
    height = 0.5
    
    ' Create the text object in model space
    Set textObj = ThisDrawing.ModelSpace.AddText(textString, insertionPoint, height)
    ZoomAll
    MsgBox "The text height is " & textObj.height, vbInformation, "Height Example"
    
    ' Change the value of the Height to 1
    textObj.height = 1
    textObj.Update
    MsgBox "The text height is set to " & textObj.height, vbInformation, "Height Example"
    
End Sub
Sub Example_AddCircle()
    ' This example creates a circle in model space.
   
    Dim circleObj As AcadCircle
    Dim centerPoint(0 To 2) As Double
    Dim radius As Double
    
    ' Define the circle
    centerPoint(0) = 0#: centerPoint(1) = 0#: centerPoint(2) = 0#
    radius = 5#
    
    ' Create the Circle object in model space
    Set circleObj = ThisDrawing.ModelSpace.AddCircle(centerPoint, radius)
    ZoomAll
    
End Sub
Sub Example_Thickness()
    ' This example creates a circle in model space
    ' and changes the thickness of the circle.
   
    Dim circleObj As AcadCircle
    Dim centerPoint(0 To 2) As Double
    Dim radius As Double
    
    ' Define the circle
    centerPoint(0) = 0#: centerPoint(1) = 0#: centerPoint(2) = 0#
    radius = 5#
    
    ' Create the Circle object in model space
    Set circleObj = ThisDrawing.ModelSpace.AddCircle(centerPoint, radius)
    ZoomAll
    
    ' Find the current thickness of the circle
    Dim currThickness As Double
    currThickness = circleObj.Thickness
    MsgBox "The thickness of the circle is " & circleObj.Thickness, vbInformation, "Thickness Example"
    
    ' Change the thickness of the circle
    circleObj.Thickness = currThickness + 3
    circleObj.Update
    
    ' Change the direction of the viewport so that you can
    ' view the change made to the thickness. Once you change
    ' the direction, you must reset the active viewport.
    Dim NewDirection(0 To 2) As Double
    NewDirection(0) = -1: NewDirection(1) = -1: NewDirection(2) = 1
    ThisDrawing.ActiveViewport.direction = NewDirection
    ThisDrawing.ActiveViewport = ThisDrawing.ActiveViewport
    MsgBox "The thickness of the circle is now " & circleObj.Thickness, vbInformation, "Thickness Example"
    
End Sub
Sub Example_Direction()
    ' This example creates a circle in model space
    ' and changes the thickness of the circle. Once
    ' the thickness has been changed, the direction
    ' of the active viewport is changed so that the
    ' new thickness setting is visible.
   
    Dim circleObj As AcadCircle
    Dim centerPoint(0 To 2) As Double
    Dim radius As Double
    
    ' Define the circle
    centerPoint(0) = 0#: centerPoint(1) = 0#: centerPoint(2) = 0#
    radius = 5#
    
    ' Create the Circle object in model space
    Set circleObj = ThisDrawing.ModelSpace.AddCircle(centerPoint, radius)
        
    ' Change the thickness of the circle
    circleObj.Thickness = 3
    
    ' Change the direction of the viewport so that you can
    ' view the change made to the thickness. Once you change
    ' the direction, you must reset the active viewport.
    Dim NewDirection(0 To 2) As Double
    NewDirection(0) = -1: NewDirection(1) = -1: NewDirection(2) = 1
    ThisDrawing.ActiveViewport.direction = NewDirection
    ThisDrawing.ActiveViewport = ThisDrawing.ActiveViewport
    
End Sub
Sub Example_FitTolerance()
    ' This example creates a spline object in model space.
    ' It then changes the FitTolerance property of that spline.

    ' Create the spline
    Dim splineObj As AcadSpline
    Dim noOfPoints As Integer
    Dim startTan(0 To 2) As Double
    Dim endTan(0 To 2) As Double
    Dim fitPoints(0 To 8) As Double
    
    noOfPoints = 3
    startTan(0) = 0.5: startTan(1) = 0.5: startTan(2) = 0
    endTan(0) = 0.5: endTan(1) = 0.5: endTan(2) = 0
    fitPoints(0) = 1: fitPoints(1) = 1: fitPoints(2) = 0
    fitPoints(3) = 5: fitPoints(4) = 5: fitPoints(5) = 0
    fitPoints(6) = 10: fitPoints(7) = 0: fitPoints(8) = 0
    Set splineObj = ThisDrawing.ModelSpace.AddSpline(fitPoints, startTan, endTan)
    ZoomAll
    
    ' Find the current FitTolerance value
    Dim currFitTolerance As Double
    currFitTolerance = splineObj.FitTolerance
    MsgBox "The current FitTolerance is " & currFitTolerance, vbInformation, "FitTolerance Example"

    ' Change the fit tolerance value
    splineObj.FitTolerance = 5
    ZoomAll
    MsgBox "The FitTolerance is now " & splineObj.FitTolerance, vbInformation, "FitTolerance Example"

End Sub
Sub Example_AddSpline()
    ' This example creates a spline object in model space.

    ' Create the spline
    Dim splineObj As AcadSpline
    Dim noOfPoints As Integer
    Dim startTan(0 To 2) As Double
    Dim endTan(0 To 2) As Double
    Dim fitPoints(0 To 8) As Double
    
    noOfPoints = 3
    startTan(0) = 0.5: startTan(1) = 0.5: startTan(2) = 0
    endTan(0) = 0.5: endTan(1) = 0.5: endTan(2) = 0
    fitPoints(0) = 1: fitPoints(1) = 1: fitPoints(2) = 0
    fitPoints(3) = 5: fitPoints(4) = 5: fitPoints(5) = 0
    fitPoints(6) = 10: fitPoints(7) = 0: fitPoints(8) = 0
    Set splineObj = ThisDrawing.ModelSpace.AddSpline(fitPoints, startTan, endTan)
    ZoomAll
    
End Sub
Sub Example_IsRational()
    ' This example creates a spline object in model space.
    ' It then determines if the spline is rational or non-rational
    ' based on the IsRational property.

    ' Create the spline
    Dim splineObj As AcadSpline
    Dim noOfPoints As Integer
    Dim startTan(0 To 2) As Double
    Dim endTan(0 To 2) As Double
    Dim fitPoints(0 To 8) As Double
    
    noOfPoints = 3
    startTan(0) = 0.5: startTan(1) = 0.5: startTan(2) = 0
    endTan(0) = 0.5: endTan(1) = 0.5: endTan(2) = 0
    fitPoints(0) = 1: fitPoints(1) = 1: fitPoints(2) = 0
    fitPoints(3) = 5: fitPoints(4) = 5: fitPoints(5) = 0
    fitPoints(6) = 10: fitPoints(7) = 0: fitPoints(8) = 0
    Set splineObj = ThisDrawing.ModelSpace.AddSpline(fitPoints, startTan, endTan)
    ZoomAll
    
    ' Display a message according to the IsRational value for the spline.
    If splineObj.IsRational Then
        MsgBox "The newly created Spline is a rational Spline", , "IsRational Example"
    Else
        MsgBox "The newly created Spline is a non-rational Spline", , "IsRational Example"
    End If

End Sub
Sub Example_NumberOfControlPoints()
    ' This example creates a spline object in model space.
    ' It then finds the number of control points for that spline.

    ' Create the spline
    Dim splineObj As AcadSpline
    Dim noOfPoints As Integer
    Dim startTan(0 To 2) As Double
    Dim endTan(0 To 2) As Double
    Dim fitPoints(0 To 8) As Double
    
    noOfPoints = 3
    startTan(0) = 0.5: startTan(1) = 0.5: startTan(2) = 0
    endTan(0) = 0.5: endTan(1) = 0.5: endTan(2) = 0
    fitPoints(0) = 1: fitPoints(1) = 1: fitPoints(2) = 0
    fitPoints(3) = 5: fitPoints(4) = 5: fitPoints(5) = 0
    fitPoints(6) = 10: fitPoints(7) = 0: fitPoints(8) = 0
    Set splineObj = ThisDrawing.ModelSpace.AddSpline(fitPoints, startTan, endTan)
    ZoomAll
    
    MsgBox "The Spline has " & splineObj.NumberOfControlPoints & " control points.", , "NumberOfControlPoints Example"

End Sub
Sub Example_NumberOfFitPoints()
    ' This example creates a spline object in model space.
    ' It then finds the number of control points for that spline.

    ' Create the spline
    Dim splineObj As AcadSpline
    Dim noOfPoints As Integer
    Dim startTan(0 To 2) As Double
    Dim endTan(0 To 2) As Double
    Dim fitPoints(0 To 8) As Double
    
    noOfPoints = 3
    startTan(0) = 0.5: startTan(1) = 0.5: startTan(2) = 0
    endTan(0) = 0.5: endTan(1) = 0.5: endTan(2) = 0
    fitPoints(0) = 1: fitPoints(1) = 1: fitPoints(2) = 0
    fitPoints(3) = 5: fitPoints(4) = 5: fitPoints(5) = 0
    fitPoints(6) = 10: fitPoints(7) = 0: fitPoints(8) = 0
    Set splineObj = ThisDrawing.ModelSpace.AddSpline(fitPoints, startTan, endTan)
    ZoomAll
    
    MsgBox "The Spline has " & splineObj.NumberOfFitPoints & " fit points.", , "NumberOfFitPoints Example"

End Sub
Sub Example_AddFitPoint()
    ' This example creates a spline object in model space.
    ' It then adds a fit point to the spline.

    ' Create the spline
    Dim splineObj As AcadSpline
    Dim noOfPoints As Integer
    Dim startTan(0 To 2) As Double
    Dim endTan(0 To 2) As Double
    Dim fitPoints(0 To 8) As Double
    
    noOfPoints = 3
    startTan(0) = 0.5: startTan(1) = 0.5: startTan(2) = 0
    endTan(0) = 0.5: endTan(1) = 0.5: endTan(2) = 0
    fitPoints(0) = 1: fitPoints(1) = 1: fitPoints(2) = 0
    fitPoints(3) = 5: fitPoints(4) = 5: fitPoints(5) = 0
    fitPoints(6) = 10: fitPoints(7) = 0: fitPoints(8) = 0
    
    ' Create the spline object
    Set splineObj = ThisDrawing.ModelSpace.AddSpline(fitPoints, startTan, endTan)
    ZoomAll
    MsgBox "The Spline has " & splineObj.NumberOfFitPoints & " fit points.", , "AddFitPoint Example"
    
    ' Define the new fit point
    Dim newFitPoint(0 To 2) As Double
    newFitPoint(0) = 8: newFitPoint(1) = 5: newFitPoint(2) = 0
    
    ' Add the new fit point at the first index in the spline's array of points
    splineObj.AddFitPoint 1, newFitPoint
    ThisDrawing.Regen True
    MsgBox "A fit point has been added at Index:1  WCS: 8, 5, 0" & vbCrLf & "The Spline has " & splineObj.NumberOfFitPoints & " fit points.", , "AddFitPoint Example"

End Sub
Sub Example_GetFitPoint()
    ' This example creates a spline object in model space.
    ' It then finds the coordinates of the fit points.

    ' Create the spline
    Dim splineObj As AcadSpline
    Dim noOfPoints As Integer
    Dim startTan(0 To 2) As Double
    Dim endTan(0 To 2) As Double
    Dim fitPoints(0 To 8) As Double
    
    noOfPoints = 3
    startTan(0) = 0.5: startTan(1) = 0.5: startTan(2) = 0
    endTan(0) = 0.5: endTan(1) = 0.5: endTan(2) = 0
    fitPoints(0) = 1: fitPoints(1) = 1: fitPoints(2) = 0
    fitPoints(3) = 5: fitPoints(4) = 5: fitPoints(5) = 0
    fitPoints(6) = 10: fitPoints(7) = 0: fitPoints(8) = 0
    Set splineObj = ThisDrawing.ModelSpace.AddSpline(fitPoints, startTan, endTan)
    ZoomAll
    
    ' Display the coordinates of the fit points
    Dim fitPoint As Variant
    Dim index As Integer
    For index = 0 To splineObj.NumberOfFitPoints - 1
        fitPoint = splineObj.GetFitPoint(index)
        MsgBox "Fit point " & index + 1 & " is at " & fitPoint(0) & ", " & fitPoint(1) & ", " & fitPoint(2), , "GetFitPoint Example"
    Next
    
End Sub
Sub Example_SetFitPoint()
    ' This example creates a spline object in model space.
    ' It then finds the coordinates of the first fit point
    ' and changes that value.

    ' Create the spline
    Dim splineObj As AcadSpline
    Dim noOfPoints As Integer
    Dim startTan(0 To 2) As Double
    Dim endTan(0 To 2) As Double
    Dim fitPoints(0 To 8) As Double
    
    noOfPoints = 3
    startTan(0) = 0.5: startTan(1) = 0.5: startTan(2) = 0
    endTan(0) = 0.5: endTan(1) = 0.5: endTan(2) = 0
    fitPoints(0) = 1: fitPoints(1) = 1: fitPoints(2) = 0
    fitPoints(3) = 5: fitPoints(4) = 5: fitPoints(5) = 0
    fitPoints(6) = 10: fitPoints(7) = 0: fitPoints(8) = 0
    Set splineObj = ThisDrawing.ModelSpace.AddSpline(fitPoints, startTan, endTan)
    ZoomAll
    
    ' Display the coordinates of the first fit point
    Dim fitPoint As Variant
    fitPoint = splineObj.GetFitPoint(0)
    MsgBox "Fit point 1 is at " & fitPoint(0) & ", " & fitPoint(1) & ", " & fitPoint(2), , "SetFitPoint Example"
    
    ' Change the coordinate of the first fit point
    fitPoint(0) = 0: fitPoint(1) = 3: fitPoint(2) = 0
    splineObj.SetFitPoint 0, fitPoint
    splineObj.Update
    MsgBox "Fit point 1 is now at " & fitPoint(0) & ", " & fitPoint(1) & ", " & fitPoint(2), , "SetFitPoint Example"
    
End Sub
Sub Example_SetWeight()
    ' This example creates a spline object in model space.
    ' It then finds the weight of the first control point
    ' and changes that value.

    ' Create the spline
    Dim splineObj As AcadSpline
    Dim noOfPoints As Integer
    Dim startTan(0 To 2) As Double
    Dim endTan(0 To 2) As Double
    Dim fitPoints(0 To 8) As Double
    
    noOfPoints = 3
    startTan(0) = 0.5: startTan(1) = 0.5: startTan(2) = 0
    endTan(0) = 0.5: endTan(1) = 0.5: endTan(2) = 0
    fitPoints(0) = 1: fitPoints(1) = 1: fitPoints(2) = 0
    fitPoints(3) = 5: fitPoints(4) = 5: fitPoints(5) = 0
    fitPoints(6) = 10: fitPoints(7) = 0: fitPoints(8) = 0
    Set splineObj = ThisDrawing.ModelSpace.AddSpline(fitPoints, startTan, endTan)
    ZoomAll
    
    ' Display the coordinates of the first fit point
    Dim weight As Double
    weight = splineObj.GetWeight(0)
    MsgBox "The weight of control point 1 is " & weight, , "SetWeight Example"
    
    ' Change the weight of the first control point
    weight = 5
    splineObj.SetWeight 0, weight
    splineObj.Update
    MsgBox "The weight of control point 1 is now " & weight, , "SetWeight Example"
    
End Sub
Sub Example_GetWeight()
    ' This example creates a spline object in model space.
    ' It then finds the weight of the first control point
    ' and changes that value.

    ' Create the spline
    Dim splineObj As AcadSpline
    Dim noOfPoints As Integer
    Dim startTan(0 To 2) As Double
    Dim endTan(0 To 2) As Double
    Dim fitPoints(0 To 8) As Double
    
    noOfPoints = 3
    startTan(0) = 0.5: startTan(1) = 0.5: startTan(2) = 0
    endTan(0) = 0.5: endTan(1) = 0.5: endTan(2) = 0
    fitPoints(0) = 1: fitPoints(1) = 1: fitPoints(2) = 0
    fitPoints(3) = 5: fitPoints(4) = 5: fitPoints(5) = 0
    fitPoints(6) = 10: fitPoints(7) = 0: fitPoints(8) = 0
    Set splineObj = ThisDrawing.ModelSpace.AddSpline(fitPoints, startTan, endTan)
    ZoomAll
    
    ' Display the coordinates of the first fit point
    Dim weight As Double
    weight = splineObj.GetWeight(0)
    MsgBox "The weight of control point 1 is " & weight, , "GetWeight Example"
    
    ' Change the weight of the first control point
    weight = 5
    splineObj.SetWeight 0, weight
    splineObj.Update
    MsgBox "The weight of control point 1 is now " & weight, , "GetWeight Example"
    
End Sub
Sub Example_SetControlPoint()
    ' This example creates a spline object in model space.
    ' It then finds the coordinates of the first control point
    ' and changes that value.

    ' Create the spline
    Dim splineObj As AcadSpline
    Dim noOfPoints As Integer
    Dim startTan(0 To 2) As Double
    Dim endTan(0 To 2) As Double
    Dim fitPoints(0 To 8) As Double
    
    noOfPoints = 3
    startTan(0) = 0.5: startTan(1) = 0.5: startTan(2) = 0
    endTan(0) = 0.5: endTan(1) = 0.5: endTan(2) = 0
    fitPoints(0) = 1: fitPoints(1) = 1: fitPoints(2) = 0
    fitPoints(3) = 5: fitPoints(4) = 5: fitPoints(5) = 0
    fitPoints(6) = 10: fitPoints(7) = 0: fitPoints(8) = 0
    Set splineObj = ThisDrawing.ModelSpace.AddSpline(fitPoints, startTan, endTan)
    ZoomAll
    
    ' Display the coordinates of the first control point
    Dim controlPoint As Variant
    controlPoint = splineObj.GetControlPoint(0)
    MsgBox "Control point 1 is at " & controlPoint(0) & ", " & controlPoint(1) & ", " & controlPoint(2), , "SetControlPoint Example"
    
    ' Change the coordinate of the first fit point
    controlPoint(0) = 0: controlPoint(1) = 3: controlPoint(2) = 0
    splineObj.SetControlPoint 0, controlPoint
    splineObj.Update
    MsgBox "Control point 1 is now at " & controlPoint(0) & ", " & controlPoint(1) & ", " & controlPoint(2), , "SetControlPoint Example"
    
End Sub
Sub Example_GetControlPoint()
    ' This example creates a spline object in model space.
    ' It then finds the coordinates of the first control point
    ' and changes that value.

    ' Create the spline
    Dim splineObj As AcadSpline
    Dim noOfPoints As Integer
    Dim startTan(0 To 2) As Double
    Dim endTan(0 To 2) As Double
    Dim fitPoints(0 To 8) As Double
    
    noOfPoints = 3
    startTan(0) = 0.5: startTan(1) = 0.5: startTan(2) = 0
    endTan(0) = 0.5: endTan(1) = 0.5: endTan(2) = 0
    fitPoints(0) = 1: fitPoints(1) = 1: fitPoints(2) = 0
    fitPoints(3) = 5: fitPoints(4) = 5: fitPoints(5) = 0
    fitPoints(6) = 10: fitPoints(7) = 0: fitPoints(8) = 0
    Set splineObj = ThisDrawing.ModelSpace.AddSpline(fitPoints, startTan, endTan)
    ZoomAll
    
    ' Display the coordinates of the first control point
    Dim controlPoint As Variant
    controlPoint = splineObj.GetControlPoint(0)
    MsgBox "Control point 1 is at " & controlPoint(0) & ", " & controlPoint(1) & ", " & controlPoint(2), , "GetControlPoint Example"
    
    ' Change the coordinate of the first fit point
    controlPoint(0) = 0: controlPoint(1) = 3: controlPoint(2) = 0
    splineObj.SetControlPoint 0, controlPoint
    splineObj.Update
    MsgBox "Control point 1 is now at " & controlPoint(0) & ", " & controlPoint(1) & ", " & controlPoint(2), , "GetControlPoint Example"
    
End Sub
Sub Example_Freeze()
    ' This example creates a new layer called "Freeze".
    ' It then displays the status of the Freeze property
    ' for the new layer, toggles the status of the
    ' Freeze property, and again displays it's status.
    ' After running this example, you can check the layer
    ' control on the Object Properties tool bar. It will
    ' show the new layer and the latest Freeze status.
    
    Dim layerObj As AcadLayer
    
    ' Create the new layer
    Set layerObj = ThisDrawing.Layers.Add("Freeze")
    
    ' Display the Freeze status of the new layer
    GoSub DISPLAYSTATUS
    
    ' Toggle the status of the Freeze property for the layer
    layerObj.Freeze = Not (layerObj.Freeze)
    
    ' Display the Freeze status of the new layer
    GoSub DISPLAYSTATUS
    Exit Sub
    
DISPLAYSTATUS:
    If layerObj.Freeze Then
        MsgBox "Layer " & layerObj.name & " is frozen.", , "Freeze Example"
    Else
        MsgBox "Layer " & layerObj.name & " is thawed.", , "Freeze Example"
    End If
    Return
        
End Sub
Sub Example_LayerOn()
    ' This example creates a new layer called "LayerOn".
    ' It then displays the status of the LayerOn property
    ' for the new layer, toggles the status of the
    ' LayerOn property, and again displays it's status.
    ' After running this example, you can check the layer
    ' control on the Object Properties tool bar. It will
    ' show the new layer and the latest LayerOn status.
    
    Dim layerObj As AcadLayer
    
    ' Create the new layer
    Set layerObj = ThisDrawing.Layers.Add("LayerOn")
    
    ' Display the LayerOn status of the new layer
    GoSub DISPLAYSTATUS
    
    ' Toggle the status of the LayerOn property for the layer
    layerObj.LayerOn = Not (layerObj.LayerOn)
    
    ' Display the LayerOn status of the new layer
    GoSub DISPLAYSTATUS
    Exit Sub
    
DISPLAYSTATUS:
    If layerObj.LayerOn Then
        MsgBox "Layer " & layerObj.name & " is turned on.", , "LayerOn Example"
    Else
        MsgBox "Layer " & layerObj.name & " is turned off.", , "LayerOn Example"
    End If
    Return
        
End Sub
Sub Example_Lock()
    ' This example creates a new layer called "Lock".
    ' It then displays the status of the Lock property
    ' for the new layer, toggles the status of the
    ' Lock property, and again displays it's status.
    ' After running this example, you can check the layer
    ' control on the Object Properties tool bar. It will
    ' show the new layer and the latest Lock status.
    
    Dim layerObj As AcadLayer
    
    ' Create the new layer
    Set layerObj = ThisDrawing.Layers.Add("Lock")
    
    ' Display the Lock status of the new layer
    GoSub DISPLAYSTATUS
    
    ' Toggle the status of the Lock property for the layer
    layerObj.Lock = Not (layerObj.Lock)
    
    ' Display the Lock status of the new layer
    GoSub DISPLAYSTATUS
    Exit Sub
    
DISPLAYSTATUS:
    If layerObj.Lock Then
        MsgBox "Layer " & layerObj.name & " is locked.", , "Lock Example"
    Else
        MsgBox "Layer " & layerObj.name & " is unlocked.", , "Lock Example"
    End If
    Return
        
End Sub
Sub Example_Add()
    ' This example adds a block, dictionary, dimension style,
    ' group, layer, registered application, selection set,
    ' textstyle, view, viewport and UCS using the Add method.
    
    GoSub ADDBLOCK
    GoSub ADDDICTIONARY
    GoSub ADDDIMSTYLE
    GoSub ADDGROUP
    GoSub ADDLAYER
    GoSub ADDREGISTEREDAPP
    GoSub ADDSELECTIONSET
    GoSub ADDTEXTSTYLE
    GoSub ADDVIEW
    GoSub ADDVIEWPORT
    GoSub ADDUCS
    Exit Sub
    
ADDBLOCK:
    ' Create a new block called "New_Block"
    Dim blockObj As AcadBlock
    
    ' Define the block
    Dim insertionPnt(0 To 2) As Double
    insertionPnt(0) = 0#: insertionPnt(1) = 0#: insertionPnt(2) = 0#
    
    ' Add the block to the blocks collection
    Set blockObj = ThisDrawing.Blocks.Add(insertionPnt, "New_Block")
    MsgBox blockObj.name & " has been added." & vbCrLf & _
            "Origin: " & blockObj.origin(0) & ", " & blockObj.origin(1) _
            & ", " & blockObj.origin(2), , "Add Example"
    Return
    
ADDDICTIONARY:
    ' Create a new dictionary called "New_Dictionary"
    Dim dictObj As AcadDictionary
    
    ' Add the dictionary to the dictionaries collection
    Set dictObj = ThisDrawing.Dictionaries.Add("New_Dictionary")
    MsgBox dictObj.name & " has been added.", , "Add Example"
    Return

ADDDIMSTYLE:
    ' Create a new dimension style called "New_Dimstyle" in current drawing
    Dim DimStyleObj As AcadDimStyle
    
    ' Add the dimstyle to the dimstyles collection
    Set DimStyleObj = ThisDrawing.DimStyles.Add("New_Dimstyle")
    MsgBox DimStyleObj.name & " has been added.", , "Add Example"
    Return
    
ADDGROUP:
    ' Create a new group called "New_Group" in current drawing
    Dim groupObj As AcadGroup
    
    ' Add the group to the groups collection
    Set groupObj = ThisDrawing.Groups.Add("New_Group")
    MsgBox groupObj.name & " has been added.", , "Add Example"
    Return
    
ADDLAYER:
    ' This example creates a new layer called "New_Layer"
    Dim layerObj As AcadLayer
    
    ' Add the layer to the layers collection
    Set layerObj = ThisDrawing.Layers.Add("New_Layer")
    
    ' Make the new layer the active layer for the drawing
    ThisDrawing.ActiveLayer = layerObj
    
    ' Display the status of the new layer
     MsgBox layerObj.name & " has been added." & vbCrLf & _
            "LayerOn Status: " & layerObj.LayerOn & vbCrLf & _
            "Freeze Status: " & layerObj.Freeze & vbCrLf & _
            "Lock Status: " & layerObj.Lock & vbCrLf & _
            "Color: " & layerObj.Color, , "Add Example"
    Return
    
ADDREGISTEREDAPP:
    ' Create a registered application named "New_RegApp" in current drawing
    Dim RegAppObj As AcadRegisteredApplication
    
    ' Add the registered application to the registered applications collection
    Set RegAppObj = ThisDrawing.RegisteredApplications.Add("New_RegApp")
    MsgBox RegAppObj.name & " has been added.", , "Add Example"
    Return

ADDSELECTIONSET:
    ' Create a selectionset named "New_SelectionSet" in current drawing
    Dim ssetObj As AcadSelectionSet
    
    ' Add the selection set to the selection sets collection
    Set ssetObj = ThisDrawing.SelectionSets.Add("New_SelectionSet")
    MsgBox ssetObj.name & " has been added." & vbCrLf & _
           "The number of items in the selection set is " & ssetObj.count _
           , , "Add Example"
    Return
    
ADDTEXTSTYLE:
    ' Create a textstyle named "New_Textstyle" in current drawing
    Dim txtStyleObj As AcadTextStyle
    
    ' Add the textstyle to the textstyles collection
    Set txtStyleObj = ThisDrawing.TextStyles.Add("New_Textstyle")
    MsgBox txtStyleObj.name & " has been added." & vbCrLf & _
           "Height: " & txtStyleObj.height & vbCrLf & _
           "Width: " & txtStyleObj.width, , "Add Example"
    Return
    
ADDVIEW:
    ' Create a view named "New_View" in current drawing
    Dim viewObj As AcadView
    
    ' Add the view to the views collection
    Set viewObj = ThisDrawing.Views.Add("New_View")
    MsgBox viewObj.name & " has been added." & vbCrLf & _
           "Height: " & viewObj.height & vbCrLf & _
           "Width: " & viewObj.width, , "Add Example"
    Return
    
ADDVIEWPORT:
    ' Create a viewport named "New_Viewport" in current drawing
    Dim vportObj As AcadViewport
    
    ' Add the viewport to the viewports collection
    Set vportObj = ThisDrawing.Viewports.Add("New_Viewport")
    MsgBox vportObj.name & " has been added." & vbCrLf & _
           "GridOn Status: " & vportObj.GridOn & vbCrLf & _
           "OrthoOn Status: " & vportObj.OrthoOn & vbCrLf & _
           "SnapOn Status: " & vportObj.SnapOn, , "Add Example"
    Return
    
ADDUCS:
    ' Create a UCS named "New_UCS" in current drawing
    Dim ucsObj As AcadUCS
    Dim origin(0 To 2) As Double
    Dim xAxisPnt(0 To 2) As Double
    Dim yAxisPnt(0 To 2) As Double
    
    ' Define the UCS
    origin(0) = 4#: origin(1) = 5#: origin(2) = 3#
    xAxisPnt(0) = 5#: xAxisPnt(1) = 5#: xAxisPnt(2) = 3#
    yAxisPnt(0) = 4#: yAxisPnt(1) = 6#: yAxisPnt(2) = 3#
    
    ' Add the UCS to the UserCoordinatesSystems collection
    Set ucsObj = ThisDrawing.UserCoordinateSystems.Add(origin, xAxisPnt, yAxisPnt, "New_UCS")
    MsgBox ucsObj.name & " has been added." & vbCrLf & _
            "Origin: " & ucsObj.origin(0) & ", " & ucsObj.origin(1) _
            & ", " & ucsObj.origin(2), , "Add Example"
    Return
    
End Sub
Sub Example_FullName()
    ' This example uses the FullName property to find
    ' the full name of the current drawing, and of
    ' the application.
    
    ' Find the full name of current drawing file including path.
    ' (If the drawing has not been saved, this name will be blank.)
    Dim docName As String
    docName = ThisDrawing.FullName
    MsgBox "The full name of the current drawing is " & docName, , "FullName Example"
    
    ' Find the full name of application
    Dim appName As String
    appName = ThisDrawing.Application.FullName
    MsgBox "The full name of the current application is " & appName, , "FullName Example"
    
End Sub
Sub Example_GridOn()
    ' This example toggles the setting of GridOn.
    
    Dim viewportObj As AcadViewport
    
    ' Set the viewportObj variable to the activeviewport
    Set viewportObj = ThisDrawing.ActiveViewport

TOGGLEGRID:
    If MsgBox("Toggle the grid?", vbOKCancel, "GridOn Example") = vbOK Then
        viewportObj.GridOn = Not (viewportObj.GridOn)
    Else
        Exit Sub
    End If
    
    ' Reset the active viewport to see the change
    ThisDrawing.ActiveViewport = viewportObj
    
    GoTo TOGGLEGRID
    
End Sub
Sub Example_OrthoOn()
    ' This example toggles the setting of OrthoOn.

    Dim viewportObj As AcadViewport
    
    ' Set the viewportObj variable to the activeviewport
    Set viewportObj = ThisDrawing.ActiveViewport
    
    ' Display the current setting of OrthoOn
    MsgBox "Ortho mode is: " & IIf(viewportObj.OrthoOn, "On", "Off"), , "OrthoOn Example"

    ' Toggle the setting of OrthoOn
    viewportObj.OrthoOn = Not (viewportObj.OrthoOn)
    
    ' Reset the active viewport to see the change on the AutoCAD status bar
    ThisDrawing.ActiveViewport = viewportObj
    
    MsgBox "Ortho mode is now: " & IIf(viewportObj.OrthoOn, "On", "Off"), , "OrthoOn Example"
    
End Sub
Sub Example_SnapOn()
    ' This example toggles the setting of SnapOn.

    Dim viewportObj As AcadViewport
    
    ' Set the viewportObj variable to the activeviewport
    Set viewportObj = ThisDrawing.ActiveViewport
    
    ' Display the current setting of SnapOn
    MsgBox "Snap mode is: " & IIf(viewportObj.SnapOn, "On", "Off"), , "SnapOn Example"

    ' Toggle the setting of SnapOn
    viewportObj.SnapOn = Not (viewportObj.SnapOn)
    
    ' Reset the active viewport to see the change on the AutoCAD status bar
    ThisDrawing.ActiveViewport = viewportObj
    
    MsgBox "Snap mode is now: " & IIf(viewportObj.SnapOn, "On", "Off"), , "SnapOn Example"
    
End Sub
Sub Example_UCSIconOn()
    ' This example toggles the setting of UCSIconOn.

    Dim viewportObj As AcadViewport
    
    ' Set the viewportObj variable to the activeviewport
    Set viewportObj = ThisDrawing.ActiveViewport
    
    ' Display the current setting of UCSIconOn
    MsgBox "UCSIcon is: " & IIf(viewportObj.UCSIconOn, "On", "Off"), , "UCSIconOn Example"

    ' Toggle the setting of UCSIconOn
    viewportObj.UCSIconOn = Not (viewportObj.UCSIconOn)
    
    ' Reset the active viewport to see the change
    ThisDrawing.ActiveViewport = viewportObj
    
    MsgBox "UCSIcon is now: " & IIf(viewportObj.UCSIconOn, "On", "Off"), , "UCSIconOn Example"
    
End Sub
Sub Example_UCSIconAtOrigin()
    ' This example toggles the setting of UCSIconAtOrigin.

    Dim viewportObj As AcadViewport
    
    ' Set the viewportObj variable to the activeviewport
    Set viewportObj = ThisDrawing.ActiveViewport
    
    ' Make sure the UCS Icon is on, and a new UCS is defined.
    ' The new UCS defines the origin for the icon. When the icon
    ' is not displayed at the origin, it is displayed at the
    ' lower-left corner of the display.
    Dim ucsObj As AcadUCS
    Dim origin(0 To 2) As Double
    Dim xAxisPoint(0 To 2) As Double
    Dim yAxisPoint(0 To 2) As Double
    origin(0) = 2: origin(1) = 2: origin(2) = 0
    xAxisPoint(0) = 3: xAxisPoint(1) = 2: xAxisPoint(2) = 0
    yAxisPoint(0) = 2: yAxisPoint(1) = 3: yAxisPoint(2) = 0
    Set ucsObj = ThisDrawing.UserCoordinateSystems.Add(origin, xAxisPoint, yAxisPoint, "UCS1")
    ThisDrawing.ActiveUCS = ucsObj
    viewportObj.UCSIconOn = True
    
    ' Display the current setting of UCSIconAtOrigin
    MsgBox "UCSIconAtOrigin is: " & IIf(viewportObj.UCSIconAtOrigin, "On", "Off"), , "UCSIconAtOrigin Example"

    ' Toggle the setting of UCSIconAtOrigin
    viewportObj.UCSIconAtOrigin = Not (viewportObj.UCSIconAtOrigin)
    
    ' Reset the active viewport to see the change
    ThisDrawing.ActiveViewport = viewportObj
    
    MsgBox "UCSIconAtOrigin is now: " & IIf(viewportObj.UCSIconAtOrigin, "On", "Off"), , "UCSIconAtOrigin Example"
    
End Sub
Sub Example_StatusID()
    ' This example displays the setting of StatusID.

    Dim currStatusID As Boolean
    
    ' Display the current setting of statusID
    currStatusID = ThisDrawing.Application.StatusId(ThisDrawing.ActiveViewport)
    MsgBox "The statusID of the active viewort is: " & currStatusID, , "StatusID Example"
    
End Sub
Sub Example_TagString()
    ' This example creates an attribute definition in model space.
    ' It then queries the tag string for the attribute, changes
    ' the tag string, and displays the new tag string.
    
    Dim attributeObj As AcadAttribute
    Dim height As Double
    Dim mode As Long
    Dim prompt As String
    Dim insertionPoint(0 To 2) As Double
    Dim tag As String
    Dim value As String
    
    ' Define the attribute definition
    height = 1#
    mode = acAttributeModeVerify
    prompt = "New Prompt"
    insertionPoint(0) = 5#: insertionPoint(1) = 5#: insertionPoint(2) = 0
    tag = "New Tag"
    value = "New Value"
    
    ' Create the attribute definition object in model space
    Set attributeObj = ThisDrawing.ModelSpace.AddAttribute(height, mode, prompt, insertionPoint, tag, value)
    ZoomAll
    
    ' Find the current tag string for the attribute
    tag = attributeObj.TagString
    MsgBox "The current tag string for the attribute is " & tag, , "TagString Example"
    
    ' Change the tag string for the attribute
    attributeObj.TagString = "Updated Tag"
    attributeObj.Update
    tag = attributeObj.TagString
    MsgBox "The new tag string for the attribute is " & tag, , "TagString Example"
    
End Sub
Sub Example_TextStyles()
    ' This example finds the current Textstyles collection and
    ' adds a new Text style to that collection.
    
    Dim TextColl As AcadTextStyles
    Set TextColl = ThisDrawing.TextStyles
    
    ' Create a Text style named "TEST" in the current drawing
    Dim textStyle As AcadTextStyle
    Set textStyle = TextColl.Add("TEST")
    MsgBox "A new Text style called " & textStyle.name & " has been added to the Textstyles collection.", vbInformation, "Textstyles Example"
End Sub
Sub Example_Version()
    ' This example returns AutoCAD version as a string
    
    Dim version As String
    version = ThisDrawing.Application.version
    MsgBox "This is AutoCAD Version " & version, , "Version Example"
    
End Sub
Sub Example_Viewports()
    ' This example finds the current Viewports collection and
    ' adds a new viewport to that collection.
    
    Dim viewportColl As AcadViewports
    Set viewportColl = ThisDrawing.Viewports
    
    ' Create a viewport named "TEST" in the current drawing
    Dim viewportObj As AcadViewport
    Set viewportObj = viewportColl.Add("TEST")
    MsgBox "A new viewport called " & viewportObj.name & " has been added to the Viewports collection.", vbInformation, "Viewports Example"
End Sub
Sub Example_Views()
    ' This example finds the current views collection and
    ' adds a new view to that collection.
    
    Dim viewColl As AcadViews
    Set viewColl = ThisDrawing.Views
    
    ' Create a view named "TEST" in the current drawing
    Dim viewObj As AcadView
    Set viewObj = viewColl.Add("TEST")
    MsgBox "A new view called " & viewObj.name & " has been added to the views collection.", vbInformation, "Views Example"
End Sub
Sub Example_UserCoordinateSystems()
    ' This example finds the current UserCoordinateSystems collection and
    ' adds a new UCS to that collection.
    
    Dim UCSColl As AcadUCSs
    Set UCSColl = ThisDrawing.UserCoordinateSystems
    
    ' Create a UCS named "TEST" in the current drawing
    Dim ucsObj As AcadUCS
    Dim origin(0 To 2) As Double
    Dim xAxisPnt(0 To 2) As Double
    Dim yAxisPnt(0 To 2) As Double
    
    ' Define the UCS
    origin(0) = 4#: origin(1) = 5#: origin(2) = 3#
    xAxisPnt(0) = 5#: xAxisPnt(1) = 5#: xAxisPnt(2) = 3#
    yAxisPnt(0) = 4#: yAxisPnt(1) = 6#: yAxisPnt(2) = 3#
    
    ' Add the UCS to the UserCoordinatesSystems collection
    Set ucsObj = UCSColl.Add(origin, xAxisPnt, yAxisPnt, "TEST")
    
    MsgBox "A new UCS called " & ucsObj.name & " has been added to the UserCoordinateSystems collection.", vbInformation, "UserCoordinateSystems Example"
End Sub
Sub Example_RegisteredApplications()
    ' This example finds the current RegisteredApps collection and
    ' adds a new RegisteredApp to that collection.
    
    Dim RegAppColl As AcadRegisteredApplications
    Set RegAppColl = ThisDrawing.RegisteredApplications
    
    ' Create a RegisteredApp named "TEST" in the current drawing
    Dim RegAppObj As AcadRegisteredApplication
    Set RegAppObj = RegAppColl.Add("TEST")
    MsgBox "A new registered application called " & RegAppObj.name & " has been added to the Registered Applications collection.", vbInformation, "RegisteredApplications Example"
End Sub
Sub Example_Regen()
    ' The following examples regenerates complete drawing
    ThisDrawing.Regen acAllViewports
    
    ' The following examples regenerates active viewport in current drawing
    ThisDrawing.Regen acActiveViewport
    
End Sub

Sub Example_SelectionSets()
    ' This example finds the current SelectionSets collection and
    ' adds a new SelectionSet to that collection.
    
    Dim SSetColl As AcadSelectionSets
    Set SSetColl = ThisDrawing.SelectionSets
    
    ' Create a SelectionSet named "TEST" in the current drawing
    Dim ssetObj As AcadSelectionSet
    Set ssetObj = SSetColl.Add("TEST")
    MsgBox "A new SelectionSet called " & ssetObj.name & " has been added to the SelectionSets collection.", vbInformation, "SelectionSets Example"
End Sub
Sub Example_Add3DFace()
    ' This example creates a 3D face in model space.

    Dim faceObj As Acad3DFace
    Dim point1(0 To 2) As Double
    Dim point2(0 To 2) As Double
    Dim point3(0 To 2) As Double
    Dim point4(0 To 2) As Double
    
    ' Define the four coordinates of the face
    point1(0) = 0#: point1(1) = 0#: point1(2) = 0#
    point2(0) = 5#: point2(1) = 0#: point2(2) = 1#
    point3(0) = 1#: point3(1) = 10#: point3(2) = 0#
    point4(0) = 5#: point4(1) = 5#: point4(2) = 1#
    
    ' Create the 3DFace object in model space
    Set faceObj = ThisDrawing.ModelSpace.Add3DFace(point1, point2, point3, point4)
    ZoomAll
    
End Sub
Sub Example_AddArc()
    ' This example creates an arc in model space.
   
    Dim arcObj As AcadArc
    Dim centerPoint(0 To 2) As Double
    Dim radius As Double
    Dim startAngleInDegree As Double
    Dim endAngleInDegree As Double
    
    ' Define the circle
    centerPoint(0) = 0#: centerPoint(1) = 0#: centerPoint(2) = 0#
    radius = 5#
    startAngleInDegree = 10#
    endAngleInDegree = 230#
    
    ' Convert the angles in degrees to angles in radians
    Dim startAngleInRadian As Double
    Dim endAngleInRadian As Double
    startAngleInRadian = startAngleInDegree * 3.141592 / 180#
    endAngleInRadian = endAngleInDegree * 3.141592 / 180#
    
    ' Create the arc object in model space
    Set arcObj = ThisDrawing.ModelSpace.AddArc(centerPoint, radius, startAngleInRadian, endAngleInRadian)
    ZoomAll
End Sub
Sub Example_AddBox()
    ' This example creates a box in model space.
        
    Dim boxObj As Acad3DSolid
    Dim length As Double, width As Double, height As Double
    Dim center(0 To 2) As Double
    
    ' Define the box
    center(0) = 5#: center(1) = 5#: center(2) = 0
    length = 5#: width = 7: height = 10#
    
    ' Create the box (3DSolid) object in model space
    Set boxObj = ThisDrawing.ModelSpace.AddBox(center, length, width, height)
    
    ' Change the viewing direction of the viewport to better see the box
    Dim NewDirection(0 To 2) As Double
    NewDirection(0) = -1: NewDirection(1) = -1: NewDirection(2) = 1
    ThisDrawing.ActiveViewport.direction = NewDirection
    ThisDrawing.ActiveViewport = ThisDrawing.ActiveViewport
    ZoomAll
    
End Sub
Sub Example_AddCone()
    ' This example creates a cone in model space.
   
    Dim coneObj As Acad3DSolid
    Dim radius As Double
    Dim center(0 To 2) As Double
    Dim height As Double
    
    ' Define the cone
    center(0) = 0#: center(1) = 0#: center(2) = 0#
    radius = 5#
    height = 20#
    
    ' Create the Cone (3DSolid) object in model space
    Set coneObj = ThisDrawing.ModelSpace.AddCone(center, radius, height)
    
    ' Change the viewing direction of the viewport to better see the cone
    Dim NewDirection(0 To 2) As Double
    NewDirection(0) = -1: NewDirection(1) = -1: NewDirection(2) = 1
    ThisDrawing.ActiveViewport.direction = NewDirection
    ThisDrawing.ActiveViewport = ThisDrawing.ActiveViewport
    ZoomAll
End Sub
Sub Example_AddCylinder()
    ' This example creates a cylinder in model space.
    
    Dim cylinderObj As Acad3DSolid
    Dim radius As Double
    Dim center(0 To 2) As Double
    Dim height As Double
    
    ' Define the cylinder
    center(0) = 0#: center(1) = 0#: center(2) = 0#
    radius = 5#
    height = 20#
    
    ' Create the Cylinder (3DSolid) object in model space
    Set cylinderObj = ThisDrawing.ModelSpace.AddCylinder(center, radius, height)
    
    ' Change the viewing direction of the viewport to better see the cylinder
    Dim NewDirection(0 To 2) As Double
    NewDirection(0) = -1: NewDirection(1) = -1: NewDirection(2) = 1
    ThisDrawing.ActiveViewport.direction = NewDirection
    ThisDrawing.ActiveViewport = ThisDrawing.ActiveViewport
    ZoomAll
End Sub
Sub Example_AddDimOrdinate()
    ' This example creats an ordinate dimension in model space.
    
    Dim dimObj As AcadDimOrdinate
    Dim definingPoint(0 To 2) As Double
    Dim leaderEndPoint(0 To 2) As Double
    Dim useXAxis As Long
    
    ' Define the dimension
    definingPoint(0) = 5#: definingPoint(1) = 5#: definingPoint(2) = 0#
    leaderEndPoint(0) = 10#: leaderEndPoint(1) = 5#: leaderEndPoint(2) = 0#
    useXAxis = 5#
    
    ' Create an ordinate dimension in model space
    Set dimObj = ThisDrawing.ModelSpace.AddDimOrdinate(definingPoint, leaderEndPoint, useXAxis)
    ZoomAll
    
End Sub
Sub Example_AddDimRadial()
    ' This example creates a radial dimension in model space.
    
    Dim dimObj As AcadDimRadial
    Dim center(0 To 2) As Double
    Dim chordPoint(0 To 2) As Double
    Dim leaderLen As Integer
    
    ' Define the dimension
    center(0) = 0#: center(1) = 0#: center(2) = 0#
    chordPoint(0) = 5#: chordPoint(1) = 5#: chordPoint(2) = 0#
    leaderLen = 5
    
    ' Create the radial dimension in model space
    Set dimObj = ThisDrawing.ModelSpace.AddDimRadial(center, chordPoint, leaderLen)
    ZoomAll
End Sub
Sub Example_AddDimRotated()
    ' This example creates a rotated dimension in model space.
        
    Dim dimObj As AcadDimRotated
    Dim point1(0 To 2) As Double
    Dim point2(0 To 2) As Double
    Dim location(0 To 2) As Double
    Dim rotAngle As Double
    
    ' Define the dimension
    point1(0) = 0#: point1(1) = 5#: point1(2) = 0#
    point2(0) = 5#: point2(1) = 5#: point2(2) = 0#
    location(0) = 0#: location(1) = 0#: location(2) = 0#
    rotAngle = 120
    rotAngle = rotAngle * 3.141592 / 180#       ' covert to Radians
    
    ' Create the rotated dimension in model space
    Set dimObj = ThisDrawing.ModelSpace.AddDimRotated(point1, point2, location, rotAngle)
    ZoomAll
End Sub
Sub Example_AddEllipticalCone()
    ' This example creates an elliptical cone in model space.
    
    Dim coneObj As Acad3DSolid
    Dim center(0 To 2) As Double
    Dim majorRadius As Double
    Dim minorRadius As Double
    Dim height As Double
    
    ' Define the elliptical cone
    center(0) = 0#: center(1) = 0#: center(2) = 0#
    majorRadius = 10#
    minorRadius = 5#
    height = 20#
    
    ' Create the elliptical cone in model space
    Set coneObj = ThisDrawing.ModelSpace.AddEllipticalCone(center, majorRadius, minorRadius, height)
    
    ' Change the viewing direction of the viewport to better see the cone
    Dim NewDirection(0 To 2) As Double
    NewDirection(0) = -1: NewDirection(1) = -1: NewDirection(2) = 1
    ThisDrawing.ActiveViewport.direction = NewDirection
    ThisDrawing.ActiveViewport = ThisDrawing.ActiveViewport
    ZoomAll
    
End Sub
Sub Example_AddEllipticalCylinder()
    ' This example creates an elliptical cylinder in model space.
   
    Dim cylinderObj As Acad3DSolid
    Dim center(0 To 2) As Double
    Dim majorRadius As Double
    Dim minorRadius As Double
    Dim height As Double
    
    ' Define the elliptical cylinder
    center(0) = 0#: center(1) = 0#: center(2) = 0#
    majorRadius = 5#
    minorRadius = 2.5
    height = 10#
    
    ' Create the elliptical cylinder in model space
    Set cylinderObj = ThisDrawing.ModelSpace.AddEllipticalCylinder(center, majorRadius, minorRadius, height)
    
    ' Change the viewing direction of the viewport to better see the cone
    Dim NewDirection(0 To 2) As Double
    NewDirection(0) = -1: NewDirection(1) = -1: NewDirection(2) = 1
    ThisDrawing.ActiveViewport.direction = NewDirection
    ThisDrawing.ActiveViewport = ThisDrawing.ActiveViewport
    ZoomAll
    
End Sub
Sub Example_MomentOfInertia()
    ' This example creates a box in model space.
    ' It then returns the MomentOfInertia for that box.
        
    Dim boxObj As Acad3DSolid
    Dim length As Double, width As Double, height As Double
    Dim center(0 To 2) As Double
    
    ' Define the box
    center(0) = 5#: center(1) = 5#: center(2) = 0
    length = 5#: width = 7: height = 10#
    
    ' Create the box (3DSolid) object in model space
    Set boxObj = ThisDrawing.ModelSpace.AddBox(center, length, width, height)
    
    ' Change the viewing direction of the viewport to better see the box
    Dim NewDirection(0 To 2) As Double
    NewDirection(0) = -1: NewDirection(1) = -1: NewDirection(2) = 1
    ThisDrawing.ActiveViewport.direction = NewDirection
    ThisDrawing.ActiveViewport = ThisDrawing.ActiveViewport
    ZoomAll
    
    ' Return the MomentOfInertia for the box
    Dim momentOfInertia As Variant
    momentOfInertia = boxObj.momentOfInertia
    MsgBox "The MomentOfInertia for the box is " & momentOfInertia(0) & ", " & momentOfInertia(1) & ", " & momentOfInertia(2), , "MomentOfInertia Example"
        
End Sub
Sub Example_PrincipalDirections()
    ' This example creates a box in model space.
    ' It then returns the PrincipalDirections for that box.
              
    Dim boxObj As Acad3DSolid
    Dim length As Double, width As Double, height As Double
    Dim center(0 To 2) As Double
    
    ' Define the box
    center(0) = 5#: center(1) = 5#: center(2) = 0
    length = 5#: width = 7: height = 10#
    
    ' Create the box (3DSolid) object in model space
    Set boxObj = ThisDrawing.ModelSpace.AddBox(center, length, width, height)
    
    ' Change the viewing direction of the viewport to better see the box
    Dim NewDirection(0 To 2) As Double
    NewDirection(0) = -1: NewDirection(1) = -1: NewDirection(2) = 1
    ThisDrawing.ActiveViewport.direction = NewDirection
    ThisDrawing.ActiveViewport = ThisDrawing.ActiveViewport
    ZoomAll
    
    ' Return the PrincipalDirections for the box
    Dim PrincipalDirections As Variant
    PrincipalDirections = boxObj.PrincipalDirections
    MsgBox "The PrincipalDirections for the box are " & PrincipalDirections(0) & ", " & PrincipalDirections(1) & ", " & PrincipalDirections(2), , "PrincipalDirections Example"
        
End Sub
Sub Example_PrincipalMoments()
    ' This example creates a box in model space.
    ' It then returns the PrincipalMoments for that box.
        
    Dim boxObj As Acad3DSolid
    Dim length As Double, width As Double, height As Double
    Dim center(0 To 2) As Double
    
    ' Define the box
    center(0) = 5#: center(1) = 5#: center(2) = 0
    length = 5#: width = 7: height = 10#
    
    ' Create the box (3DSolid) object in model space
    Set boxObj = ThisDrawing.ModelSpace.AddBox(center, length, width, height)
    
    ' Change the viewing direction of the viewport to better see the box
    Dim NewDirection(0 To 2) As Double
    NewDirection(0) = -1: NewDirection(1) = -1: NewDirection(2) = 1
    ThisDrawing.ActiveViewport.direction = NewDirection
    ThisDrawing.ActiveViewport = ThisDrawing.ActiveViewport
    ZoomAll
    
    ' Return the PrincipalMoments for the box
    Dim PrincipalMoments As Variant
    PrincipalMoments = boxObj.PrincipalMoments
    MsgBox "The PrincipalMoments for the box are " & PrincipalMoments(0) & ", " & PrincipalMoments(1) & ", " & PrincipalMoments(2), , "PrincipalMoments Example"
        
End Sub
Sub Example_ProductOfInertia()
    ' This example creates a box in model space.
    ' It then returns the ProductOfInertia for that box.
        
    Dim boxObj As Acad3DSolid
    Dim length As Double, width As Double, height As Double
    Dim center(0 To 2) As Double
    
    ' Define the box
    center(0) = 5#: center(1) = 5#: center(2) = 0
    length = 5#: width = 7: height = 10#
    
    ' Create the box (3DSolid) object in model space
    Set boxObj = ThisDrawing.ModelSpace.AddBox(center, length, width, height)
    
    ' Change the viewing direction of the viewport to better see the box
    Dim NewDirection(0 To 2) As Double
    NewDirection(0) = -1: NewDirection(1) = -1: NewDirection(2) = 1
    ThisDrawing.ActiveViewport.direction = NewDirection
    ThisDrawing.ActiveViewport = ThisDrawing.ActiveViewport
    ZoomAll
    
    ' Return the ProductOfInertia for the box
    Dim ProductOfInertia As Variant
    ProductOfInertia = boxObj.ProductOfInertia
    MsgBox "The ProductOfInertia for the box is " & ProductOfInertia(0) & ", " & ProductOfInertia(1) & ", " & ProductOfInertia(2), , "ProductOfInertia Example"
        
End Sub
Sub Example_RadiiOfGyration()
    ' This example creates a box in model space.
    ' It then returns the RadiiOfGyration for that box.
        
    Dim boxObj As Acad3DSolid
    Dim length As Double, width As Double, height As Double
    Dim center(0 To 2) As Double
    
    ' Define the box
    center(0) = 5#: center(1) = 5#: center(2) = 0
    length = 5#: width = 7: height = 10#
    
    ' Create the box (3DSolid) object in model space
    Set boxObj = ThisDrawing.ModelSpace.AddBox(center, length, width, height)
    
    ' Change the viewing direction of the viewport to better see the box
    Dim NewDirection(0 To 2) As Double
    NewDirection(0) = -1: NewDirection(1) = -1: NewDirection(2) = 1
    ThisDrawing.ActiveViewport.direction = NewDirection
    ThisDrawing.ActiveViewport = ThisDrawing.ActiveViewport
    ZoomAll
    
    ' Return the RadiiOfGyration for the box
    Dim RadiiOfGyration As Variant
    RadiiOfGyration = boxObj.RadiiOfGyration
    MsgBox "The RadiiOfGyration for the box is " & RadiiOfGyration(0) & ", " & RadiiOfGyration(1) & ", " & RadiiOfGyration(2), , "RadiiOfGyration Example"
        
End Sub
Sub Example_Volume()
    ' This example creates a box in model space.
    ' It then returns the Volume for that box.
    
    Dim boxObj As Acad3DSolid
    Dim length As Double, width As Double, height As Double
    Dim center(0 To 2) As Double
    
    ' Define the box
    center(0) = 5#: center(1) = 5#: center(2) = 0
    length = 5#: width = 7: height = 10#
    
    ' Create the box (3DSolid) object in model space
    Set boxObj = ThisDrawing.ModelSpace.AddBox(center, length, width, height)
    
    ' Change the viewing direction of the viewport to better see the box
    Dim NewDirection(0 To 2) As Double
    NewDirection(0) = -1: NewDirection(1) = -1: NewDirection(2) = 1
    ThisDrawing.ActiveViewport.direction = NewDirection
    ThisDrawing.ActiveViewport = ThisDrawing.ActiveViewport
    ZoomAll
    
    ' Return the Volume for the box
    Dim Volume As Double
    Volume = boxObj.Volume
    MsgBox "The Volume for the box is " & Volume, , "Volume Example"
        
End Sub
Sub Example_Centroid()
    ' This example creates a box in model space.
    ' It then returns the Centroid for that box.
    
    Dim boxObj As Acad3DSolid
    Dim length As Double, width As Double, height As Double
    Dim center(0 To 2) As Double
    
    ' Define the box
    center(0) = 5#: center(1) = 5#: center(2) = 0
    length = 5#: width = 7: height = 10#
    
    ' Create the box (3DSolid) object in model space
    Set boxObj = ThisDrawing.ModelSpace.AddBox(center, length, width, height)
    
    ' Change the viewing direction of the viewport to better see the box
    Dim NewDirection(0 To 2) As Double
    NewDirection(0) = -1: NewDirection(1) = -1: NewDirection(2) = 1
    ThisDrawing.ActiveViewport.direction = NewDirection
    ThisDrawing.ActiveViewport = ThisDrawing.ActiveViewport
    ZoomAll
    
    ' Return the Centroid for the box
    Dim Centroid As Variant
    Centroid = boxObj.Centroid
    MsgBox "The Centroid for the box is " & Centroid(0) & ", " & Centroid(1), , "Centroid Example"
        
End Sub
Sub Example_Mirror3D()
    ' This example creates a box in model space.
    ' It then mirrors the box about a plane and colors
    ' the new box red.
    
    Dim boxObj As Acad3DSolid
    Dim length As Double, width As Double, height As Double
    Dim center(0 To 2) As Double
    
    ' Define the box
    center(0) = 5#: center(1) = 5#: center(2) = 0
    length = 5#: width = 7: height = 10#
    
    ' Create the box (3DSolid) object in model space
    Set boxObj = ThisDrawing.ModelSpace.AddBox(center, length, width, height)
    
    ' Define the mirroring plane with three points
    Dim mirrorPt1(0 To 2) As Double
    Dim mirrorPt2(0 To 2) As Double
    Dim mirrorPt3(0 To 2) As Double
    
    mirrorPt1(0) = 1.25: mirrorPt1(1) = 0: mirrorPt1(2) = 0
    mirrorPt2(0) = 1.25: mirrorPt2(1) = 2: mirrorPt2(2) = 0
    mirrorPt3(0) = 1.25: mirrorPt3(1) = 2: mirrorPt3(2) = 2
    
    ' Mirror the box
    Dim mirrorBoxObj As Acad3DSolid
    Set mirrorBoxObj = boxObj.Mirror3D(mirrorPt1, mirrorPt2, mirrorPt3)
    mirrorBoxObj.Color = acRed
    
    ' Change the viewing direction of the viewport
    Dim NewDirection(0 To 2) As Double
    NewDirection(0) = -1: NewDirection(1) = -1: NewDirection(2) = 1
    ThisDrawing.ActiveViewport.direction = NewDirection
    ThisDrawing.ActiveViewport = ThisDrawing.ActiveViewport
    ZoomAll
    
End Sub
Sub Example_CheckInterference()
    ' This example creates a box and a cylinder in model space.
    ' It then finds the interference between the two solids and
    ' creates a new solid from that interference.
    
    ' For ease of viewing, the box is colored white, the
    ' cylinder is colored cyan, and the interference solid
    ' is colored red.
    
    Dim boxObj As Acad3DSolid
    Dim boxLength As Double, boxWidth As Double, boxHeight As Double
    Dim boxCenter(0 To 2) As Double
    boxCenter(0) = 5#: boxCenter(1) = 5#: boxCenter(2) = 0
    boxLength = 10#: boxWidth = 7: boxHeight = 10#
    
    ' Create the box (3DSolid) object in model space
    Set boxObj = ThisDrawing.ModelSpace.AddBox(boxCenter, boxLength, boxWidth, boxHeight)
    boxObj.Color = acWhite
    
    ' Define the cylinder
    Dim cylinderObj As Acad3DSolid
    Dim cylinderCenter(0 To 2) As Double
    Dim cylinderRadius As Double
    Dim cylinderHeight As Double
    cylinderCenter(0) = 0#: cylinderCenter(1) = 0#: cylinderCenter(2) = 0#
    cylinderRadius = 5#
    cylinderHeight = 20#
    
    ' Create the Cylinder (3DSolid) object in model space
    Set cylinderObj = ThisDrawing.ModelSpace.AddCylinder(cylinderCenter, cylinderRadius, cylinderHeight)
    cylinderObj.Color = acCyan
    
    ' Find the interference between the two solids and create a new solid from it
    Dim solidObj As Acad3DSolid
    Set solidObj = boxObj.CheckInterference(cylinderObj, True)
    solidObj.Color = acRed
    
    ' Change the viewing direction of the viewport
    Dim NewDirection(0 To 2) As Double
    NewDirection(0) = -1: NewDirection(1) = -1: NewDirection(2) = 1
    ThisDrawing.ActiveViewport.direction = NewDirection
    ThisDrawing.ActiveViewport = ThisDrawing.ActiveViewport
    ZoomAll
    
    ' You can now delete the box and cylinder in AutoCAD to
    ' see the interference solid more clearly.
               
End Sub
Sub Example_Boolean()
    ' This example creates a box and a cylinder in model space.
    ' It then performs a boolean operation on the two solids.
    
    Dim boxObj As Acad3DSolid
    Dim boxLength As Double, boxWidth As Double, boxHeight As Double
    Dim boxCenter(0 To 2) As Double
    boxCenter(0) = 5#: boxCenter(1) = 5#: boxCenter(2) = 0
    boxLength = 10#: boxWidth = 7: boxHeight = 10#
    
    ' Create the box (3DSolid) object in model space
    Set boxObj = ThisDrawing.ModelSpace.AddBox(boxCenter, boxLength, boxWidth, boxHeight)
    boxObj.Color = acWhite
    
    ' Define the cylinder
    Dim cylinderObj As Acad3DSolid
    Dim cylinderCenter(0 To 2) As Double
    Dim cylinderRadius As Double
    Dim cylinderHeight As Double
    cylinderCenter(0) = 0#: cylinderCenter(1) = 0#: cylinderCenter(2) = 0#
    cylinderRadius = 5#
    cylinderHeight = 20#
    
    ' Create the Cylinder (3DSolid) object in model space
    Set cylinderObj = ThisDrawing.ModelSpace.AddCylinder(cylinderCenter, cylinderRadius, cylinderHeight)
    cylinderObj.Color = acWhite
    
    ' Change the viewing direction of the viewport
    Dim NewDirection(0 To 2) As Double
    NewDirection(0) = -1: NewDirection(1) = -1: NewDirection(2) = 1
    ThisDrawing.ActiveViewport.direction = NewDirection
    ThisDrawing.ActiveViewport = ThisDrawing.ActiveViewport
    ZoomAll
    
    ' Perform an intersection on the two solids
    MsgBox "Perform an intersection on the two solids.", vbOKOnly, "Boolean Example"
    boxObj.Boolean acIntersection, cylinderObj
    ThisDrawing.Regen True
    
    MsgBox "Intersection complete.", , "Boolean Example"
    
End Sub
Sub Example_Rotate3D()
    ' This example creates a box in model space.
    ' It then rotates the box about an axis.
        
    Dim boxObj As Acad3DSolid
    Dim length As Double, width As Double, height As Double
    Dim center(0 To 2) As Double
    
    ' Define the box
    center(0) = 5#: center(1) = 5#: center(2) = 0
    length = 5#: width = 7: height = 10#
    
    ' Create the box (3DSolid) object in model space
    Set boxObj = ThisDrawing.ModelSpace.AddBox(center, length, width, height)
    
    ' Change the viewing direction of the viewport
    Dim NewDirection(0 To 2) As Double
    NewDirection(0) = -1: NewDirection(1) = -1: NewDirection(2) = 1
    ThisDrawing.ActiveViewport.direction = NewDirection
    ThisDrawing.ActiveViewport = ThisDrawing.ActiveViewport
    ThisDrawing.Regen True
        
    ' Define the rotation axis with two points
    Dim rotatePt1(0 To 2) As Double
    Dim rotatePt2(0 To 2) As Double
    Dim rotateAngle As Double
    
    rotatePt1(0) = -3: rotatePt1(1) = 4: rotatePt1(2) = 0
    rotatePt2(0) = -3: rotatePt2(1) = -4: rotatePt2(2) = 0
    rotateAngle = 30
    rotateAngle = rotateAngle * 3.141592 / 180#
    
    ' Draw a line between the two axis points so that it is visible.
    ' This is optional. It is not required for the rotation.
    Dim axisLine As AcadLine
    Set axisLine = ThisDrawing.ModelSpace.AddLine(rotatePt1, rotatePt2)
    axisLine.Update
    MsgBox "Rotate the box 30 degrees about the axis shown.", , "Rotate3D Example"

    ' Rotate the box
    boxObj.Rotate3D rotatePt1, rotatePt2, rotateAngle
    ThisDrawing.Regen True
    MsgBox "The box is rotated 30 degrees.", , "Rotate3D Example"
    
End Sub
Sub Example_SectionSolid()
    ' This example creates a box in model space.
    ' It then sections the box based on a plane
    ' defined by three points. The section is returned
    ' as a region.
        
    Dim boxObj As Acad3DSolid
    Dim length As Double, width As Double, height As Double
    Dim center(0 To 2) As Double
    
    ' Define the box
    center(0) = 5#: center(1) = 5#: center(2) = 0
    length = 5#: width = 7: height = 10#
    
    ' Create the box (3DSolid) object in model space
    Set boxObj = ThisDrawing.ModelSpace.AddBox(center, length, width, height)
    
    ' Define the secion plane with three points
    Dim sectionPt1(0 To 2) As Double
    Dim sectionPt2(0 To 2) As Double
    Dim sectionPt3(0 To 2) As Double
    
    sectionPt1(0) = 1.5: sectionPt1(1) = 7.5: sectionPt1(2) = 0
    sectionPt2(0) = 1.5: sectionPt2(1) = 7.5: sectionPt2(2) = 10
    sectionPt3(0) = 8.5: sectionPt3(1) = 2.5: sectionPt3(2) = 10
    
    ' Section the box
    Dim sectionObj As AcadRegion
    Set sectionObj = boxObj.SectionSolid(sectionPt1, sectionPt2, sectionPt3)
    sectionObj.Color = acRed
    
    ' Change the viewing direction of the viewport
    Dim NewDirection(0 To 2) As Double
    NewDirection(0) = -1: NewDirection(1) = -1: NewDirection(2) = 1
    ThisDrawing.ActiveViewport.direction = NewDirection
    ThisDrawing.ActiveViewport = ThisDrawing.ActiveViewport
    ZoomAll
    
End Sub
Sub Example_SliceSolid()
    ' This example creates a box in model space.
    ' It then slices the box based on a plane
    ' defined by three points. The slice is returned
    ' as a 3Dsolid.
        
    Dim boxObj As Acad3DSolid
    Dim length As Double, width As Double, height As Double
    Dim center(0 To 2) As Double
    
    ' Define the box
    center(0) = 5#: center(1) = 5#: center(2) = 0
    length = 5#: width = 7: height = 10#
    
    ' Create the box (3DSolid) object in model space
    Set boxObj = ThisDrawing.ModelSpace.AddBox(center, length, width, height)
    
    ' Define the secion plane with three points
    Dim slicePt1(0 To 2) As Double
    Dim slicePt2(0 To 2) As Double
    Dim slicePt3(0 To 2) As Double
    
    slicePt1(0) = 1.5: slicePt1(1) = 7.5: slicePt1(2) = 0
    slicePt2(0) = 1.5: slicePt2(1) = 7.5: slicePt2(2) = 10
    slicePt3(0) = 8.5: slicePt3(1) = 2.5: slicePt3(2) = 10
    
    ' slice the box
    Dim sliceObj As Acad3DSolid
    Set sliceObj = boxObj.SliceSolid(slicePt1, slicePt2, slicePt3, True)
    sliceObj.Color = acRed
    
    ' Change the viewing direction of the viewport
    Dim NewDirection(0 To 2) As Double
    NewDirection(0) = -1: NewDirection(1) = -1: NewDirection(2) = 1
    ThisDrawing.ActiveViewport.direction = NewDirection
    ThisDrawing.ActiveViewport = ThisDrawing.ActiveViewport
    ZoomAll
    
End Sub
Sub Example_Highlight()
    ' This example creates several objects in model space.
    ' It then iterates through model space and highlights each
    ' object and displays it's Entity Name.
    
    ' Create a Ray object in model space
    Dim rayObj As AcadRay
    Dim basePoint(0 To 2) As Double
    Dim SecondPoint(0 To 2) As Double
    basePoint(0) = 3#: basePoint(1) = 3#: basePoint(2) = 0#
    SecondPoint(0) = 1#: SecondPoint(1) = 3#: SecondPoint(2) = 0#
    Set rayObj = ThisDrawing.ModelSpace.AddRay(basePoint, SecondPoint)
    
    ' Create a polyline object in model space
    Dim plineObj As AcadLWPolyline
    Dim points(0 To 5) As Double
    points(0) = 3: points(1) = 7
    points(2) = 9: points(3) = 2
    points(4) = 3: points(5) = 5
    Set plineObj = ThisDrawing.ModelSpace.AddLightWeightPolyline(points)
    plineObj.Closed = True

    ' Create a line object in model space
    Dim lineObj As AcadLine
    Dim startPoint(0 To 2) As Double
    Dim endPoint(0 To 2) As Double
    startPoint(0) = 0: startPoint(1) = 0: startPoint(2) = 0
    endPoint(0) = 2: endPoint(1) = 2: endPoint(2) = 0
    Set lineObj = ThisDrawing.ModelSpace.AddLine(startPoint, endPoint)
    
    ' Create a circle object in model space
    Dim circObj As AcadCircle
    Dim centerPt(0 To 2) As Double
    Dim radius As Double
    centerPt(0) = 20: centerPt(1) = 30: centerPt(2) = 0
    radius = 3
    Set circObj = ThisDrawing.ModelSpace.AddCircle(centerPt, radius)

    ' Create an ellipse object in model space
    Dim ellObj As AcadEllipse
    Dim majAxis(0 To 2) As Double
    Dim center(0 To 2) As Double
    Dim radRatio As Double
    center(0) = 5#: center(1) = 5#: center(2) = 0#
    majAxis(0) = 10: majAxis(1) = 20#: majAxis(2) = 0#
    radRatio = 0.3
    Set ellObj = ThisDrawing.ModelSpace.AddEllipse(center, majAxis, radRatio)

    ZoomAll
    
    ' Iterate through the model space collection and
    ' highlight each entity.
    
    Dim entName As String
    Dim entry As AcadEntity
    For Each entry In ThisDrawing.ModelSpace
        entName = entry.ObjectName
        entry.Highlight (True)
        MsgBox "The name of this object is " & entName, vbInformation, "Highlight Example"
        entry.Highlight (False)
    Next
End Sub
Sub Example_AddRegion()
    ' This example creates a region from an arc and a line.
    
    Dim curves(0 To 1) As AcadEntity

    ' Define the arc
    Dim centerPoint(0 To 2) As Double
    Dim radius As Double
    Dim startAngle As Double
    Dim endAngle As Double
    centerPoint(0) = 5#: centerPoint(1) = 3#: centerPoint(2) = 0#
    radius = 2#
    startAngle = 0
    endAngle = 3.141592
    Set curves(0) = ThisDrawing.ModelSpace.AddArc(centerPoint, radius, startAngle, endAngle)
    
    ' Define the line
    Set curves(1) = ThisDrawing.ModelSpace.AddLine(curves(0).startPoint, curves(0).endPoint)
        
    ' Create the region
    Dim regionObj As Variant
    regionObj = ThisDrawing.ModelSpace.AddRegion(curves)
    regionObj(0).Color = acRed
    ZoomAll
    
End Sub
Sub Example_AddExtrudedSolid()
    ' This example extrudes a solid from a region.
    ' The region is created from an arc and a line.
    
    Dim curves(0 To 1) As AcadEntity

    ' Define the arc
    Dim centerPoint(0 To 2) As Double
    Dim radius As Double
    Dim startAngle As Double
    Dim endAngle As Double
    centerPoint(0) = 5#: centerPoint(1) = 3#: centerPoint(2) = 0#
    radius = 2#
    startAngle = 0
    endAngle = 3.141592
    Set curves(0) = ThisDrawing.ModelSpace.AddArc(centerPoint, radius, startAngle, endAngle)
    
    ' Define the line
    Set curves(1) = ThisDrawing.ModelSpace.AddLine(curves(0).startPoint, curves(0).endPoint)
        
    ' Create the region
    Dim regionObj As Variant
    regionObj = ThisDrawing.ModelSpace.AddRegion(curves)
    
    ' Define the extrusion
    Dim height As Double
    Dim taperAngle As Double
    height = 3
    taperAngle = 0
    
    ' Create the solid
    Dim solidObj As Acad3DSolid
    Set solidObj = ThisDrawing.ModelSpace.AddExtrudedSolid(regionObj(0), height, taperAngle)
    
    ' Change the viewing direction of the viewport
    Dim NewDirection(0 To 2) As Double
    NewDirection(0) = -1: NewDirection(1) = -1: NewDirection(2) = 1
    ThisDrawing.ActiveViewport.direction = NewDirection
    ThisDrawing.ActiveViewport = ThisDrawing.ActiveViewport
    ZoomAll
        
End Sub
Sub Example_AddExtrudedSolidAlongPath()
    ' This example extrudes a solid from a region
    ' along a path defined by a spline.
    ' The region is created from an arc and a line.
    
    Dim curves(0 To 1) As AcadEntity

    ' Define the arc
    Dim centerPoint(0 To 2) As Double
    Dim radius As Double
    Dim startAngle As Double
    Dim endAngle As Double
    centerPoint(0) = 5#: centerPoint(1) = 3#: centerPoint(2) = 0#
    radius = 2#
    startAngle = 0
    endAngle = 3.141592
    Set curves(0) = ThisDrawing.ModelSpace.AddArc(centerPoint, radius, startAngle, endAngle)
    
    ' Define the line
    Set curves(1) = ThisDrawing.ModelSpace.AddLine(curves(0).startPoint, curves(0).endPoint)
        
    ' Create the region
    Dim regionObj As Variant
    regionObj = ThisDrawing.ModelSpace.AddRegion(curves)
    regionObj(0).Color = acCyan
    
    ' Define the extrusion path (spline object)
    Dim splineObj As AcadSpline
    Dim startTan(0 To 2) As Double
    Dim endTan(0 To 2) As Double
    Dim noOfPoints As Integer
    Dim fitPoints(0 To 8) As Double
    
    ' Define the Spline Object
    startTan(0) = 10: startTan(1) = 10: startTan(2) = 10
    endTan(0) = 10: endTan(1) = 10: endTan(2) = 10
    fitPoints(0) = 0: fitPoints(1) = 10: fitPoints(2) = 10
    fitPoints(0) = 10: fitPoints(1) = 10: fitPoints(2) = 10
    fitPoints(0) = 15: fitPoints(1) = 10: fitPoints(2) = 10
    noOfPoints = 3
    Set splineObj = ThisDrawing.ModelSpace.AddSpline(fitPoints, startTan, endTan)
    
    ' Create the solid
    Dim solidObj As Acad3DSolid
    Set solidObj = ThisDrawing.ModelSpace.AddExtrudedSolidAlongPath(regionObj(0), splineObj)
    solidObj.Color = acRed
    ZoomAll
    
End Sub
Sub Example_AddRevolvedSolid()
    ' This example creates a solid from a region
    ' rotated around an axis.
    ' The region is created from an arc and a line.
    Dim curves(0 To 1) As AcadEntity

    ' Define the arc
    Dim centerPoint(0 To 2) As Double
    Dim radius As Double
    Dim startAngle As Double
    Dim endAngle As Double
    centerPoint(0) = 5#: centerPoint(1) = 3#: centerPoint(2) = 0#
    radius = 2#
    startAngle = 0
    endAngle = 3.141592
    Set curves(0) = ThisDrawing.ModelSpace.AddArc(centerPoint, radius, startAngle, endAngle)
    
    ' Define the line
    Set curves(1) = ThisDrawing.ModelSpace.AddLine(curves(0).startPoint, curves(0).endPoint)
        
    ' Create the region
    Dim regionObj As Variant
    regionObj = ThisDrawing.ModelSpace.AddRegion(curves)
    regionObj(0).Color = acCyan
    ZoomAll
    MsgBox "Revolve the region to create the solid.", , "AddRevolvedSolid Example"
    
    ' Define the rotation axis
    Dim axisPt(0 To 2) As Double
    Dim axisDir(0 To 2) As Double
    Dim angle As Double
    axisPt(0) = 7: axisPt(1) = 2.5: axisPt(2) = 0
    axisDir(0) = 11: axisDir(1) = 1: axisDir(2) = 3
    angle = 6.28
        
    ' Create the solid
    Dim solidObj As Acad3DSolid
    Set solidObj = ThisDrawing.ModelSpace.AddRevolvedSolid(regionObj(0), axisPt, axisDir, angle)
    solidObj.Color = acRed
    ZoomAll
    
     ' Change the viewing direction of the viewport
    Dim NewDirection(0 To 2) As Double
    NewDirection(0) = -1: NewDirection(1) = -1: NewDirection(2) = 1
    ThisDrawing.ActiveViewport.direction = NewDirection
    ThisDrawing.ActiveViewport = ThisDrawing.ActiveViewport
    ZoomAll
    MsgBox "Solid created.", , "AddRevolvedSolid Example"

End Sub
Sub Example_AddSphere()
    ' This example creates a sphere in model space.
    
    Dim sphereObj As Acad3DSolid
    Dim centerPoint(0 To 2) As Double
    Dim radius As Double
    
    centerPoint(0) = 5#: centerPoint(1) = 5#: centerPoint(2) = 0#
    radius = 5#
    Set sphereObj = ThisDrawing.ModelSpace.AddSphere(centerPoint, radius)
        
     ' Change the viewing direction of the viewport
    Dim NewDirection(0 To 2) As Double
    NewDirection(0) = -1: NewDirection(1) = -1: NewDirection(2) = 1
    ThisDrawing.ActiveViewport.direction = NewDirection
    ThisDrawing.ActiveViewport = ThisDrawing.ActiveViewport
    ZoomAll

End Sub
Sub Example_AddTorus()
    ' This example creates a torus in model space.
    
    Dim torusObj As Acad3DSolid
    Dim centerPoint(0 To 2) As Double
    Dim torusRadius As Double
    Dim tubeRadius As Double
    
    ' Define the torus
    centerPoint(0) = 5: centerPoint(1) = 5: centerPoint(2) = 0
    torusRadius = 15
    tubeRadius = 5
    
    ' Create the torus
    Set torusObj = ThisDrawing.ModelSpace.AddTorus(centerPoint, torusRadius, tubeRadius)
            
     ' Change the viewing direction of the viewport
    Dim NewDirection(0 To 2) As Double
    NewDirection(0) = -1: NewDirection(1) = -1: NewDirection(2) = 1
    ThisDrawing.ActiveViewport.direction = NewDirection
    ThisDrawing.ActiveViewport = ThisDrawing.ActiveViewport
    ZoomAll

End Sub
Sub Example_AddTrace()
    ' This example creates a trace in model space.
    
    Dim traceObj As AcadTrace
    Dim tracePts(0 To 11) As Double       ' 4 (3D) points
    
    ' Define the points of the trace
    tracePts(0) = 1: tracePts(1) = 1: tracePts(2) = 0
    tracePts(3) = 3: tracePts(4) = 3: tracePts(5) = 0
    tracePts(6) = 5: tracePts(7) = 3: tracePts(8) = 0
    tracePts(9) = 5: tracePts(10) = 1: tracePts(11) = 0
    
    ' Turn on the system variable (FILLMODE)
    ' to fill the outline of the trace
    ThisDrawing.SetVariable "FILLMODE", 1
        
    ' Create the trace object in model space
    Set traceObj = ThisDrawing.ModelSpace.AddTrace(tracePts)
    ZoomAll
    
End Sub
Sub Example_AddTolerance()
    ' This example creates a tolerance object in model space.
    
    Dim toleranceObj As AcadTolerance
    Dim textString As String
    Dim insertionPoint(0 To 2) As Double
    Dim direction(0 To 2) As Double
    
    ' Define the tolerance object
    textString = "Here is the Feature Control Frame"
    insertionPoint(0) = 5#: insertionPoint(1) = 5#: insertionPoint(2) = 0#
    direction(0) = 1#: direction(1) = 1#: direction(2) = 0#

    ' Create the tolerance object in model space
    Set toleranceObj = ThisDrawing.ModelSpace.AddTolerance(textString, insertionPoint, direction)
    ZoomAll
    
End Sub
Sub Example_AddWedge()
    ' This example creates a wedge in model space.
    
    Dim wedgeObj As Acad3DSolid
    Dim center(0 To 2) As Double
    Dim length As Double
    Dim width As Double
    Dim height As Double
    
    ' Define the wedge
    center(0) = 5#: center(1) = 5#: center(2) = 0
    length = 10#: width = 15#: height = 20#
    
    ' Create the wedge in model space
    Set wedgeObj = ThisDrawing.ModelSpace.AddWedge(center, length, width, height)
    
    ' Change the viewing direction of the viewport
    Dim NewDirection(0 To 2) As Double
    NewDirection(0) = -1: NewDirection(1) = -1: NewDirection(2) = 1
    ThisDrawing.ActiveViewport.direction = NewDirection
    ThisDrawing.ActiveViewport = ThisDrawing.ActiveViewport
    ZoomAll

End Sub
Sub Example_AddXLine()
    ' This example creates an XLine in model space.
    
    Dim xlineObj As AcadXline
    Dim basePoint(0 To 2) As Double
    Dim directionVec(0 To 2) As Double
    
    ' Define the xline
    basePoint(0) = 2#: basePoint(1) = 2#: basePoint(2) = 0#
    directionVec(0) = 1#: directionVec(1) = 1#: directionVec(2) = 0#
    
    ' Create the xline in model space
    Set xlineObj = ThisDrawing.ModelSpace.AddXline(basePoint, directionVec)
    ZoomAll
    
End Sub
Sub Example_AuditInfo()
    ' This example requests AutoCAD perform auditing
    ' and have fix any problems found
    
    ThisDrawing.AuditInfo "audit.txt", True
    
    MsgBox "Auditing has been requested." & vbCrLf & _
           "The fix error flag is set to True.", , "AuditInfo Example"
End Sub
Sub Example_Erase()
    ' This example creates a selection set and several objects.
    ' It then adds the objects to the selection set, and then
    ' erases the objects from the selection set.
    
    ' Create the new selection set
    Dim ssetObj As AcadSelectionSet
    Set ssetObj = ThisDrawing.SelectionSets.Add("TEST_SELECTIONSET")
    
    ' Create a Ray object in model space
    Dim rayObj As AcadRay
    Dim basePoint(0 To 2) As Double
    Dim SecondPoint(0 To 2) As Double
    basePoint(0) = 3#: basePoint(1) = 3#: basePoint(2) = 0#
    SecondPoint(0) = 1#: SecondPoint(1) = 3#: SecondPoint(2) = 0#
    Set rayObj = ThisDrawing.ModelSpace.AddRay(basePoint, SecondPoint)
    
    ' Create a polyline object in model space
    Dim plineObj As AcadLWPolyline
    Dim points(0 To 5) As Double
    points(0) = 3: points(1) = 7
    points(2) = 9: points(3) = 2
    points(4) = 3: points(5) = 5
    Set plineObj = ThisDrawing.ModelSpace.AddLightWeightPolyline(points)
    plineObj.Closed = True

    ' Create a line object in model space
    Dim lineObj As AcadLine
    Dim startPoint(0 To 2) As Double
    Dim endPoint(0 To 2) As Double
    startPoint(0) = 0: startPoint(1) = 0: startPoint(2) = 0
    endPoint(0) = 2: endPoint(1) = 2: endPoint(2) = 0
    Set lineObj = ThisDrawing.ModelSpace.AddLine(startPoint, endPoint)
    
    ' Create a circle object in model space
    Dim circObj As AcadCircle
    Dim centerPt(0 To 2) As Double
    Dim radius As Double
    centerPt(0) = 20: centerPt(1) = 30: centerPt(2) = 0
    radius = 3
    Set circObj = ThisDrawing.ModelSpace.AddCircle(centerPt, radius)

    ' Create an ellipse object in model space
    Dim ellObj As AcadEllipse
    Dim majAxis(0 To 2) As Double
    Dim center(0 To 2) As Double
    Dim radRatio As Double
    center(0) = 5#: center(1) = 5#: center(2) = 0#
    majAxis(0) = 10: majAxis(1) = 20#: majAxis(2) = 0#
    radRatio = 0.3
    Set ellObj = ThisDrawing.ModelSpace.AddEllipse(center, majAxis, radRatio)

    ZoomAll
    
    ' Iterate through the model space collection.
    ' Collect the objects found into an array of objects
    ' to be added to the selection set.
    ReDim ssobjs(0 To ThisDrawing.ModelSpace.count - 1) As AcadEntity
    Dim I As Integer
    For I = 0 To ThisDrawing.ModelSpace.count - 1
        Set ssobjs(I) = ThisDrawing.ModelSpace.Item(I)
    Next
    
    ' Add the array of objects to the selection set
    ssetObj.AddItems ssobjs
    
    GoSub LISTOBJS
    
    ' Erase the objects in the selection set
    ssetObj.Erase
    
    GoSub LISTOBJS
    
    ' exit the subroutine
Exit Sub
LISTOBJS:
    
        ' List all the objects in the selection set
        If ssetObj.count = 0 Then
            MsgBox "The selection set is empty"
        Else
            For I = 0 To ssetObj.count - 1
                MsgBox "The selection set contains: " & ssetObj.Item(I).ObjectName
            Next
        End If
        Return
End Sub

Sub Example_GetVariable()
    ' This example finds the current setting of the
    ' system variable FILLMODE.
    
    Dim sysVarName As String
    Dim varData As Variant
    
    sysVarName = "FILLMODE"
    varData = ThisDrawing.GetVariable(sysVarName)
    MsgBox sysVarName & " = " & varData, , "GetVariable Example"
    
End Sub

Sub Example_SetVariable()
    ' This example sets various system variables, each of
    ' a different data type.
    
    Dim sysVarName As String
    Dim sysVarData As Variant
    Dim DataType As Integer
    
    ' Set FILEDIA system variable (data type Integer) to 1. NOTE that
    ' you need to declare a variable as the data type of system variable,
    ' assign data to that variable and then make it variant type
    Dim intData As Integer
    sysVarName = "FILEDIA"
    intData = 1
    sysVarData = intData    ' Integer data
    ThisDrawing.SetVariable sysVarName, sysVarData
    
    ' Check the variable using GetVariable
    sysVarData = ThisDrawing.GetVariable(sysVarName)
    MsgBox sysVarName & " = " & sysVarData, , "SetVariable Example"
    
    ' Set DCTCUST system variable (data type String) to "My Custom Dictionary"
    Dim strData As String
    sysVarName = "DCTCUST"
    strData = "My Custom Dictionary"
    sysVarData = strData        ' String data
    ThisDrawing.SetVariable sysVarName, sysVarData
    
    ' Check the variable using GetVariable
    sysVarData = ThisDrawing.GetVariable(sysVarName)
    MsgBox sysVarName & " = " & sysVarData, , "SetVariable Example"
   
    ' Set CHAMFERA system variable (data type Double) to 1.5
    Dim dataDouble As Double
    sysVarName = "CHAMFERA"
    dataDouble = 1.5
    sysVarData = dataDouble ' Double data
    ThisDrawing.SetVariable sysVarName, sysVarData
    ' Check the variable using GetVariable
    sysVarData = ThisDrawing.GetVariable(sysVarName)
    MsgBox sysVarName & " = " & sysVarData, , "SetVariable Example"
   
    ' Set INSBASE system variable (data type array) to (1.0,1.0,0)
    Dim arrayData3D(0 To 2) As Double
    sysVarName = "INSBASE"
    arrayData3D(0) = 1#: arrayData3D(1) = 1#: arrayData3D(2) = 0
    sysVarData = arrayData3D    ' 3D array data
    ThisDrawing.SetVariable sysVarName, sysVarData
    ' Check the variable using GetVariable
    sysVarData = ThisDrawing.GetVariable(sysVarName)
    MsgBox sysVarName & " = " & sysVarData(0) & ", " & sysVarData(1) & ", " & sysVarData(2), , "SetVariable Example"
    
End Sub
Sub Example_AddHatch()
    ' This example creates an associative hatch in model space.
    
    Dim hatchObj As AcadHatch
    Dim patternName As String
    Dim PatternType As Long
    Dim bAssociativity As Boolean
    
    ' Define the hatch
    patternName = "ANSI31"
    PatternType = 0
    bAssociativity = True
    
    ' Create the associative Hatch object in model space
    Set hatchObj = ThisDrawing.ModelSpace.AddHatch(PatternType, patternName, bAssociativity)
    
    ' Create the outer boundary for the hatch. (a circle)
    Dim outerLoop(0 To 0) As AcadEntity
    Dim center(0 To 2) As Double
    Dim radius As Double
    center(0) = 3: center(1) = 3: center(2) = 0
    radius = 1
    Set outerLoop(0) = ThisDrawing.ModelSpace.AddCircle(center, radius)
    
    ' Append the outerboundary to the hatch object, and display the hatch
    hatchObj.AppendOuterLoop (outerLoop)
    hatchObj.Evaluate
    ThisDrawing.Regen True
    
End Sub
Sub Example_Evaluate()
    ' This example creates an associative hatch in model space.
    ' It uses the Evaluate method to calculate the hatch
    ' lines for the given boundary.
    
    Dim hatchObj As AcadHatch
    Dim patternName As String
    Dim PatternType As Long
    Dim bAssociativity As Boolean
    
    ' Define the hatch
    patternName = "ANSI31"
    PatternType = 0
    bAssociativity = True
    
    ' Create the associative Hatch object in model space
    Set hatchObj = ThisDrawing.ModelSpace.AddHatch(PatternType, patternName, bAssociativity)
    
    ' Create the outer boundary for the hatch. (a circle)
    Dim outerLoop(0 To 0) As AcadEntity
    Dim center(0 To 2) As Double
    Dim radius As Double
    center(0) = 3: center(1) = 3: center(2) = 0
    radius = 1
    Set outerLoop(0) = ThisDrawing.ModelSpace.AddCircle(center, radius)
    
    ' Append the outerboundary to the hatch object, and display the hatch
    hatchObj.AppendOuterLoop (outerLoop)
    hatchObj.Evaluate
    ThisDrawing.Regen True
    
End Sub
Sub Example_AppendOuterLoop()
    ' This example creates an associative hatch in model space.
    
    Dim hatchObj As AcadHatch
    Dim patternName As String
    Dim PatternType As Long
    Dim bAssociativity As Boolean
    
    ' Define the hatch
    patternName = "ANSI31"
    PatternType = 0
    bAssociativity = True
    
    ' Create the associative Hatch object
    Set hatchObj = ThisDrawing.ModelSpace.AddHatch(PatternType, patternName, bAssociativity)
    
    ' Create the outer loop for the hatch.
    ' An arc and a line are used to create a closed loop.
    Dim outerLoop(0 To 1) As AcadEntity
    Dim center(0 To 2) As Double
    Dim radius As Double
    Dim startAngle As Double
    Dim endAngle As Double
    center(0) = 5: center(1) = 3: center(2) = 0
    radius = 1
    startAngle = 0
    endAngle = 3.141592
    Set outerLoop(0) = ThisDrawing.ModelSpace.AddArc(center, radius, startAngle, endAngle)
    Set outerLoop(1) = ThisDrawing.ModelSpace.AddLine(outerLoop(0).startPoint, outerLoop(0).endPoint)
        
    ' Append the outer loop to the hatch object, and display the hatch
    hatchObj.AppendOuterLoop (outerLoop)
    hatchObj.Evaluate
    ZoomAll
    
End Sub
Sub Example_AppendVertex()
    ' This example creates a polyline in model space.
    ' It then appends a vertex to the polyline.
    
    Dim plineObj As AcadPolyline
    Dim points(0 To 14) As Double
    
    
    ' Define the 2D polyline points
    points(0) = 1: points(1) = 1: points(2) = 0
    points(3) = 1: points(4) = 2: points(5) = 0
    points(6) = 2: points(7) = 2: points(8) = 0
    points(9) = 3: points(10) = 2: points(11) = 0
    points(12) = 4: points(13) = 4: points(14) = 0
        
    ' Create a light weight Polyline object in model space
    Set plineObj = ThisDrawing.ModelSpace.AddPolyline(points)
    ZoomAll
    MsgBox "Append the vertex 4, 1, 0.", , "AppendVertex Example"
    
    Dim newVertex(0 To 2) As Double
    newVertex(0) = 4: newVertex(1) = 1: newVertex(2) = 0
    plineObj.AppendVertex newVertex
    ZoomAll
    MsgBox "The vertex 4, 1, 0 as been appended.", , "AppendVertex Example"

End Sub

Sub Example_AppendInnerLoop()
    ' This example creates an associative hatch in model space.
    
    Dim hatchObj As AcadHatch
    Dim patternName As String
    Dim PatternType As Long
    Dim bAssociativity As Boolean
    
    ' Define the hatch
    patternName = "ANSI31"
    PatternType = 0
    bAssociativity = True
    
    ' Create the associative Hatch object
    Set hatchObj = ThisDrawing.ModelSpace.AddHatch(PatternType, patternName, bAssociativity)
    
    ' Create the outer loop for the hatch.
    ' An arc and a line are used to create a closed loop.
    
    Dim outerLoop(0 To 1) As AcadEntity
    Dim center(0 To 2) As Double
    Dim radius As Double
    Dim startAngle As Double
    Dim endAngle As Double
    center(0) = 5: center(1) = 3: center(2) = 0
    radius = 3
    startAngle = 0
    endAngle = 3.141592
    Set outerLoop(0) = ThisDrawing.ModelSpace.AddArc(center, radius, startAngle, endAngle)
    Set outerLoop(1) = ThisDrawing.ModelSpace.AddLine(outerLoop(0).startPoint, outerLoop(0).endPoint)
        
    ' Append the outer loop to the hatch object
    hatchObj.AppendOuterLoop (outerLoop)
    
    ' Append a circle as the inner loop for the hatch.
    Dim innerLoop(0) As AcadEntity
    center(0) = 5: center(1) = 4.5: center(2) = 0
    radius = 1
    Set innerLoop(0) = ThisDrawing.ModelSpace.AddCircle(center, radius)
    hatchObj.AppendInnerLoop (innerLoop)
    
    ' Evaluate and display the hatch
    hatchObj.Evaluate
    ThisDrawing.Regen True
    
End Sub
Sub Example_HatchStyle()
    ' This example creates an associative hatch in model space.
    ' The hatch style is then changed to demonstrate the different
    ' ways that inner loops are processed.
    
    Dim hatchObj As AcadHatch
    Dim patternName As String
    Dim PatternType As Long
    Dim bAssociativity As Boolean
    
    ' Define the hatch
    patternName = "ANSI31"
    PatternType = 0
    bAssociativity = True
    
    ' Create the associative Hatch object
    Set hatchObj = ThisDrawing.ModelSpace.AddHatch(PatternType, patternName, bAssociativity)
    
    ' Create the outer loop for the hatch.
    ' An arc and a line are used to create a closed loop.
    
    Dim outerLoop(0 To 1) As AcadEntity
    Dim center(0 To 2) As Double
    Dim radius As Double
    Dim startAngle As Double
    Dim endAngle As Double
    center(0) = 5: center(1) = 3: center(2) = 0
    radius = 3
    startAngle = 0
    endAngle = 3.141592
    Set outerLoop(0) = ThisDrawing.ModelSpace.AddArc(center, radius, startAngle, endAngle)
    Set outerLoop(1) = ThisDrawing.ModelSpace.AddLine(outerLoop(0).startPoint, outerLoop(0).endPoint)
        
    ' Append the outer loop to the hatch object
    hatchObj.AppendOuterLoop (outerLoop)
    
    ' Append the first circle as one inner loop
    Dim innerLoop1(0) As AcadEntity
    center(0) = 5: center(1) = 4.5: center(2) = 0
    radius = 1
    Set innerLoop1(0) = ThisDrawing.ModelSpace.AddCircle(center, radius)
    hatchObj.AppendInnerLoop (innerLoop1)
    
    ' Append the second circle as the other inner loop
    Dim innerLoop2(0) As AcadEntity
    radius = 0.5
    Set innerLoop2(0) = ThisDrawing.ModelSpace.AddCircle(center, radius)
    hatchObj.AppendInnerLoop (innerLoop2)
    
    ' Set the hatch style to normal
    hatchObj.HatchStyle = acHatchStyleNormal
    hatchObj.Evaluate
    ThisDrawing.Regen True
    MsgBox "The HatchStyle is set to " & Choose(hatchObj.HatchStyle + 1, "acHatchStyleNormal", "acHatchStyleOuter", "acHatchStyleIgnore"), , "HatchStyle Example"
    
    ' Set the hatch style to outer
    hatchObj.HatchStyle = acHatchStyleOuter
    hatchObj.Evaluate
    ThisDrawing.Regen True
    MsgBox "The HatchStyle is set to " & Choose(hatchObj.HatchStyle + 1, "acHatchStyleNormal", "acHatchStyleOuter", "acHatchStyleIgnore"), , "HatchStyle Example"
        
    ' Set the hatch style to ignore
    hatchObj.HatchStyle = acHatchStyleIgnore
    hatchObj.Evaluate
    ThisDrawing.Regen True
    MsgBox "The HatchStyle is set to " & Choose(hatchObj.HatchStyle + 1, "acHatchStyleNormal", "acHatchStyleOuter", "acHatchStyleIgnore"), , "HatchStyle Example"
               
End Sub
Sub Example_AssociativeHatch()
    ' This example creates an hatch in model space.
    ' It then returns if the hatch is associative or not.
    
    Dim hatchObj As AcadHatch
    Dim patternName As String
    Dim PatternType As Long
    Dim bAssociativity As Boolean
    
    ' Define the hatch
    patternName = "ANSI31"
    PatternType = 0
    bAssociativity = True
    
    ' Create the associative Hatch object
    Set hatchObj = ThisDrawing.ModelSpace.AddHatch(PatternType, patternName, bAssociativity)
    
    ' Create the outer loop for the hatch.
    ' An arc and a line are used to create a closed loop.
    
    Dim outerLoop(0 To 1) As AcadEntity
    Dim center(0 To 2) As Double
    Dim radius As Double
    Dim startAngle As Double
    Dim endAngle As Double
    center(0) = 5: center(1) = 3: center(2) = 0
    radius = 3
    startAngle = 0
    endAngle = 3.141592
    Set outerLoop(0) = ThisDrawing.ModelSpace.AddArc(center, radius, startAngle, endAngle)
    Set outerLoop(1) = ThisDrawing.ModelSpace.AddLine(outerLoop(0).startPoint, outerLoop(0).endPoint)
        
    ' Append the outer loop to the hatch object
    hatchObj.AppendOuterLoop (outerLoop)
    
    ' Evaluate and display the hatch
    hatchObj.Evaluate
    ThisDrawing.Regen True
    
    ' Return if the hatch is associative or not
    Dim hatchAssoc As Boolean
    hatchAssoc = hatchObj.AssociativeHatch
    MsgBox "The HatchStyle is " & IIf(hatchObj.AssociativeHatch, "associative.", "not associative."), , "AssociativeHatch Example"
    
End Sub
Sub Example_NumberOfLoops()
    ' This example creates an associative hatch in model space.
    ' The number of loops in the hatch is then returned.
    
    Dim hatchObj As AcadHatch
    Dim patternName As String
    Dim PatternType As Long
    Dim bAssociativity As Boolean
    
    ' Define the hatch
    patternName = "ANSI31"
    PatternType = 0
    bAssociativity = True
    
    ' Create the associative Hatch object
    Set hatchObj = ThisDrawing.ModelSpace.AddHatch(PatternType, patternName, bAssociativity)
    
    ' Create the outer loop for the hatch.
    ' An arc and a line are used to create a closed loop.
    
    Dim outerLoop(0 To 1) As AcadEntity
    Dim center(0 To 2) As Double
    Dim radius As Double
    Dim startAngle As Double
    Dim endAngle As Double
    center(0) = 5: center(1) = 3: center(2) = 0
    radius = 3
    startAngle = 0
    endAngle = 3.141592
    Set outerLoop(0) = ThisDrawing.ModelSpace.AddArc(center, radius, startAngle, endAngle)
    Set outerLoop(1) = ThisDrawing.ModelSpace.AddLine(outerLoop(0).startPoint, outerLoop(0).endPoint)
        
    ' Append the outer loop to the hatch object
    hatchObj.AppendOuterLoop (outerLoop)
    
    ' Append the first circle as one inner loop
    Dim innerLoop1(0) As AcadEntity
    center(0) = 5: center(1) = 4.5: center(2) = 0
    radius = 1
    Set innerLoop1(0) = ThisDrawing.ModelSpace.AddCircle(center, radius)
    hatchObj.AppendInnerLoop (innerLoop1)
    
    ' Append the second circle as the other inner loop
    Dim innerLoop2(0) As AcadEntity
    radius = 0.5
    Set innerLoop2(0) = ThisDrawing.ModelSpace.AddCircle(center, radius)
    hatchObj.AppendInnerLoop (innerLoop2)
    
    ' Evaluate and display the hatch
    hatchObj.Evaluate
    ThisDrawing.Regen True
    
    ' Find the number of loops in the hatch
    Dim numOfLoops As Integer
    numOfLoops = hatchObj.NumberOfLoops
    MsgBox "The number of loops in the hatch is " & hatchObj.NumberOfLoops, , "NumberOfLoops Example"
               
End Sub
Sub Example_PatternAngle()
    ' This example creates an associative hatch in model space.
    ' The angle of the hatch pattern is returned, and updated.
    
    Dim hatchObj As AcadHatch
    Dim patternName As String
    Dim PatternType As Long
    Dim bAssociativity As Boolean
    
    ' Define the hatch
    patternName = "ANSI31"
    PatternType = 0
    bAssociativity = True
    
    ' Create the associative Hatch object
    Set hatchObj = ThisDrawing.ModelSpace.AddHatch(PatternType, patternName, bAssociativity)
    
    ' Create the outer loop for the hatch.
    ' An arc and a line are used to create a closed loop.
    
    Dim outerLoop(0 To 1) As AcadEntity
    Dim center(0 To 2) As Double
    Dim radius As Double
    Dim startAngle As Double
    Dim endAngle As Double
    center(0) = 5: center(1) = 3: center(2) = 0
    radius = 3
    startAngle = 0
    endAngle = 3.141592
    Set outerLoop(0) = ThisDrawing.ModelSpace.AddArc(center, radius, startAngle, endAngle)
    Set outerLoop(1) = ThisDrawing.ModelSpace.AddLine(outerLoop(0).startPoint, outerLoop(0).endPoint)
        
    ' Append the outer loop to the hatch object
    hatchObj.AppendOuterLoop (outerLoop)
    
    ' Append the first circle as one inner loop
    Dim innerLoop1(0) As AcadEntity
    center(0) = 5: center(1) = 4.5: center(2) = 0
    radius = 1
    Set innerLoop1(0) = ThisDrawing.ModelSpace.AddCircle(center, radius)
    hatchObj.AppendInnerLoop (innerLoop1)
    
    ' Append the second circle as the other inner loop
    Dim innerLoop2(0) As AcadEntity
    radius = 0.5
    Set innerLoop2(0) = ThisDrawing.ModelSpace.AddCircle(center, radius)
    hatchObj.AppendInnerLoop (innerLoop2)
    
    ' Evaluate and display the hatch
    hatchObj.Evaluate
    ThisDrawing.Regen True
    
    ' Find the angle of the hatch pattern
    Dim patternAngle As Double
    patternAngle = hatchObj.patternAngle
    MsgBox "The angle of the hatch pattern is " & hatchObj.patternAngle, , "PatternAngle Example"
               
    ' Change the angle of the hatch pattern
    hatchObj.patternAngle = 5.25
    hatchObj.Evaluate
    ThisDrawing.Regen True
    MsgBox "The angle of the hatch pattern is now " & hatchObj.patternAngle, , "PatternAngle Example"
    
End Sub
Sub Example_PatternDouble()
    ' This example creates an associative hatch in model space.
    ' It then returns whether or not the pattern is doubled, and
    ' then changes that value.
    
    Dim hatchObj As AcadHatch
    Dim patternName As String
    Dim PatternType As Long
    Dim bAssociativity As Boolean
    
    ' Define the hatch
    patternName = "ansi31"
    PatternType = acHatchPatternTypePreDefined
    bAssociativity = True
    
    ' Create the associative Hatch object
    Set hatchObj = ThisDrawing.ModelSpace.AddHatch(PatternType, patternName, bAssociativity)
    
    ' Create the outer loop for the hatch.
    ' An arc and a line are used to create a closed loop.
    
    Dim outerLoop(0 To 1) As AcadEntity
    Dim center(0 To 2) As Double
    Dim radius As Double
    Dim startAngle As Double
    Dim endAngle As Double
    center(0) = 5: center(1) = 3: center(2) = 0
    radius = 3
    startAngle = 0
    endAngle = 3.141592
    Set outerLoop(0) = ThisDrawing.ModelSpace.AddArc(center, radius, startAngle, endAngle)
    Set outerLoop(1) = ThisDrawing.ModelSpace.AddLine(outerLoop(0).startPoint, outerLoop(0).endPoint)
        
    ' Append the outer loop to the hatch object
    hatchObj.AppendOuterLoop (outerLoop)
    
    ' Append the first circle as one inner loop
    Dim innerLoop1(0) As AcadEntity
    center(0) = 5: center(1) = 4.5: center(2) = 0
    radius = 1
    Set innerLoop1(0) = ThisDrawing.ModelSpace.AddCircle(center, radius)
    hatchObj.AppendInnerLoop (innerLoop1)
    
    ' Append the second circle as the other inner loop
    Dim innerLoop2(0) As AcadEntity
    radius = 0.5
    Set innerLoop2(0) = ThisDrawing.ModelSpace.AddCircle(center, radius)
    hatchObj.AppendInnerLoop (innerLoop2)
    
    ' Evaluate and display the hatch
    hatchObj.Evaluate
    ThisDrawing.Regen True
    
    ' Determine if the pattern is doubled
    Dim patternDouble As Boolean
    patternDouble = hatchObj.patternDouble
    MsgBox "Pattern doubling: " & hatchObj.patternDouble, , "PatternDouble Example"
               
    ' Change the angle of the hatch pattern
    hatchObj.patternDouble = Not (hatchObj.patternDouble)
    hatchObj.Evaluate
    ThisDrawing.Regen True
    MsgBox "Pattern doubling: " & hatchObj.patternDouble, , "PatternDouble Example"
    
End Sub
Sub Example_XVector()
    ' This finds the current setting of XVector for a given UCS.
    ' It then changes the XVector and resets the UCS.

    Dim viewportObj As AcadViewport
    
    ' Set the viewportObj variable to the activeviewport
    Set viewportObj = ThisDrawing.ActiveViewport
    
    ' Define a new UCS and turn on the UCS icon at the origin.
    Dim ucsObj As AcadUCS
    Dim origin(0 To 2) As Double
    Dim xAxisPoint(0 To 2) As Double
    Dim yAxisPoint(0 To 2) As Double
    
    origin(0) = 2: origin(1) = 2: origin(2) = 0
    xAxisPoint(0) = 3: xAxisPoint(1) = 2: xAxisPoint(2) = 0
    yAxisPoint(0) = 2: yAxisPoint(1) = 3: yAxisPoint(2) = 0
    
    Set ucsObj = ThisDrawing.UserCoordinateSystems.Add(origin, xAxisPoint, yAxisPoint, "UCS1")
    ThisDrawing.ActiveUCS = ucsObj
    viewportObj.UCSIconOn = True
    viewportObj.UCSIconAtOrigin = True
    ThisDrawing.ActiveViewport = viewportObj
    
    ' Display the current setting of the XVector
    MsgBox "The current XVector is: " _
            & ucsObj.XVector(0) & ", " & ucsObj.XVector(1) & ", " & ucsObj.XVector(2) & vbCrLf _
            & "The current YVector is: " _
            & ucsObj.YVector(0) & ", " & ucsObj.YVector(1) & ", " & ucsObj.YVector(2), , "XVector Example"

    ' Change the setting of XVector
    Dim newVector(0 To 2) As Double
    newVector(0) = 1: newVector(1) = 1: newVector(2) = 0
    ucsObj.XVector = newVector
    
    ' Reset the active UCS to see the change
    ThisDrawing.ActiveUCS = ucsObj
    
    MsgBox "The new XVector is: " _
            & ucsObj.XVector(0) & ", " & ucsObj.XVector(1) & ", " & ucsObj.XVector(2) & vbCrLf _
            & "The YVector is: " _
            & ucsObj.YVector(0) & ", " & ucsObj.YVector(1) & ", " & ucsObj.YVector(2), , "XVector Example"
    
End Sub
Sub Example_YVector()
    ' This finds the current setting of YVector for a given UCS.
    ' It then changes the YVector and resets the UCS.

    Dim viewportObj As AcadViewport
    
    ' Set the viewportObj variable to the activeviewport
    Set viewportObj = ThisDrawing.ActiveViewport
    
    ' Define a new UCS and turn on the UCS icon at the origin.
    Dim ucsObj As AcadUCS
    Dim origin(0 To 2) As Double
    Dim xAxisPoint(0 To 2) As Double
    Dim yAxisPoint(0 To 2) As Double
    
    origin(0) = 2: origin(1) = 2: origin(2) = 0
    xAxisPoint(0) = 3: xAxisPoint(1) = 2: xAxisPoint(2) = 0
    yAxisPoint(0) = 2: yAxisPoint(1) = 3: yAxisPoint(2) = 0
    
    Set ucsObj = ThisDrawing.UserCoordinateSystems.Add(origin, xAxisPoint, yAxisPoint, "UCS1")
    ThisDrawing.ActiveUCS = ucsObj
    viewportObj.UCSIconOn = True
    viewportObj.UCSIconAtOrigin = True
    ThisDrawing.ActiveViewport = viewportObj
    
    ' Display the current setting of the vectors
    MsgBox "The current XVector is: " _
            & ucsObj.XVector(0) & ", " & ucsObj.XVector(1) & ", " & ucsObj.XVector(2) & vbCrLf _
            & "The current YVector is: " _
            & ucsObj.YVector(0) & ", " & ucsObj.YVector(1) & ", " & ucsObj.YVector(2), , "YVector Example"

    ' Change the setting of YVector
    Dim newVector(0 To 2) As Double
    newVector(0) = -1: newVector(1) = -1: newVector(2) = 0
    ucsObj.YVector = newVector
    
    ' Reset the active UCS to see the change
    ThisDrawing.ActiveUCS = ucsObj
    
    MsgBox "The new XVector is: " _
            & ucsObj.XVector(0) & ", " & ucsObj.XVector(1) & ", " & ucsObj.XVector(2) & vbCrLf _
            & "The YVector is: " _
            & ucsObj.YVector(0) & ", " & ucsObj.YVector(1) & ", " & ucsObj.YVector(2), , "YVector Example"
    
End Sub
Sub Example_GetUCSMatrix()
    ' This example creates a new UCS and finds the UCS matrix for it.
    ' It then creates a circle using WCS coordinates and
    ' transforms the circle for the UCS.
    
    ' Define a new UCS and turn on the UCS icon at the origin.
    Dim ucsObj As AcadUCS
    Dim origin(0 To 2) As Double
    Dim xAxisPoint(0 To 2) As Double
    Dim yAxisPoint(0 To 2) As Double
    
    origin(0) = 2: origin(1) = 2: origin(2) = 0
    xAxisPoint(0) = 3: xAxisPoint(1) = 2: xAxisPoint(2) = 0
    yAxisPoint(0) = 2: yAxisPoint(1) = 3: yAxisPoint(2) = 0
    
    Set ucsObj = ThisDrawing.UserCoordinateSystems.Add(origin, xAxisPoint, yAxisPoint, "UCS1")
    ThisDrawing.ActiveUCS = ucsObj
    ThisDrawing.ActiveViewport.UCSIconOn = True
    ThisDrawing.ActiveViewport.UCSIconAtOrigin = True
    ThisDrawing.ActiveViewport = ThisDrawing.ActiveViewport
    
    ' Create a circle using WCS coordinates
    Dim circleObj As AcadCircle
    Dim center(0 To 2) As Double
    Dim radius As Double
    center(0) = 1: center(1) = 1: center(2) = 0
    radius = 0.5
    Set circleObj = ThisDrawing.ModelSpace.AddCircle(center, radius)
    ZoomAll
    
    ' Get the UCS transformation matrix
    Dim TransMatrix As Variant
    TransMatrix = ucsObj.GetUCSMatrix()
    
    ' Transform the circle to the UCS coordinates
    MsgBox "Transform the circle.", , "GetUCSMatrix Example"
    circleObj.TransformBy (TransMatrix)
    circleObj.Update
    
    MsgBox "The circle is transformed.", , "GetUCSMatrix Example"
        
End Sub
Sub Example_TransformBy()
    ' This example creates a line and rotates it 90 degrees
    ' using a transformation matrix.
    
    ' Create a line
    Dim lineObj As AcadLine
    Dim startPt(0 To 2) As Double
    Dim endPt(0 To 2) As Double
    startPt(0) = 2: startPt(1) = 1: startPt(2) = 0
    endPt(0) = 5: endPt(1) = 1: endPt(2) = 0
    Set lineObj = ThisDrawing.ModelSpace.AddLine(startPt, endPt)
    lineObj.Update
    
    ' Initialize the transMat variable with a transformation matrix
    ' that will rotate an object by 90 degrees about the point(0,0,0)
    ' (More examples of transformation matrices are listed below)
    Dim transMat(0 To 3, 0 To 3) As Double
    transMat(0, 0) = 0#: transMat(0, 1) = -1#: transMat(0, 2) = 0#: transMat(0, 3) = 0#
    transMat(1, 0) = 1#: transMat(1, 1) = 0#: transMat(1, 2) = 0#: transMat(1, 3) = 0#
    transMat(2, 0) = 0#: transMat(2, 1) = 0#: transMat(2, 2) = 1#: transMat(2, 3) = 0#
    transMat(3, 0) = 0#: transMat(3, 1) = 0#: transMat(3, 2) = 0#: transMat(3, 3) = 1#
    
    ' Transform the line using the defined transformation matrix
    MsgBox "Transform the line.", , "TransformBy Example"
    lineObj.TransformBy (transMat)
    ZoomAll
    MsgBox "The line is transformed.", , "TransformBy Example"
    
' More examples of transformation matrices:

' Rotation Matrix: 90 Degrees about point 0,0,0
        ' 0.000000  -1.000000  0.000000  0.000000
        ' 1.000000  0.000000  0.000000  0.000000
        ' 0.000000  0.000000  1.000000  0.000000
        ' 0.000000  0.000000  0.000000  1.000000
        
' Rotation Matrix: 45 Degrees about point 5,5,0
        ' 0.707107  -0.707107  0.000000  5.000000
        ' 0.707107  0.707107  0.000000  -2.071068
        ' 0.000000  0.000000  1.000000  0.000000
        ' 0.000000  0.000000  0.000000  1.000000
        
' Translation Matrix: move an object by 10,10,0
        ' 1.000000  0.000000  0.000000  10.000000
        ' 0.000000  1.000000  0.000000  10.000000
        ' 0.000000  0.000000  1.000000  0.000000
        ' 0.000000  0.000000  0.000000  1.000000

' Scaling Matrix: scale by 10,10 at point 0,0,0
        ' 10.000000  0.000000  0.000000  0.000000
        ' 0.000000  10.000000  0.000000  0.000000
        ' 0.000000  0.000000  10.000000  0.000000
        ' 0.000000  0.000000  0.000000  1.000000
        
' Scaling Matrix: scale by 10 at point 2,2
        ' 10.000000  0.000000  0.000000  -18.000000
        ' 0.000000  10.000000  0.000000  -18.000000
        ' 0.000000  0.000000  10.000000  0.000000
        ' 0.000000  0.000000  0.000000  1.000000
End Sub
Sub Example_DisplayPlotPreview()
    ' This example creates a circle and then performs
    ' a plot preview.
    
    ' Create the circle
    Dim circleObj As AcadCircle
    Dim center(0 To 2) As Double
    Dim radius As Double
    center(0) = 2: center(1) = 2: center(2) = 0
    radius = 1
    Set circleObj = ThisDrawing.ModelSpace.AddCircle(center, radius)
    ZoomAll
    
    ' Preview the plot of the circle
    ThisDrawing.Plot.DisplayPlotPreview acFullPreview
        
End Sub
Sub Example_PlotToDevice()
    ' This example sends a plot of the current drawing
    ' to a the default device for your system.
    
    ThisDrawing.Plot.PlotToDevice
    
End Sub
Sub Example_PlotToFile()
    ' This example sends a plot of the current drawing
    ' to a file.
    
    ' Define the output file name.
    ' Use "" to use the drawing name as the file name.
    Dim plotFileName As String
    plotFileName = "MyPlot"
    
    Dim result As Boolean
        
    result = ThisDrawing.Plot.PlotToFile(plotFileName)
    
End Sub
Sub Example_LocaleID()
    ' This code retrieves the Locale ID and displays it in a message box
    MsgBox "The locale ID is " & ThisDrawing.Application.LocaleId, , "LocaleID Example"
    
End Sub
Sub Example_Elevation()
    ' This example creates an associative hatch in model space.
    ' The elevation for that hatch is then changed.
    
    Dim hatchObj As AcadHatch
    Dim patternName As String
    Dim PatternType As Long
    Dim bAssociativity As Boolean
    
    ' Define the hatch
    patternName = "ANSI31"
    PatternType = 0
    bAssociativity = True
    
    ' Create the associative Hatch object
    Set hatchObj = ThisDrawing.ModelSpace.AddHatch(PatternType, patternName, bAssociativity)
    
    ' Create the outer loop for the hatch.
    ' An arc and a line are used to create a closed loop.
    
    Dim arcObj As AcadArc
    Dim lineObj As AcadLine
    Dim outerLoop(0 To 1) As AcadEntity
    Dim center(0 To 2) As Double
    Dim radius As Double
    Dim startAngle As Double
    Dim endAngle As Double
    center(0) = 5: center(1) = 3: center(2) = 0
    radius = 3
    startAngle = 0
    endAngle = 3.141592
    Set arcObj = ThisDrawing.ModelSpace.AddArc(center, radius, startAngle, endAngle)
    Set lineObj = ThisDrawing.ModelSpace.AddLine(arcObj.startPoint, arcObj.endPoint)
    
    Set outerLoop(0) = arcObj
    Set outerLoop(1) = lineObj
        
    ' Append the outer loop to the hatch object
    hatchObj.AppendOuterLoop (outerLoop)
    
    ' Append the first circle as one inner loop
    Dim innerLoop1(0) As AcadEntity
    center(0) = 5: center(1) = 4.5: center(2) = 0
    radius = 1
    Set innerLoop1(0) = ThisDrawing.ModelSpace.AddCircle(center, radius)
    hatchObj.AppendInnerLoop (innerLoop1)
    
    ' Append the second circle as the other inner loop
    Dim innerLoop2(0) As AcadEntity
    radius = 0.5
    Set innerLoop2(0) = ThisDrawing.ModelSpace.AddCircle(center, radius)
    hatchObj.AppendInnerLoop (innerLoop2)
    
    ' Change the viewing direction of the viewport to better see the elevation
    Dim NewDirection(0 To 2) As Double
    NewDirection(0) = -1: NewDirection(1) = -1: NewDirection(2) = 1
    ThisDrawing.ActiveViewport.direction = NewDirection
    ThisDrawing.ActiveViewport = ThisDrawing.ActiveViewport
    ZoomAll
    
    ' Find the current elevation for the hatch
    Dim currElevation As Double
    currElevation = hatchObj.Elevation
    MsgBox "The current elevation is " & hatchObj.Elevation, , "Elevation Example"
    
    ' Set the hatch elevation to 3
    hatchObj.Elevation = 3#
    hatchObj.Evaluate
    ZoomAll
    MsgBox "The elevation is now " & hatchObj.Elevation, , "Elevation Example"
                 
End Sub
Sub Example_CreateTypedArray()
    ' This example creates a spline from a variant arrays created
    ' from doubles using the CreateTypedArray.
    ' Note that this method must be late bound. This is done
    ' by declaring the utility object (utilObj) as Object,
    ' not as AcadUtility.
        
    Dim splineObj As AcadSpline
    Dim noOfPoints As Integer
    
    ' Even though these are arrays, they are declared as variants
    Dim startTan As Variant
    Dim endTan As Variant
    Dim fitPoints As Variant
    
    Dim utilObj As Object   ' Late bound object
    Set utilObj = ThisDrawing.Utility
    
    ' Define the spline.
    noOfPoints = 3
    utilObj.CreateTypedArray startTan, vbDouble, 0.5, 0.5, 0
    utilObj.CreateTypedArray endTan, vbDouble, 0.5, 0.5, 0
    utilObj.CreateTypedArray fitPoints, vbDouble, 0, 0, 0, 5, 5, 0, 10, 0, 0
    
    ' Create the spline
    Set splineObj = ThisDrawing.ModelSpace.AddSpline(fitPoints, startTan, endTan)
    ZoomAll
    
End Sub
Sub Example_LowerLeftCorner()
    ' This example creates a new viewport and makes it active.
    ' Then it splits the viewport into 4 windows.
    ' It then takes finds the lower left corner of each of the
    ' windows.
    Dim newViewport As AcadViewport
       
    ' Create a new viewport and make it active
    Set newViewport = ThisDrawing.Viewports.Add("TESTVIEWPORT")
    ThisDrawing.ActiveViewport = newViewport
    
    ' Split the viewport in 4 windows
    newViewport.Split acViewport4
    
    ' Make the newly split viewport active
    ThisDrawing.ActiveViewport = newViewport
    
    ' Iterate through the viewports. For each viewport,
    ' make that viewport active and display the coordinates
    ' of the lower left corner.
    Dim entry As AcadViewport
    Dim lowerLeft As Variant
    For Each entry In ThisDrawing.Viewports
        entry.GridOn = True
        ThisDrawing.ActiveViewport = entry
        lowerLeft = entry.LowerLeftCorner
        MsgBox "The lower left corner of this viewport is " & lowerLeft(0) & ", " & lowerLeft(1), , "LowerLeftCorner Example"
        entry.GridOn = False
    Next
End Sub
Sub Example_UpperRightCorner()
    ' This example creates a new viewport and makes it active.
    ' Then it splits the viewport into 4 windows.
    ' It then takes finds the upper right corner of each of the
    ' windows.
    Dim newViewport As AcadViewport
       
    ' Create a new viewport and make it active
    Set newViewport = ThisDrawing.Viewports.Add("TESTVIEWPORT")
    ThisDrawing.ActiveViewport = newViewport
    
    ' Split the viewport in 4 windows
    newViewport.Split acViewport4
    
    ' Make the newly split viewport active
    ThisDrawing.ActiveViewport = newViewport
    
    ' Iterate through the viewports. For each viewport,
    ' make that viewport active and display the coordinates
    ' of the upper right corner.
    Dim entry As AcadViewport
    Dim UpperRight As Variant
    For Each entry In ThisDrawing.Viewports
        entry.GridOn = True
        ThisDrawing.ActiveViewport = entry
        UpperRight = entry.UpperRightCorner
        MsgBox "The upper right corner of this viewport is " & UpperRight(0) & ", " & UpperRight(1), , "UpperRightCorner Example"
        entry.GridOn = False
    Next
End Sub
Sub Example_Caption()
    ' This example returns the caption for the current
    ' AutoCAD session.
    
    ' Get the Caption property
    Dim strCaption As String
    strCaption = ThisDrawing.Application.Caption
    MsgBox "The caption for this session is " & ThisDrawing.Application.Caption, , "Caption Example"
    
End Sub
Sub Example_LastHeight()
    ' This example finds the current value for LastHeight.
    ' It then changes that value, and resets it again.

    Dim txtStyleObj As AcadTextStyle
    Set txtStyleObj = ThisDrawing.ActiveTextStyle
    
    ' Set and retrieve the LastHeight property
    Dim currHeight As Double
    Dim newHeight As Double
    
    ' Retrieve current LastHeight property
    currHeight = txtStyleObj.LastHeight
    MsgBox "The current value for LastHeight is " & txtStyleObj.LastHeight, , "LastHeight Example"
    
    ' Set LastHeight to a new value
    txtStyleObj.LastHeight = 4#
    
    ' Retrieve the current LastHeight value
    newHeight = txtStyleObj.LastHeight
    MsgBox "The new value for LastHeight is " & txtStyleObj.LastHeight, , "LastHeight Example"
    
    ' Finally reset LastHeight to its default value
    txtStyleObj.LastHeight = currHeight
    MsgBox "The value for LastHeight has been reset to " & txtStyleObj.LastHeight, , "LastHeight Example"
    
End Sub
Sub Example_Layer()
    ' This example creates a new layer named "ABC" (colored red.)
    ' It then creates a circle and assigns it to layer "ABC"
 
    ' Create new layer
    Dim layerObj As AcadLayer
    Set layerObj = ThisDrawing.Layers.Add("ABC")
    layerObj.Color = acRed
    
    ' Create Circle
    Dim circleObj As AcadCircle
    Dim center(0 To 2) As Double
    Dim radius As Double
    center(0) = 3: center(1) = 3: center(2) = 0
    radius = 1.5
    Set circleObj = ThisDrawing.ModelSpace.AddCircle(center, radius)
    ZoomAll
    MsgBox "The circle has been created on layer " & circleObj.Layer, , "Layer Example"
        
    ' Set the layer of new circle to "ABC"
    circleObj.Layer = "ABC"

    ' Refresh view
    ThisDrawing.Regen (True)
    MsgBox "The circle is now on layer " & circleObj.Layer, , "Layer Example"
    
End Sub
Sub Example_Left()
    ' This example creates a new toolbar called and inserts a
    ' button into it. The toolbar is then displayed and the Left
    ' position is returned.
    ' To remove the toolbar after execution of this macro, use the Customize Menu
    ' option from the Tools menu.
    
    Dim currMenuGroup As acadMenuGroup
    Set currMenuGroup = ThisDrawing.Application.MenuGroups.Item(0)
    
    ' Create the new toolbar
    Dim newToolBar As AcadToolbar
    Set newToolBar = currMenuGroup.Toolbars.Add("TestToolbar")
    
    ' Add a button to the new toolbar.
    Dim newButton1 As AcadToolbarItem
    Dim openMacro As String
    
    ' Assign the macro string the VB equivalent of "ESC ESC _open "
    openMacro = Chr(3) & Chr(3) & Chr(95) & "open" & Chr(32)
    
    Set newButton1 = newToolBar.AddToolbarButton("", "NewButton1", "Open a file.", openMacro)
    
    
    ' Display the toolbar
    newToolBar.Visible = True
    
    'Find the Left position
    Dim currLeft As Integer
    currLeft = newToolBar.Left
    MsgBox "The current value of Left is " & newToolBar.Left, , "Left Example"
    
    ' Change the value of Left
    newToolBar.Left = currLeft + 100
    MsgBox "The new value of Left is " & newToolBar.Left, , "Left Example"
    
    ' Reset the value of Left
    newToolBar.Left = currLeft
    MsgBox "The value of Left has been reset to " & newToolBar.Left, , "Left Example"
    
End Sub
Sub Example_WindowLeft()
    ' This example finds the WindowLeft (X coordinate) of the top of the
    ' AutoCAD window. It then changes that position to be 100 more
    ' than it currently is. Finally, it resets the window to the
    ' original value.
    
    ' Find the current value of the WindowLeft property
    Dim currWindowLeft As Integer
    currWindowLeft = ThisDrawing.Application.WindowLeft
    MsgBox "The current value of WindowLeft is " & ThisDrawing.Application.WindowLeft, , "WindowLeft Example"
    
    ' Change the value of WindowLeft
    ThisDrawing.Application.WindowLeft = currWindowLeft + 100
    MsgBox "The new value of WindowLeft is " & ThisDrawing.Application.WindowLeft, , "WindowLeft Example"
    
    ' Reset the value of WindowLeft
    ThisDrawing.Application.WindowLeft = currWindowLeft
    MsgBox "The value of WindowLeft has been reset to " & ThisDrawing.Application.WindowLeft, , "WindowLeft Example"
    
End Sub
Sub Example_Top()
    ' This example creates a new toolbar called and inserts a
    ' button into it. The toolbar is then displayed and the top
    ' position is returned.
    ' To remove the toolbar after execution of this macro, use the Customize Menu
    ' option from the Tools menu.
    
    Dim currMenuGroup As acadMenuGroup
    Set currMenuGroup = ThisDrawing.Application.MenuGroups.Item(0)
    
    ' Create the new toolbar
    Dim newToolBar As AcadToolbar
    Set newToolBar = currMenuGroup.Toolbars.Add("TestToolbar")
    
    ' Add a button to the new toolbar.
    Dim newButton1 As AcadToolbarItem
    Dim openMacro As String
    
    ' Assign the macro string the VB equivalent of "ESC ESC _open "
    openMacro = Chr(3) & Chr(3) & Chr(95) & "open" & Chr(32)
    
    Set newButton1 = newToolBar.AddToolbarButton("", "NewButton1", "Open a file.", openMacro)
    
    
    ' Display the toolbar
    newToolBar.Visible = True
    
    'Find the top position
    Dim currTop As Integer
    currTop = newToolBar.top
    MsgBox "The current value of Top is " & newToolBar.top, , "Top Example"
    
    ' Change the value of Top
    newToolBar.top = currTop + 100
    MsgBox "The new value of Top is " & newToolBar.top, , "Top Example"
    
    ' Reset the value of Top
    newToolBar.top = currTop
    MsgBox "The value of Top has been reset to " & newToolBar.top, , "Top Example"
    
End Sub
Sub Example_WindowTop()
    ' This example finds the WindowTop (X coordinate) of the WindowTop of the
    ' AutoCAD window. It then changes that position to be 100 more
    ' than it currently is. Finally, it resets the window to the
    ' original value.
    
    ' Find the current value of the WindowTop property
    Dim currWindowTop As Integer
    currWindowTop = ThisDrawing.Application.WindowTop
    MsgBox "The current value of WindowTop is " & ThisDrawing.Application.WindowTop, , "WindowTop Example"
    
    ' Change the value of WindowTop
    ThisDrawing.Application.WindowTop = currWindowTop + 100
    MsgBox "The new value of WindowTop is " & ThisDrawing.Application.WindowTop, , "WindowTop Example"
    
    ' Reset the value of WindowTop
    ThisDrawing.Application.WindowTop = currWindowTop
    MsgBox "The value of WindowTop has been reset to " & ThisDrawing.Application.WindowTop, , "WindowTop Example"
    
End Sub
Sub Example_Limits()
    ' This example finds the current limits for the drawing.
    ' It then changes the limits for the drawing. The grid
    ' is turned on to show the limits.
    
    ' Turn on the grid for the active viewport
    ThisDrawing.ActiveViewport.GridOn = True
    ThisDrawing.ActiveViewport = ThisDrawing.ActiveViewport
    
    ' Find the current limits
    Dim currLimits As Variant
    currLimits = ThisDrawing.Limits
    MsgBox "The current drawing limits are " & vbCrLf _
           & "Lower-left corner " & ThisDrawing.Limits(0) & ", " & ThisDrawing.Limits(1) & vbCrLf _
           & "Upper-right corner " & ThisDrawing.Limits(2) & ", " & ThisDrawing.Limits(3), , "Limits Example"
           
    ' Change the limits
    Dim newLimits(0 To 3) As Double
    newLimits(0) = 2#: newLimits(1) = 2#: newLimits(2) = 4#: newLimits(3) = 4#
    ThisDrawing.Limits = newLimits
    ThisDrawing.Regen acActiveViewport
    MsgBox "The new drawing limits are " & vbCrLf _
           & "Lower-left corner " & ThisDrawing.Limits(0) & ", " & ThisDrawing.Limits(1) & vbCrLf _
           & "Upper-right corner " & ThisDrawing.Limits(2) & ", " & ThisDrawing.Limits(3), , "Limits Example"
    
    ' Reset the drawing limits
    ThisDrawing.Limits = currLimits
    ThisDrawing.Regen acActiveViewport
    MsgBox "The drawing limits have been reset to " & vbCrLf _
           & "Lower-left corner " & ThisDrawing.Limits(0) & ", " & ThisDrawing.Limits(1) & vbCrLf _
           & "Upper-right corner " & ThisDrawing.Limits(2) & ", " & ThisDrawing.Limits(3), , "Limits Example"
End Sub
Sub Example_Linetype()
    ' This example searches for the linetype DashDot. If it is
    ' not found, it is added from the acad.lin file. Then a
    ' line is created and changed to the DashDot linetype.
    
    ' Search the linetypes collection for the DashDot linetype.
    Dim entry As AcadLineType
    Dim found As Boolean
    found = False
    For Each entry In ThisDrawing.Linetypes
        If StrComp(entry.name, "DASHDOT", 1) = 0 Then
            found = True
            Exit For
        End If
    Next
    If Not (found) Then ThisDrawing.Linetypes.Load "DASHDOT", "acad.lin"
        
    ' Create the line
    Dim lineObj As AcadLine
    Dim startPoint(0 To 2) As Double
    Dim endPoint(0 To 2) As Double
    startPoint(0) = 1#: startPoint(1) = 1#: startPoint(2) = 0#
    endPoint(0) = 4#: endPoint(1) = 4#: endPoint(2) = 0#
    Set lineObj = ThisDrawing.ModelSpace.AddLine(startPoint, endPoint)
    
    ' Change the linetype of the line
    lineObj.Linetype = "DASHDOT"
    ZoomAll
    
End Sub
Sub Example_Load()
    ' This example attempts to load the linetype "CENTER" from
    ' the acad.lin file. If the linetype already exists, then
    ' a message is displayed.
    
    Dim linetypeName As String
    linetypeName = "CENTER"
    
    ' Load "CENTER" line type from acad.lin file
    On Error Resume Next    ' trap any load errors
    ThisDrawing.Linetypes.Load linetypeName, "acad.lin"
    
    ' If the name already exists, then notify user
    If Err.Description = "Duplicate record name" Then
        MsgBox "A line type named '" & linetypeName & "' already exists.", , "Load Example"
    End If
    
End Sub
Sub Example_Add3DMesh()
    ' This example creates a 4 X 4 polygonmesh in model space.
    Dim meshObj As AcadPolygonMesh
    Dim mSize, nSize, count As Integer
    Dim points(0 To 47) As Double
    
    ' create the matrix of points
    points(0) = 0: points(1) = 0: points(2) = 0
    points(3) = 2: points(4) = 0: points(5) = 1
    points(6) = 4: points(7) = 0: points(8) = 0
    points(9) = 6: points(10) = 0: points(11) = 1
    points(12) = 0: points(13) = 2: points(14) = 0
    points(15) = 2: points(16) = 2: points(17) = 1
    points(18) = 4: points(19) = 2: points(20) = 0
    points(21) = 6: points(22) = 2: points(23) = 1
    points(24) = 0: points(25) = 4: points(26) = 0
    points(27) = 2: points(28) = 4: points(29) = 1
    points(30) = 4: points(31) = 4: points(32) = 0
    points(33) = 6: points(34) = 4: points(35) = 0
    points(36) = 0: points(37) = 6: points(38) = 0
    points(39) = 2: points(40) = 6: points(41) = 1
    points(42) = 4: points(43) = 6: points(44) = 0
    points(45) = 6: points(46) = 6: points(47) = 0
    
    mSize = 4: nSize = 4
    
    ' creates a 3Dmesh in model space
    Set meshObj = ThisDrawing.ModelSpace.Add3DMesh(mSize, nSize, points)
    
    ' Change the viewing direction of the viewport to better see the cylinder
    Dim NewDirection(0 To 2) As Double
    NewDirection(0) = -1: NewDirection(1) = -1: NewDirection(2) = 1
    ThisDrawing.ActiveViewport.direction = NewDirection
    ThisDrawing.ActiveViewport = ThisDrawing.ActiveViewport
    ZoomAll
    
End Sub
Sub Example_MClose()
    ' This example creates a 4 X 4 polygonmesh in model space.
    ' It then closes the polymesh in the 'M' direction.
    Dim meshObj As AcadPolygonMesh
    Dim mSize, nSize, count As Integer
    Dim points(0 To 47) As Double
    
    ' create the matrix of points
    points(0) = 2: points(1) = 2: points(2) = 1
    points(3) = 2.5: points(4) = 2: points(5) = 0
    points(6) = 5: points(7) = 2: points(8) = 0
    points(9) = 5.5: points(10) = 2: points(11) = 1
    points(12) = 2: points(13) = 4: points(14) = 0.5
    points(15) = 2.5: points(16) = 4: points(17) = 0
    points(18) = 5: points(19) = 4: points(20) = 0
    points(21) = 5.5: points(22) = 4: points(23) = 0.5
    points(24) = 2: points(25) = 6: points(26) = 0.5
    points(27) = 2.5: points(28) = 6: points(29) = 0
    points(30) = 5: points(31) = 6: points(32) = 0
    points(33) = 5.5: points(34) = 6: points(35) = 0.5
    points(36) = 2: points(37) = 8: points(38) = 1
    points(39) = 2.5: points(40) = 8: points(41) = 0
    points(42) = 5: points(43) = 8: points(44) = 0
    points(45) = 5.5: points(46) = 8: points(47) = 1
    
    mSize = 4: nSize = 4
    
    ' create a 3Dmesh in model space
    Set meshObj = ThisDrawing.ModelSpace.Add3DMesh(mSize, nSize, points)
    
    ' Change the viewing direction of the viewport to better see the cylinder
    Dim NewDirection(0 To 2) As Double
    NewDirection(0) = -1: NewDirection(1) = -1: NewDirection(2) = 1
    ThisDrawing.ActiveViewport.direction = NewDirection
    ThisDrawing.ActiveViewport = ThisDrawing.ActiveViewport
    ZoomAll
    
    ' Close the polymesh in the 'M' direction
    MsgBox "The polymesh is " & IIf(meshObj.MClose, "closed", "open") & " in the 'M' direction.", , "MClose Example"
    meshObj.MClose = True
    ThisDrawing.Regen acActiveViewport
    MsgBox "The polymesh is " & IIf(meshObj.MClose, "closed", "open") & " in the 'M' direction.", , "MClose Example"

End Sub
Sub Example_NClose()
    ' This example creates a 4 X 4 polygonmesh in model space.
    ' It then closes the polymesh in the 'N' direction.
    Dim meshObj As AcadPolygonMesh
    Dim mSize, nSize, count As Integer
    Dim points(0 To 47) As Double
    
    ' create the matrix of points
    points(0) = 2: points(1) = 2: points(2) = 1
    points(3) = 2.5: points(4) = 2: points(5) = 0
    points(6) = 5: points(7) = 2: points(8) = 0
    points(9) = 5.5: points(10) = 2: points(11) = 1
    points(12) = 2: points(13) = 4: points(14) = 0.5
    points(15) = 2.5: points(16) = 4: points(17) = 0
    points(18) = 5: points(19) = 4: points(20) = 0
    points(21) = 5.5: points(22) = 4: points(23) = 0.5
    points(24) = 2: points(25) = 6: points(26) = 0.5
    points(27) = 2.5: points(28) = 6: points(29) = 0
    points(30) = 5: points(31) = 6: points(32) = 0
    points(33) = 5.5: points(34) = 6: points(35) = 0.5
    points(36) = 2: points(37) = 8: points(38) = 1
    points(39) = 2.5: points(40) = 8: points(41) = 0
    points(42) = 5: points(43) = 8: points(44) = 0
    points(45) = 5.5: points(46) = 8: points(47) = 1
    
    mSize = 4: nSize = 4
    
    ' create a 3Dmesh in model space
    Set meshObj = ThisDrawing.ModelSpace.Add3DMesh(mSize, nSize, points)
    
    ' Change the viewing direction of the viewport to better see the cylinder
    Dim NewDirection(0 To 2) As Double
    NewDirection(0) = -1: NewDirection(1) = -1: NewDirection(2) = 1
    ThisDrawing.ActiveViewport.direction = NewDirection
    ThisDrawing.ActiveViewport = ThisDrawing.ActiveViewport
    ZoomAll
    
    ' Close the polymesh in the 'M' direction
    MsgBox "The polymesh is " & IIf(meshObj.NClose, "closed", "open") & " in the 'N' direction.", , "NClose Example"
    meshObj.NClose = True
    ThisDrawing.Regen acActiveViewport
    MsgBox "The polymesh is " & IIf(meshObj.NClose, "closed", "open") & " in the 'N' direction.", , "NClose Example"

End Sub
Sub Example_MDensity()
    ' This example creates a 4 X 4 polygonmesh in model space.
    ' It then changes the type of polymesh, and finds the
    ' number of points in the 'M' direction.
    Dim meshObj As AcadPolygonMesh
    Dim mSize, nSize, count As Integer
    Dim points(0 To 47) As Double
    
    ' create the matrix of points
    points(0) = 0: points(1) = 0: points(2) = 0
    points(3) = 2: points(4) = 0: points(5) = 1
    points(6) = 4: points(7) = 0: points(8) = 0
    points(9) = 6: points(10) = 0: points(11) = 1
    points(12) = 0: points(13) = 2: points(14) = 0
    points(15) = 2: points(16) = 2: points(17) = 1
    points(18) = 4: points(19) = 2: points(20) = 0
    points(21) = 6: points(22) = 2: points(23) = 1
    points(24) = 0: points(25) = 4: points(26) = 0
    points(27) = 2: points(28) = 4: points(29) = 1
    points(30) = 4: points(31) = 4: points(32) = 0
    points(33) = 6: points(34) = 4: points(35) = 0
    points(36) = 0: points(37) = 6: points(38) = 0
    points(39) = 2: points(40) = 6: points(41) = 1
    points(42) = 4: points(43) = 6: points(44) = 0
    points(45) = 6: points(46) = 6: points(47) = 0
      
    mSize = 4: nSize = 4
    
    ' Create a 3Dmesh in model space
    Set meshObj = ThisDrawing.ModelSpace.Add3DMesh(mSize, nSize, points)
    
    ' Change the viewing direction of the viewport to better see the polymesh
    Dim NewDirection(0 To 2) As Double
    NewDirection(0) = -1: NewDirection(1) = -1: NewDirection(2) = 1
    ThisDrawing.ActiveViewport.direction = NewDirection
    ThisDrawing.ActiveViewport = ThisDrawing.ActiveViewport
    ZoomAll
    
    ' Change the type of mesh. (MDensity is not valid for acSimpleMesh type.)
    meshObj.Type = acQuadSurfaceMesh
    meshObj.Update
    ThisDrawing.Regen acActiveViewport

    ' Find the MDensity for the mesh
    Dim currDensity As Integer
    currDensity = meshObj.MDensity
    MsgBox "The MDensity for the mesh is " & meshObj.MDensity, , "MDensity Example"
    
End Sub
Sub Example_NDensity()
    ' This example creates a 4 X 4 polygonmesh in model space.
    ' It then changes the type of polymesh, and finds the
    ' number of points in the 'N' direction.
    Dim meshObj As AcadPolygonMesh
    Dim mSize, nSize, count As Integer
    Dim points(0 To 47) As Double
    
    ' create the matrix of points
    points(0) = 0: points(1) = 0: points(2) = 0
    points(3) = 2: points(4) = 0: points(5) = 1
    points(6) = 4: points(7) = 0: points(8) = 0
    points(9) = 6: points(10) = 0: points(11) = 1
    points(12) = 0: points(13) = 2: points(14) = 0
    points(15) = 2: points(16) = 2: points(17) = 1
    points(18) = 4: points(19) = 2: points(20) = 0
    points(21) = 6: points(22) = 2: points(23) = 1
    points(24) = 0: points(25) = 4: points(26) = 0
    points(27) = 2: points(28) = 4: points(29) = 1
    points(30) = 4: points(31) = 4: points(32) = 0
    points(33) = 6: points(34) = 4: points(35) = 0
    points(36) = 0: points(37) = 6: points(38) = 0
    points(39) = 2: points(40) = 6: points(41) = 1
    points(42) = 4: points(43) = 6: points(44) = 0
    points(45) = 6: points(46) = 6: points(47) = 0
      
    mSize = 4: nSize = 4
    
    ' Create a 3Dmesh in model space
    Set meshObj = ThisDrawing.ModelSpace.Add3DMesh(mSize, nSize, points)
    
    ' Change the viewing direction of the viewport to better see the polymesh
    Dim NewDirection(0 To 2) As Double
    NewDirection(0) = -1: NewDirection(1) = -1: NewDirection(2) = 1
    ThisDrawing.ActiveViewport.direction = NewDirection
    ThisDrawing.ActiveViewport = ThisDrawing.ActiveViewport
    ZoomAll
    
    ' Change the type of mesh. (NDensity is not valid for acSimpleMesh type.)
    meshObj.Type = acQuadSurfaceMesh
    meshObj.Update
    ThisDrawing.Regen acActiveViewport

    ' Find the NDensity for the mesh
    Dim currDensity As Integer
    currDensity = meshObj.NDensity
    MsgBox "The NDensity for the mesh is " & meshObj.NDensity, , "NDensity Example"
    
End Sub
Sub Example_NVertexCount()
    ' This example creates a 4 X 4 polygonmesh in model space.
    ' It then finds the number of points in the 'N' direction.
    Dim meshObj As AcadPolygonMesh
    Dim mSize, nSize, count As Integer
    Dim points(0 To 47) As Double
    
    ' create the matrix of points
    points(0) = 0: points(1) = 0: points(2) = 0
    points(3) = 2: points(4) = 0: points(5) = 1
    points(6) = 4: points(7) = 0: points(8) = 0
    points(9) = 6: points(10) = 0: points(11) = 1
    points(12) = 0: points(13) = 2: points(14) = 0
    points(15) = 2: points(16) = 2: points(17) = 1
    points(18) = 4: points(19) = 2: points(20) = 0
    points(21) = 6: points(22) = 2: points(23) = 1
    points(24) = 0: points(25) = 4: points(26) = 0
    points(27) = 2: points(28) = 4: points(29) = 1
    points(30) = 4: points(31) = 4: points(32) = 0
    points(33) = 6: points(34) = 4: points(35) = 0
    points(36) = 0: points(37) = 6: points(38) = 0
    points(39) = 2: points(40) = 6: points(41) = 1
    points(42) = 4: points(43) = 6: points(44) = 0
    points(45) = 6: points(46) = 6: points(47) = 0
      
    mSize = 4: nSize = 4
    
    ' Create a 3Dmesh in model space
    Set meshObj = ThisDrawing.ModelSpace.Add3DMesh(mSize, nSize, points)
    
    ' Change the viewing direction of the viewport to better see the polymesh
    Dim NewDirection(0 To 2) As Double
    NewDirection(0) = -1: NewDirection(1) = -1: NewDirection(2) = 1
    ThisDrawing.ActiveViewport.direction = NewDirection
    ThisDrawing.ActiveViewport = ThisDrawing.ActiveViewport
    ZoomAll
    
    ' Find the NVertexCount for the mesh
    Dim currVertexCount As Integer
    currVertexCount = meshObj.NVertexCount
    MsgBox "The NVertexCount for the mesh is " & meshObj.NVertexCount, , "NVertexCount Example"
    
End Sub
Sub Example_MVertexCount()
    ' This example creates a 4 X 4 polygonmesh in model space.
    ' It then finds the number of points in the 'M' direction.
    Dim meshObj As AcadPolygonMesh
    Dim mSize, nSize, count As Integer
    Dim points(0 To 47) As Double
    
    ' create the matrix of points
    points(0) = 0: points(1) = 0: points(2) = 0
    points(3) = 2: points(4) = 0: points(5) = 1
    points(6) = 4: points(7) = 0: points(8) = 0
    points(9) = 6: points(10) = 0: points(11) = 1
    points(12) = 0: points(13) = 2: points(14) = 0
    points(15) = 2: points(16) = 2: points(17) = 1
    points(18) = 4: points(19) = 2: points(20) = 0
    points(21) = 6: points(22) = 2: points(23) = 1
    points(24) = 0: points(25) = 4: points(26) = 0
    points(27) = 2: points(28) = 4: points(29) = 1
    points(30) = 4: points(31) = 4: points(32) = 0
    points(33) = 6: points(34) = 4: points(35) = 0
    points(36) = 0: points(37) = 6: points(38) = 0
    points(39) = 2: points(40) = 6: points(41) = 1
    points(42) = 4: points(43) = 6: points(44) = 0
    points(45) = 6: points(46) = 6: points(47) = 0
      
    mSize = 4: nSize = 4
    
    ' Create a 3Dmesh in model space
    Set meshObj = ThisDrawing.ModelSpace.Add3DMesh(mSize, nSize, points)
    
    ' Change the viewing direction of the viewport to better see the polymesh
    Dim NewDirection(0 To 2) As Double
    NewDirection(0) = -1: NewDirection(1) = -1: NewDirection(2) = 1
    ThisDrawing.ActiveViewport.direction = NewDirection
    ThisDrawing.ActiveViewport = ThisDrawing.ActiveViewport
    ZoomAll
    
    ' Find the MVertexCount for the mesh
    Dim currVertexCount As Integer
    currVertexCount = meshObj.MVertexCount
    MsgBox "The MVertexCount for the mesh is " & meshObj.MVertexCount, , "MVertexCount Example"
    
End Sub
Sub Example_ModelSpace()
    ' This example adds a line and a circle to model space.
    ' The line is added using a user-defined variable representing
    ' the model space. The circle is added without using the
    ' user-defined variable. Either use of the ModelSpace
    ' property is valid.
    
    ' Define the line
    Dim lineObj As AcadLine
    Dim startPoint(0 To 2) As Double
    Dim endPoint(0 To 2) As Double
    startPoint(0) = 0: startPoint(1) = 0: startPoint(2) = 0
    endPoint(0) = 4: endPoint(1) = 4: endPoint(2) = 0
    
    ' Add the line to model space using the mspace variable
    Dim mspace As AcadModelSpace
    Set mspace = ThisDrawing.ModelSpace
    Set lineObj = mspace.AddLine(startPoint, endPoint)
    
    ' Define a circle
    Dim circleObj As AcadCircle
    Dim center(0 To 2) As Double
    Dim radius As Double
    center(0) = 4: center(1) = 4: center(2) = 0
    radius = 1
    
    ' Add the circle to modelspace without using the mspace variable
    Set circleObj = ThisDrawing.ModelSpace.AddCircle(center, radius)
    
    ZoomAll
    
End Sub
Sub Example_Name()
    ' This example creates a new layer. It then
    ' changes the name of that layer.
    
    ' Add the new layer
    Dim layerObj As AcadLayer
    Set layerObj = ThisDrawing.Layers.Add("NewLayer")
    
    ' Find the name of the new layer
    Dim layerName As String
    layerName = layerObj.name
    MsgBox "A new layer was created with the name: " & layerObj.name, , "Name Example"
    
    ' Change the name of the layer to "TEST". Note that behaviour of
    ' following code will be different for different object. In some cases such as
    ' Block reference, changing the name means referencing to a new Block and therefore
    ' a Block with named "TEST" should already exist otherwise an error will be
    ' returned.
    layerObj.name = "TEST"
    layerName = layerObj.name
    MsgBox "The new name of the layer is: " & layerObj.name, , "Name Example"
    
End Sub
Sub Example_Normal()
    ' This example creates a circle in model space.
    ' It then finds the current normal to that circle
    ' and changes the normal.
    
    ' Define a circle
    Dim circleObj As AcadCircle
    Dim center(0 To 2) As Double
    Dim radius As Double
    center(0) = 4: center(1) = 4: center(2) = 0
    radius = 1
    
    ' Add the circle to modelspace
    Set circleObj = ThisDrawing.ModelSpace.AddCircle(center, radius)
    ZoomAll
    
    ' Find the normal for the circle
    Dim currNormal As Variant
    currNormal = circleObj.Normal
    MsgBox "The current normal for the circle is " & circleObj.Normal(0) & ", " & circleObj.Normal(1) & ", " & circleObj.Normal(2), , "Normal Example"
    
    ' Change the normal for the circle
    Dim newNormal(0 To 2) As Double
    newNormal(0) = 1: newNormal(1) = 1: newNormal(2) = -1
    circleObj.Normal = newNormal
    circleObj.Update
    MsgBox "The current normal for the circle is " & circleObj.Normal(0) & ", " & circleObj.Normal(1) & ", " & circleObj.Normal(2), , "Normal Example"
    
End Sub
Sub Example_ObjectSnapMode()
    ' This example toggles the setting of the Object Snap Mode.
    
    Dim currObjSnapMode As Boolean
    
    ' Get the current ObjectSnapMode value
    currObjSnapMode = ThisDrawing.ObjectSnapMode
    MsgBox "The object snap mode is currently " & IIf(ThisDrawing.ObjectSnapMode, "on.", "off."), , "ObjectSnapMode Example"
    
    ' Change the default ObjectSnapMode value
    ThisDrawing.ObjectSnapMode = Not (currObjSnapMode)
    MsgBox "The object snap mode is now " & IIf(ThisDrawing.ObjectSnapMode, "on.", "off."), , "ObjectSnapMode Example"

End Sub
Sub Example_Origin()
    ' This example creates a UCS and returns its origin.

    Dim viewportObj As AcadViewport
    
    ' Set the viewportObj variable to the activeviewport
    Set viewportObj = ThisDrawing.ActiveViewport
    
    ' Create a new UCS with origin 2, 2, 0
    Dim ucsObj As AcadUCS
    Dim origin(0 To 2) As Double
    Dim xAxisPoint(0 To 2) As Double
    Dim yAxisPoint(0 To 2) As Double
    
    origin(0) = 2: origin(1) = 2: origin(2) = 0
    xAxisPoint(0) = 3: xAxisPoint(1) = 2: xAxisPoint(2) = 0
    yAxisPoint(0) = 2: yAxisPoint(1) = 3: yAxisPoint(2) = 0
    
    Set ucsObj = ThisDrawing.UserCoordinateSystems.Add(origin, xAxisPoint, yAxisPoint, "UCS1")
    ThisDrawing.ActiveUCS = ucsObj
    viewportObj.UCSIconOn = True
    viewportObj.UCSIconAtOrigin = True
    ThisDrawing.ActiveViewport = viewportObj
    
    ' Display the current origin for the new UCS
    MsgBox "The origin of the UCS is: " & ucsObj.origin(0) & ", " & ucsObj.origin(1) & ", " & ucsObj.origin(2), , "Origin Example"

    ' Change the origin of the UCS
    origin(0) = 4: origin(1) = 4: origin(2) = 0
    ucsObj.origin = origin
    
    ' Reset the active UCS and viewport to see the change
    ThisDrawing.ActiveUCS = ucsObj
    ThisDrawing.ActiveViewport = viewportObj
    
    MsgBox "The origin of the UCS is now: " & ucsObj.origin(0) & ", " & ucsObj.origin(1) & ", " & ucsObj.origin(2), , "Origin Example"
    
End Sub
Sub Example_PaperSpace()
    ' This example sets the variable pspace to the paperspace entity collection.
    
    Dim pspace As AcadPaperSpace
    Set pspace = ThisDrawing.PaperSpace
    
End Sub
Sub Example_Path()
    ' This example returns the path of the drawing and application.
    
    ' If the drawing has not been saved, the path of the
    ' document will be blank.
    Dim docPath As String
    docPath = ThisDrawing.Path
    MsgBox "The Path of the current drawing is " & docPath, , "Path Example"
    
    Dim appPath As String
    appPath = ThisDrawing.Application.Path
    MsgBox "The Path of the current appication is " & appPath, , "Path Example"
    
End Sub
Sub Example_PatternName()
    ' This example creates an associative hatch in model space.
    ' The name of the hatch pattern is then returned.
    
    Dim hatchObj As AcadHatch
    Dim patternName As String
    Dim PatternType As Long
    Dim bAssociativity As Boolean
    
    ' Define the hatch
    patternName = "ANSI31"
    PatternType = 0
    bAssociativity = True
    
    ' Create the associative Hatch object
    Set hatchObj = ThisDrawing.ModelSpace.AddHatch(PatternType, patternName, bAssociativity)
    
    ' Create the outer loop for the hatch.
    ' An arc and a line are used to create a closed loop.
    
    Dim outerLoop(0 To 1) As AcadEntity
    Dim center(0 To 2) As Double
    Dim radius As Double
    Dim startAngle As Double
    Dim endAngle As Double
    center(0) = 5: center(1) = 3: center(2) = 0
    radius = 3
    startAngle = 0
    endAngle = 3.141592
    Set outerLoop(0) = ThisDrawing.ModelSpace.AddArc(center, radius, startAngle, endAngle)
    Set outerLoop(1) = ThisDrawing.ModelSpace.AddLine(outerLoop(0).startPoint, outerLoop(0).endPoint)
        
    ' Append the outer loop to the hatch object
    hatchObj.AppendOuterLoop (outerLoop)
    
    ' Append the first circle as one inner loop
    Dim innerLoop1(0) As AcadEntity
    center(0) = 5: center(1) = 4.5: center(2) = 0
    radius = 1
    Set innerLoop1(0) = ThisDrawing.ModelSpace.AddCircle(center, radius)
    hatchObj.AppendInnerLoop (innerLoop1)
    
    ' Append the second circle as the other inner loop
    Dim innerLoop2(0) As AcadEntity
    radius = 0.5
    Set innerLoop2(0) = ThisDrawing.ModelSpace.AddCircle(center, radius)
    hatchObj.AppendInnerLoop (innerLoop2)
    
    ' Evaluate and display the hatch
    hatchObj.Evaluate
    ThisDrawing.Regen True
    
    ' Find the name of the hatch pattern
    patternName = hatchObj.patternName
    MsgBox "The name of the hatch pattern is " & hatchObj.patternName, , "patternName Example"
                   
End Sub
Sub Example_PatternSpace()
    ' This example creates an associative hatch in model space.
    ' The spacing of the hatch pattern is then returned and changed.
    
    Dim hatchObj As AcadHatch
    Dim patternName As String
    Dim PatternType As Long
    Dim bAssociativity As Boolean
    
    ' Define the hatch
    patternName = "ANSI31"
    PatternType = 0
    bAssociativity = True
    
    ' Create the associative Hatch object
    Set hatchObj = ThisDrawing.ModelSpace.AddHatch(PatternType, patternName, bAssociativity)
    
    ' Create the outer loop for the hatch.
    ' An arc and a line are used to create a closed loop.
    Dim outerLoop(0 To 1) As AcadEntity
    Dim center(0 To 2) As Double
    Dim radius As Double
    Dim startAngle As Double
    Dim endAngle As Double
    center(0) = 5: center(1) = 3: center(2) = 0
    radius = 3
    startAngle = 0
    endAngle = 3.141592
    Set outerLoop(0) = ThisDrawing.ModelSpace.AddArc(center, radius, startAngle, endAngle)
    Set outerLoop(1) = ThisDrawing.ModelSpace.AddLine(outerLoop(0).startPoint, outerLoop(0).endPoint)
        
    ' Append the outer loop to the hatch object
    hatchObj.AppendOuterLoop (outerLoop)
    
    ' Append the first circle as one inner loop
    Dim innerLoop1(0) As AcadEntity
    center(0) = 5: center(1) = 4.5: center(2) = 0
    radius = 1
    Set innerLoop1(0) = ThisDrawing.ModelSpace.AddCircle(center, radius)
    hatchObj.AppendInnerLoop (innerLoop1)
    
    ' Append the second circle as the other inner loop
    Dim innerLoop2(0) As AcadEntity
    radius = 0.5
    Set innerLoop2(0) = ThisDrawing.ModelSpace.AddCircle(center, radius)
    hatchObj.AppendInnerLoop (innerLoop2)
    
    ' Evaluate and display the hatch
    hatchObj.Evaluate
    ThisDrawing.Regen True
    
    ' Find the space of the hatch pattern
    Dim patternSpace As Double
    patternSpace = hatchObj.patternSpace
    MsgBox "The spacing of the hatch pattern is " & hatchObj.patternSpace, , "PatternSpace Example"
                  
    ' Change the spacing of the hatch pattern
    hatchObj.patternSpace = patternSpace + 2
    hatchObj.Evaluate
    ThisDrawing.Regen True
    MsgBox "The spacing of the hatch pattern is now " & hatchObj.patternSpace, , "PatternSpace Example"
    
End Sub
Sub Example_PatternScale()
    ' This example creates an associative hatch in model space.
    ' The scale of the hatch pattern is then returned and changed.
    
    Dim hatchObj As AcadHatch
    Dim patternName As String
    Dim PatternType As Long
    Dim bAssociativity As Boolean
    
    ' Define the hatch
    patternName = "ANSI31"
    PatternType = 0
    bAssociativity = True
    
    ' Create the associative Hatch object
    Set hatchObj = ThisDrawing.ModelSpace.AddHatch(PatternType, patternName, bAssociativity)
    
    ' Create the outer loop for the hatch.
    ' An arc and a line are used to create a closed loop.
    Dim outerLoop(0 To 1) As AcadEntity
    Dim center(0 To 2) As Double
    Dim radius As Double
    Dim startAngle As Double
    Dim endAngle As Double
    center(0) = 5: center(1) = 3: center(2) = 0
    radius = 3
    startAngle = 0
    endAngle = 3.141592
    Set outerLoop(0) = ThisDrawing.ModelSpace.AddArc(center, radius, startAngle, endAngle)
    Set outerLoop(1) = ThisDrawing.ModelSpace.AddLine(outerLoop(0).startPoint, outerLoop(0).endPoint)
        
    ' Append the outer loop to the hatch object
    hatchObj.AppendOuterLoop (outerLoop)
    
    ' Append the first circle as one inner loop
    Dim innerLoop1(0) As AcadEntity
    center(0) = 5: center(1) = 4.5: center(2) = 0
    radius = 1
    Set innerLoop1(0) = ThisDrawing.ModelSpace.AddCircle(center, radius)
    hatchObj.AppendInnerLoop (innerLoop1)
    
    ' Append the second circle as the other inner loop
    Dim innerLoop2(0) As AcadEntity
    radius = 0.5
    Set innerLoop2(0) = ThisDrawing.ModelSpace.AddCircle(center, radius)
    hatchObj.AppendInnerLoop (innerLoop2)
    
    ' Evaluate and display the hatch
    hatchObj.Evaluate
    ThisDrawing.Regen True
    
    ' Find the scale of the hatch pattern
    Dim PatternScale As Double
    PatternScale = hatchObj.PatternScale
    MsgBox "The scale of the hatch pattern is " & hatchObj.PatternScale, , "PatternScale Example"
                  
    ' Change the scale of the hatch pattern
    hatchObj.PatternScale = PatternScale + 2
    hatchObj.Evaluate
    ThisDrawing.Regen True
    MsgBox "The scale of the hatch pattern is now " & hatchObj.PatternScale, , "PatternScale Example"
    
End Sub
Sub Example_PatternType()
    ' This example creates an associative hatch in model space.
    ' The type of the hatch pattern is then returned.
    
    Dim hatchObj As AcadHatch
    Dim patternName As String
    Dim PatternType As Long
    Dim bAssociativity As Boolean
    
    ' Define the hatch
    patternName = "ANSI31"
    PatternType = acHatchPatternTypePreDefined
    bAssociativity = True
    
    ' Create the associative Hatch object
    Set hatchObj = ThisDrawing.ModelSpace.AddHatch(PatternType, patternName, bAssociativity)
    
    ' Create the outer loop for the hatch.
    ' An arc and a line are used to create a closed loop.
    Dim outerLoop(0 To 1) As AcadEntity
    Dim center(0 To 2) As Double
    Dim radius As Double
    Dim startAngle As Double
    Dim endAngle As Double
    center(0) = 5: center(1) = 3: center(2) = 0
    radius = 3
    startAngle = 0
    endAngle = 3.141592
    Set outerLoop(0) = ThisDrawing.ModelSpace.AddArc(center, radius, startAngle, endAngle)
    Set outerLoop(1) = ThisDrawing.ModelSpace.AddLine(outerLoop(0).startPoint, outerLoop(0).endPoint)
        
    ' Append the outer loop to the hatch object
    hatchObj.AppendOuterLoop (outerLoop)
    
    ' Append the first circle as one inner loop
    Dim innerLoop1(0) As AcadEntity
    center(0) = 5: center(1) = 4.5: center(2) = 0
    radius = 1
    Set innerLoop1(0) = ThisDrawing.ModelSpace.AddCircle(center, radius)
    hatchObj.AppendInnerLoop (innerLoop1)
    
    ' Append the second circle as the other inner loop
    Dim innerLoop2(0) As AcadEntity
    radius = 0.5
    Set innerLoop2(0) = ThisDrawing.ModelSpace.AddCircle(center, radius)
    hatchObj.AppendInnerLoop (innerLoop2)
    
    ' Evaluate and display the hatch
    hatchObj.Evaluate
    ThisDrawing.Regen True
    
    ' Find the type of hatch
    PatternType = hatchObj.PatternType
    MsgBox "The type of hatch pattern is " & Choose(hatchObj.PatternType + 1, "acHatchPatternTypeUserDefined", "acHatchPatternTypePreDefined", "acHatchPatternTypeCustomDefined"), , "PatternType Example"
                      
End Sub
Sub Example_Plot()
    ' This example sends a plot of the current drawing
    ' to a file.
    
    ' Define the plot variable
    Dim currentPlot As AcadPlot
    Set currentPlot = ThisDrawing.Plot
    
    ' Define the output file name.
    ' Use "" to use the drawing name as the file name.
    ' Note: if the filename exists an error will be generated.
    Dim plotFileName As String
    plotFileName = "MyPlot"
    
    currentPlot.PlotToFile (plotFileName)
    
End Sub
Sub Example_Perimeter()
    ' This example creates a region from an arc and a line.
    ' It then returns the length of the perimeter of the region.
    Dim curves(0 To 1) As AcadEntity
    Dim arcObj As AcadArc
    Dim lineObj As AcadLine
    
    ' Create the arc and line
    Dim centerPoint(0 To 2) As Double
    Dim radius As Double
    Dim startAngle As Double
    Dim endAngle As Double
    centerPoint(0) = 5#: centerPoint(1) = 3#: centerPoint(2) = 0#
    radius = 2#
    startAngle = 0
    endAngle = 3.141592
    Set arcObj = ThisDrawing.ModelSpace.AddArc(centerPoint, radius, startAngle, endAngle)
    Set lineObj = ThisDrawing.ModelSpace.AddLine(arcObj.startPoint, arcObj.endPoint)
    Set curves(0) = arcObj
    Set curves(1) = lineObj
    
    ' Create the region
    Dim regionObj As Variant
    regionObj = ThisDrawing.ModelSpace.AddRegion(curves)
    ZoomAll
    
    ' Find the perimeter of the region.
    Dim perimeter As Double
    perimeter = regionObj(0).perimeter
    MsgBox "The perimeter of the region is " & regionObj(0).perimeter, , "Perimeter Example"
    
End Sub
Sub Example_Radius()
    ' This example creates an arc in model space.
    ' It then returns the radius of the arc.
    Dim arcObj As AcadArc
    Dim centerPoint(0 To 2) As Double
    Dim radius As Double
    Dim startAngleInDegree As Double
    Dim endAngleInDegree As Double
    
    ' Define the circle
    centerPoint(0) = 0#: centerPoint(1) = 0#: centerPoint(2) = 0#
    radius = 5#
    startAngleInDegree = 10#
    endAngleInDegree = 230#
    
    ' Convert the angles in degrees to angles in radians
    Dim startAngleInRadian As Double
    Dim endAngleInRadian As Double
    startAngleInRadian = startAngleInDegree * 3.141592 / 180#
    endAngleInRadian = endAngleInDegree * 3.141592 / 180#
    
    ' Create the arc object in model space
    Set arcObj = ThisDrawing.ModelSpace.AddArc(centerPoint, radius, startAngleInRadian, endAngleInRadian)
    ZoomAll
    
    ' Find the radius of the arc
    radius = arcObj.radius
    MsgBox "The radius of the arc is " & arcObj.radius, , "Radius Example"
    
End Sub
Sub Example_ReadOnly()
    ' This example shows if current drawing file is read only or not
    
    If ThisDrawing.ReadOnly Then
        MsgBox "The current drawing file is read only.", , "ReadOnly Example"
    Else
        MsgBox "The current drawing file is read-write.", , "ReadOnly Example"
    End If
    
End Sub
Sub Example_Saved()
    ' This example checks to see if the current drawing has been modified.
    
    If Not ThisDrawing.Saved Then
        MsgBox "Drawing has been modified! Use the Save or SaveAs method to save the drawing.", , "Saved Example"
    Else
        MsgBox "Drawing has not been modified since the last save.", , "Saved Example"
    End If
    
End Sub
Sub Example_ScaleFactor()
    ' This example creates a text object in model space.
    ' It then finds the current scale factor, and changes it.
    Dim textObj As AcadText
    Dim textString As String
    Dim insertionPoint(0 To 2) As Double
    Dim height As Double
    
    ' Define the text object
    textString = "Hello, World."
    insertionPoint(0) = 2: insertionPoint(1) = 2: insertionPoint(2) = 0
    height = 0.5
    
    ' Create the text object in model space
    Set textObj = ThisDrawing.ModelSpace.AddText(textString, insertionPoint, height)
    ZoomAll
    
    ' Find the current scale factor for the text object
    Dim currScaleFactor As Double
    currScaleFactor = textObj.scalefactor
    MsgBox "The scale factor of the text is " & textObj.scalefactor, , "ScaleFactor Example"
    
    ' Change the scale factor for the text object
    textObj.scalefactor = currScaleFactor + 1
    ThisDrawing.Regen True
    MsgBox "The scale factor of the text is now " & textObj.scalefactor, , "ScaleFactor Example"
    
End Sub
Sub Example_AddLeader()
    ' This example creates a leader in model space.
    ' The leader is not attached to any annotation object
    ' in this example.
   
    Dim leaderObj As AcadLeader
    Dim points(0 To 8) As Double
    Dim leaderType As Integer
    Dim annotationObject As AcadObject
    
    points(0) = 0: points(1) = 0: points(2) = 0
    points(3) = 4: points(4) = 4: points(5) = 0
    points(6) = 4: points(7) = 5: points(8) = 0
    leaderType = acLineWithArrow
    Set annotationObject = Nothing
        
    ' Create the leader object in model space
    Set leaderObj = ThisDrawing.ModelSpace.AddLeader(points, annotationObject, leaderType)
    ZoomAll
    
End Sub
Sub Example_Type()
    ' This example creates a leader in model space.
    ' It then changes the type of the leader.
   
    Dim leaderObj As AcadLeader
    Dim points(0 To 8) As Double
    Dim leaderType As Integer
    Dim annotationObject As AcadEntity
    
    points(0) = 0: points(1) = 2: points(2) = 0
    points(3) = 4: points(4) = 4: points(5) = 0
    points(6) = 4: points(7) = 2: points(8) = 0
    leaderType = acLineNoArrow
    Set annotationObject = Nothing
        
    ' Create the leader object in model space
    Set leaderObj = ThisDrawing.ModelSpace.AddLeader(points, annotationObject, leaderType)
    ZoomAll
    
    ' Find the current leader type
    leaderType = leaderObj.Type
    MsgBox "The leader type is " & Choose(leaderObj.Type + 1, "acLineNoArrow.", "acSplineNoArrow.", "acLineWithArrow.", "acSplineWithArrow."), , "Type Example"
    
    ' Change the leader type
    leaderObj.Type = acLineWithArrow
    leaderObj.Update
    MsgBox "The leader type is " & Choose(leaderObj.Type + 1, "acLineNoArrow.", "acSplineNoArrow.", "acLineWithArrow.", "acSplineWithArrow."), , "Type Example"
    
    ' Change the leader type
    leaderObj.Type = acSplineNoArrow
    leaderObj.Update
    MsgBox "The leader type is " & Choose(leaderObj.Type + 1, "acLineNoArrow.", "acSplineNoArrow.", "acLineWithArrow.", "acSplineWithArrow."), , "Type Example"
    
    ' Change the leader type
    leaderObj.Type = acSplineWithArrow
    leaderObj.Update
    MsgBox "The leader type is " & Choose(leaderObj.Type + 1, "acLineNoArrow.", "acSplineNoArrow.", "acLineWithArrow.", "acSplineWithArrow."), , "Type Example"
    
End Sub
Sub Example_Visible()
    ' This example creates a line in model space.
    ' It then toggles the visibility of the line.
    
    Dim lineObj As AcadLine
    Dim startPoint(0 To 2) As Double
    Dim endPoint(0 To 2) As Double

    ' Create the line
    startPoint(0) = 2#: startPoint(1) = 2#: startPoint(2) = 0#
    endPoint(0) = 4#: endPoint(1) = 4#: endPoint(2) = 0#
    Set lineObj = ThisDrawing.ModelSpace.AddLine(startPoint, endPoint)
    ZoomAll
    
DISPLAY:
    Dim response As Integer
    response = MsgBox("Do you want the new line to be visible?", vbYesNoCancel & vbQuestion)
    Select Case response
    Case vbYes
        lineObj.Visible = True
    Case vbNo
        lineObj.Visible = False
    Case vbCancel
        Exit Sub
    End Select
    
    ThisDrawing.Regen True
    GoTo DISPLAY
End Sub
Sub Example_AddMtext()
    ' This example creates an MText object in model space.
    
    Dim MTextObj As AcadMText
    Dim corner(0 To 2) As Double
    Dim width As Double
    Dim text As String
    corner(0) = 0#: corner(1) = 10#: corner(2) = 0#
    width = 10
    text = "This is the text String for the mtext Object"

    ' Creates the mtext Object
    Set MTextObj = ThisDrawing.ModelSpace.AddMText(corner, width, text)
    ZoomAll
    
End Sub
Sub Example_SetWidth()
    ' This example creates an MText object in model space.
    ' It then changes the width of the MText object.
    
    Dim MTextObj As AcadMText
    Dim corner(0 To 2) As Double
    Dim width As Double
    Dim text As String
    corner(0) = 0#: corner(1) = 10#: corner(2) = 0#
    width = 10
    text = "This is the text String for the mtext Object"

    ' Creates the mtext Object
    Set MTextObj = ThisDrawing.ModelSpace.AddMText(corner, width, text)
    ZoomAll
    
    ' Find the current width of the mtext object
    width = MTextObj.width
    MsgBox "The current width of the mtext object is " & MTextObj.width, , "Width Example"
    
    ' Change the width of the mtext object
    MTextObj.width = width / 2
    MTextObj.Update
    MsgBox "The new width of the mtext object is " & MTextObj.width, , "Width Example"
    
End Sub
Sub Example_Item()
    ' This example show two uses of the Item method.
    ' The first uses Item with an index counter to return an item in a collection.
    ' The second uses Item with a string to return an item in a collection.
    
    ' Iterate thru the model space collection,
    ' get all the items in the collection
    ' and store them in an array called newObjs
    Dim count As Integer
    count = ThisDrawing.ModelSpace.count
    
    ReDim newObjs(count) As AcadEntity
    Dim index As Integer
    For index = 0 To count - 1
        Set newObjs(index) = ThisDrawing.ModelSpace.Item(index)
    Next
    
    ' Get a particular item, in this case a layer, based on name "0"
    Dim layerObj As AcadLayer
    Set layerObj = ThisDrawing.Layers.Item("0")
    
End Sub
Sub Example_ListARX()
    ' This example gets all the loaded ARX applications
    
    ' Get the list of applications
    Dim appList As Variant
    appList = ThisDrawing.Application.ListArx
    
    ' Iterate through the list, and display the names, if any.
    If VarType(appList) <> vbEmpty Then
        Dim I As Integer
        For I = LBound(appList) To UBound(appList)
            MsgBox "ARX application name: " & appList(I)
        Next
    Else
        MsgBox "No ARX applications present."
    End If
    
End Sub
Sub Example_PromptString()
    ' This example creates an attribute definition in a block.
    ' It then inserts the block. Then it changes the prompt string
    ' of the attribute definition, and inserts the block again.
    
    ' Create the block
    Dim blockObj As AcadBlock
    Dim insertionPnt(0 To 2) As Double
    insertionPnt(0) = 0#: insertionPnt(1) = 0#: insertionPnt(2) = 0#
    Set blockObj = ThisDrawing.Blocks.Add(insertionPnt, "TEST")
    
    ' Add a circle to block
    Dim circleObj As AcadCircle
    Dim center(0 To 2) As Double
    Dim radius As Double
    center(0) = 0: center(1) = 0: center(2) = 0
    radius = 1
    Set circleObj = blockObj.AddCircle(center, radius)

    ' Define the attribute definition
    Dim attributeObj As AcadAttribute
    Dim height As Double
    Dim mode As Integer
    Dim prompt As String
    Dim tag As String
    Dim value As String
    
    height = 1#
    mode = acAttributeModeVerify
    prompt = "Enter value:"
    insertionPnt(0) = 0#: insertionPnt(1) = 0#: insertionPnt(2) = 0
    tag = "Tag1"
    value = "Circle1"
    
    ' Create the attribute definition on the block
    Set attributeObj = blockObj.AddAttribute(height, mode, prompt, insertionPnt, tag, value)
    
    ' Insert the block
    Dim blockRefObj1 As AcadBlockReference
    insertionPnt(0) = 2#: insertionPnt(1) = 2#: insertionPnt(2) = 0
    Set blockRefObj1 = ThisDrawing.ModelSpace.InsertBlock(insertionPnt, "TEST", 1#, 1#, 1#, 0)
        
    ' Change the prompt string and tag of the attribute definition
    attributeObj.PromptString = "Verify value:"
    
    ' Insert the block again
    Dim blockRefObj2 As AcadBlockReference
    insertionPnt(0) = 4#: insertionPnt(1) = 4#: insertionPnt(2) = 0
    Set blockRefObj2 = ThisDrawing.ModelSpace.InsertBlock(insertionPnt, "TEST", 1#, 1#, 1#, 0)
    
    ZoomAll

End Sub
Sub Example_InsertBlock()
    ' This example creates a block containing a circle.
    ' It then inserts the block.

    ' Create the block
    Dim blockObj As AcadBlock
    Dim insertionPnt(0 To 2) As Double
    insertionPnt(0) = 0#: insertionPnt(1) = 0#: insertionPnt(2) = 0#
    Set blockObj = ThisDrawing.Blocks.Add(insertionPnt, "CircleBlock")
    
    ' Add a circle to the block
    Dim circleObj As AcadCircle
    Dim center(0 To 2) As Double
    Dim radius As Double
    center(0) = 0: center(1) = 0: center(2) = 0
    radius = 1
    Set circleObj = blockObj.AddCircle(center, radius)
   
    ' Insert the block
    Dim blockRefObj As AcadBlockReference
    insertionPnt(0) = 2#: insertionPnt(1) = 2#: insertionPnt(2) = 0
    Set blockRefObj = ThisDrawing.ModelSpace.InsertBlock(insertionPnt, "CircleBlock", 1#, 1#, 1#, 0)
    
    ZoomAll
    
End Sub
Sub Example_SnapBasePoint()
    ' This example changes the snap base point for a
    ' model space and paperspace viewport.
    
    ' Create a new model space viewport
    Dim viewportObj As AcadViewport
    Set viewportObj = ThisDrawing.Viewports.Add("NewViewport")
    
    ' Find the current snap base point
    Dim currSnapPnt As Variant
    currSnapPnt = viewportObj.SnapBasePoint
    MsgBox "The current model space snap base point is " & viewportObj.SnapBasePoint(0) & ", " & viewportObj.SnapBasePoint(1), , "SnapBasePoint Example"
    
    ' Change the snap base point
    Dim newSnapPnt(0 To 1) As Double
    newSnapPnt(0) = 5#: newSnapPnt(1) = 5#
    viewportObj.SnapBasePoint = newSnapPnt
    MsgBox "The new model space snap base point is " & viewportObj.SnapBasePoint(0) & ", " & viewportObj.SnapBasePoint(1), , "SnapBasePoint Example"
   
    
    ' Create a new paperspace viewport
    Dim pviewportObj As AcadPViewport
    Dim center(0 To 2) As Double
    Dim width As Double
    Dim height As Double
    
    center(0) = 3: center(1) = 3: center(2) = 0
    width = 40
    height = 40
    ThisDrawing.ActiveSpace = acPaperSpace
    Set pviewportObj = ThisDrawing.PaperSpace.AddPViewport(center, width, height)
    
    ' Find the current snap base point
    currSnapPnt = pviewportObj.SnapBasePoint
    MsgBox "The current paperspace snap base point is " & pviewportObj.SnapBasePoint(0) & ", " & pviewportObj.SnapBasePoint(1), , "SnapBasePoint Example"
    
    ' Change the snap base point
    newSnapPnt(0) = 2#: newSnapPnt(1) = 2#
    pviewportObj.SnapBasePoint = newSnapPnt
    MsgBox "The new paperspace snap base point is " & pviewportObj.SnapBasePoint(0) & ", " & pviewportObj.SnapBasePoint(1), , "SnapBasePoint Example"

End Sub
Sub Example_SnapRotationAngle()
    ' This example changes the snap rotation angle for a
    ' model space and paperspace viewport.
    
    ' Create a new model space viewport
    Dim viewportObj As AcadViewport
    Set viewportObj = ThisDrawing.Viewports.Add("NewViewport")
    
    ' Find the current snap rotation angle
    Dim currSnapAngle As Double
    currSnapAngle = viewportObj.SnapRotationAngle
    MsgBox "The current model space snap rotation angle is " & viewportObj.SnapRotationAngle, , "SnapRotationAngle Example"
    
    ' Change the snap rotation angle
    viewportObj.SnapRotationAngle = 1.5
    MsgBox "The new model space snap rotation angle is " & viewportObj.SnapRotationAngle, , "SnapRotationAngle Example"
   
    
    ' Create a new paperspace viewport
    Dim pviewportObj As AcadPViewport
    Dim center(0 To 2) As Double
    Dim width As Double
    Dim height As Double
    
    center(0) = 3: center(1) = 3: center(2) = 0
    width = 40
    height = 40
    ThisDrawing.ActiveSpace = acPaperSpace
    Set pviewportObj = ThisDrawing.PaperSpace.AddPViewport(center, width, height)
    
    ' Find the current snap rotation angle
    currSnapAngle = pviewportObj.SnapRotationAngle
    MsgBox "The current paperspace snap rotation angle is " & pviewportObj.SnapRotationAngle, , "SnapRotationAngle Example"
    
    ' Change the snap rotation angle
    pviewportObj.SnapRotationAngle = 1.5
    MsgBox "The new paperspace snap base point is " & pviewportObj.SnapRotationAngle, , "SnapRotationAngle Example"

End Sub
Sub Example_Target()
    ' This example changes the target for a model space viewport.
    
    ' Create a new model space viewport
    Dim viewportObj As AcadViewport
    Set viewportObj = ThisDrawing.Viewports.Add("NewViewport")
    
    ' Add a circle
    Dim circleObj As AcadCircle
    Dim center(0 To 2) As Double
    Dim radius As Double
    center(0) = 0: center(1) = 0: center(2) = 0
    radius = 1
    Set circleObj = ThisDrawing.ModelSpace.AddCircle(center, radius)
    
    ' Find the current target
    Dim currTarget As Variant
    currTarget = viewportObj.Target
    MsgBox "The current target is " & viewportObj.Target(0) & ", " & viewportObj.Target(1) & ", " & viewportObj.Target(2), , "Target Example"
    
    ' Change the target
    Dim newTarget(0 To 2) As Double
    newTarget(0) = 2#: newTarget(1) = 2#: newTarget(2) = 0
    viewportObj.Target = newTarget
    ThisDrawing.ActiveViewport = viewportObj
    ThisDrawing.Regen acAllViewports
    MsgBox "The new target is " & viewportObj.Target(0) & ", " & viewportObj.Target(1) & ", " & viewportObj.Target(2), , "Target Example"
   
End Sub
Sub Example_XScaleFactor()
    ' This example creates a block containing a circle.
    ' It then inserts the block and changes the XScaleFactor.
    
    ' Create the block
    Dim blockObj As AcadBlock
    Dim insertionPnt(0 To 2) As Double
    insertionPnt(0) = 0#: insertionPnt(1) = 0#: insertionPnt(2) = 0#
    Set blockObj = ThisDrawing.Blocks.Add(insertionPnt, "CircleBlock")
    
    ' Add a circle to the block
    Dim circleObj As AcadCircle
    Dim center(0 To 2) As Double
    Dim radius As Double
    center(0) = 0: center(1) = 0: center(2) = 0
    radius = 1
    Set circleObj = blockObj.AddCircle(center, radius)
   
    ' Insert the block
    Dim blockRefObj As AcadBlockReference
    insertionPnt(0) = 2#: insertionPnt(1) = 2#: insertionPnt(2) = 0
    Set blockRefObj = ThisDrawing.ModelSpace.InsertBlock(insertionPnt, "CircleBlock", 1#, 1#, 1#, 0)
    
    ' Find the current XScaleFactor for the block reference
    Dim currXScaleFactor As Double
    currXScaleFactor = blockRefObj.XScaleFactor
    ZoomAll
    MsgBox "The current XScaleFactor for the block reference is " & blockRefObj.XScaleFactor, , "XScaleFactor Example"
    
    ' Change the XScaleFactor for the block reference
    blockRefObj.XScaleFactor = currXScaleFactor + 2
    ZoomAll
    MsgBox "The new XScaleFactor for the block reference is " & blockRefObj.XScaleFactor, , "XScaleFactor Example"
    
End Sub
Sub Example_YScaleFactor()
    ' This example creates a block containing a circle.
    ' It then inserts the block and changes the YScaleFactor.
    
    ' Create the block
    Dim blockObj As AcadBlock
    Dim insertionPnt(0 To 2) As Double
    insertionPnt(0) = 0#: insertionPnt(1) = 0#: insertionPnt(2) = 0#
    Set blockObj = ThisDrawing.Blocks.Add(insertionPnt, "CircleBlock")
    
    ' Add a circle to the block
    Dim circleObj As AcadCircle
    Dim center(0 To 2) As Double
    Dim radius As Double
    center(0) = 0: center(1) = 0: center(2) = 0
    radius = 1
    Set circleObj = blockObj.AddCircle(center, radius)
   
    ' Insert the block
    Dim blockRefObj As AcadBlockReference
    insertionPnt(0) = 2#: insertionPnt(1) = 2#: insertionPnt(2) = 0
    Set blockRefObj = ThisDrawing.ModelSpace.InsertBlock(insertionPnt, "CircleBlock", 1#, 1#, 1#, 0)
    ZoomAll
    
    ' Find the current YScaleFactor for the block reference
    Dim currYScaleFactor As Double
    currYScaleFactor = blockRefObj.YScaleFactor
    MsgBox "The current YScaleFactor for the block reference is " & blockRefObj.YScaleFactor, , "YScaleFactor Example"
    
    ' Change the YScaleFactor for the block reference
    blockRefObj.YScaleFactor = currYScaleFactor + 2
    ZoomAll
    MsgBox "The new YScaleFactor for the block reference is " & blockRefObj.YScaleFactor, , "YScaleFactor Example"
    
End Sub
Sub Example_ZScaleFactor()
    ' This example creates a block containing a circle.
    ' It then inserts the block and changes the ZScaleFactor.
    
    ' Create the block
    Dim blockObj As AcadBlock
    Dim insertionPnt(0 To 2) As Double
    insertionPnt(0) = 0#: insertionPnt(1) = 0#: insertionPnt(2) = 0#
    Set blockObj = ThisDrawing.Blocks.Add(insertionPnt, "CircleBlock")
    
    ' Add a circle to the block
    Dim circleObj As AcadCircle
    Dim center(0 To 2) As Double
    Dim radius As Double
    center(0) = 0: center(1) = 0: center(2) = 0
    radius = 1
    Set circleObj = blockObj.AddCircle(center, radius)
   
    ' Insert the block
    Dim blockRefObj As AcadBlockReference
    insertionPnt(0) = 2#: insertionPnt(1) = 2#: insertionPnt(2) = 0
    Set blockRefObj = ThisDrawing.ModelSpace.InsertBlock(insertionPnt, "CircleBlock", 1#, 1#, 1#, 0)
    ZoomAll
    
    ' Find the current ZScaleFactor for the block reference
    Dim currZScaleFactor As Double
    currZScaleFactor = blockRefObj.ZScaleFactor
    MsgBox "The current ZScaleFactor for the block reference is " & blockRefObj.ZScaleFactor, , "ZScaleFactor Example"
    
    ' Change the ZScaleFactor for the block reference
    blockRefObj.ZScaleFactor = currZScaleFactor + 2
    
    ' Change the viewing direction of the viewport
    ' to better see the zscale change
    Dim NewDirection(0 To 2) As Double
    NewDirection(0) = -1: NewDirection(1) = -1: NewDirection(2) = 1
    ThisDrawing.ActiveViewport.direction = NewDirection
    ThisDrawing.ActiveViewport = ThisDrawing.ActiveViewport
    ZoomAll
    
    MsgBox "The new ZScaleFactor for the block reference is " & blockRefObj.ZScaleFactor, , "ZScaleFactor Example"
    
End Sub
Sub Example_AddCustomObject()
    ' This example adds a custom object to modelspace.
    
    ' Load the ARX application that defines the custom object.
    ' Note: The application listed here does not exist and
    ' will cause an error when run. Change the application name
    ' to the path and name of your ARX Application.
    ThisDrawing.Application.LoadArx ("MyARXApp.dll")
    
    ' Once the application has been loaded successfully,
    ' add the custom object to model space.
    Dim customObj As AcadObject
    Set customObj = ThisDrawing.ModelSpace.AddCustomObject("MyNewObject")
    
End Sub
Sub Example_LoadARX()
    ' This example loads an ObjectARX application.
    
    ' Note: The application listed here does not exist and
    ' will cause an error when run. Change the application name
    ' to the path and name of your ARX Application.
    ThisDrawing.Application.LoadArx ("MyARXApp.arx")
        
End Sub
Sub Example_AddItems()
    ' This example creates a selection set and several objects.
    ' It then adds the objects to the selection set.
    
    ' Create the new selection set
    Dim ssetObj As AcadSelectionSet
    Set ssetObj = ThisDrawing.SelectionSets.Add("TEST_SELECTIONSET")
    
    ' Create a Ray object in model space
    Dim rayObj As AcadRay
    Dim basePoint(0 To 2) As Double
    Dim SecondPoint(0 To 2) As Double
    basePoint(0) = 3#: basePoint(1) = 3#: basePoint(2) = 0#
    SecondPoint(0) = 1#: SecondPoint(1) = 3#: SecondPoint(2) = 0#
    Set rayObj = ThisDrawing.ModelSpace.AddRay(basePoint, SecondPoint)
    
    ' Create a polyline object in model space
    Dim plineObj As AcadLWPolyline
    Dim points(0 To 5) As Double
    points(0) = 3: points(1) = 7
    points(2) = 9: points(3) = 2
    points(4) = 3: points(5) = 5
    Set plineObj = ThisDrawing.ModelSpace.AddLightWeightPolyline(points)
    plineObj.Closed = True

    ' Create a line object in model space
    Dim lineObj As AcadLine
    Dim startPoint(0 To 2) As Double
    Dim endPoint(0 To 2) As Double
    startPoint(0) = 0: startPoint(1) = 0: startPoint(2) = 0
    endPoint(0) = 2: endPoint(1) = 2: endPoint(2) = 0
    Set lineObj = ThisDrawing.ModelSpace.AddLine(startPoint, endPoint)
    
    ' Create a circle object in model space
    Dim circObj As AcadCircle
    Dim centerPt(0 To 2) As Double
    Dim radius As Double
    centerPt(0) = 20: centerPt(1) = 30: centerPt(2) = 0
    radius = 3
    Set circObj = ThisDrawing.ModelSpace.AddCircle(centerPt, radius)

    ' Create an ellipse object in model space
    Dim ellObj As AcadEllipse
    Dim majAxis(0 To 2) As Double
    Dim center(0 To 2) As Double
    Dim radRatio As Double
    center(0) = 5#: center(1) = 5#: center(2) = 0#
    majAxis(0) = 10: majAxis(1) = 20#: majAxis(2) = 0#
    radRatio = 0.3
    Set ellObj = ThisDrawing.ModelSpace.AddEllipse(center, majAxis, radRatio)

    ZoomAll
    
    ' Iterate through the model space collection.
    ' Collect the objects found into an array of objects
    ' to be added to the selection set.
    ReDim ssobjs(0 To ThisDrawing.ModelSpace.count - 1) As AcadEntity
    Dim I As Integer
    For I = 0 To ThisDrawing.ModelSpace.count - 1
        Set ssobjs(I) = ThisDrawing.ModelSpace.Item(I)
    Next
    
    ' Add the array of objects to the selection set
    ssetObj.AddItems ssobjs
    
    ThisDrawing.Regen acActiveViewport
    
End Sub
Sub Example_AddLightWeightPolyline()
    ' This example creates a light weight polyline in model space.
    
    Dim plineObj As AcadLWPolyline
    Dim points(0 To 9) As Double
    
    ' Define the 2D polyline points
    points(0) = 1: points(1) = 1
    points(2) = 1: points(3) = 2
    points(4) = 2: points(5) = 2
    points(6) = 3: points(7) = 2
    points(8) = 4: points(9) = 4
        
    ' Create a light weight Polyline object in model space
    Set plineObj = ThisDrawing.ModelSpace.AddLightWeightPolyline(points)
    ZoomAll
    
End Sub
Sub Example_AddLine()
    ' This example adds a line in model space
    
    Dim lineObj As AcadLine
    Dim startPoint(0 To 2) As Double
    Dim endPoint(0 To 2) As Double
    
    ' Define the start and end points for the line
    startPoint(0) = 1#: startPoint(1) = 1#: startPoint(2) = 0#
    endPoint(0) = 5#: endPoint(1) = 5#: endPoint(2) = 0#
    
    ' Create the line in model space
    Set lineObj = ThisDrawing.ModelSpace.AddLine(startPoint, endPoint)
    ZoomAll
    
End Sub
Sub Example_AddObject()
    ' This example creates a dictionary and adds
    ' a custom object to that dictionary.
    
    Dim dictObj As AcadDictionary
    Set dictObj = ThisDrawing.Dictionaries.Add("TEST_DICTIONARY")
    
    ' Load the ARX application that defines the custom object.
    ' Note: The application listed here does not exist and
    ' will cause an error when run. Change the application name
    ' to the path and name of your ARX Application.
    ThisDrawing.Application.LoadArx ("MyARXApp.dll")
    
    ' Create the custom object in the dictionary
    Dim keyName As String
    Dim className As String
    Dim customObj As AcadObject
    
    keyName = "OBJ1"
    className = "CAsdkDictObject"
    
    Set customObj = dictObj.AddObject(keyName, className)
    
End Sub
Sub Example_AddPoint()
    ' This example creates a point in model space.
    Dim pointObj As AcadPoint
    Dim location(0 To 2) As Double
    
    ' Define the location of the point
    location(0) = 5#: location(1) = 5#: location(2) = 0#
    
    ' Create the point
    Set pointObj = ThisDrawing.ModelSpace.AddPoint(location)
    pointObj.Color = acCyan
    ZoomAll
    
End Sub
Sub Example_AddPolyline()
    ' This example creates a polyline in model space.
    
    Dim plineObj As AcadPolyline
    Dim points(0 To 14) As Double
    
    ' Define the 2D polyline points
    points(0) = 1: points(1) = 1: points(2) = 0
    points(3) = 1: points(4) = 2: points(5) = 0
    points(6) = 2: points(7) = 2: points(8) = 0
    points(9) = 3: points(10) = 2: points(11) = 0
    points(12) = 4: points(13) = 4: points(14) = 0
        
    ' Create a light weight Polyline object in model space
    Set plineObj = ThisDrawing.ModelSpace.AddPolyline(points)
    ZoomAll
    
End Sub
Sub Example_AddPViewport()
    ' This example creates a new paperspace viewport
    
    Dim pviewportObj As AcadPViewport
    Dim center(0 To 2) As Double
    Dim width As Double
    Dim height As Double
    
    ' Define the pviewport
    center(0) = 3: center(1) = 3: center(2) = 0
    width = 40
    height = 40
    
    ' Change from model space to paperspace
    ThisDrawing.ActiveSpace = acPaperSpace
    
    ' Create the pviewport
    Set pviewportObj = ThisDrawing.PaperSpace.AddPViewport(center, width, height)
    
    ThisDrawing.Regen acAllViewports
    
End Sub
Sub Example_AddRaster()
    ' This example adds a raster image in model space.
    
    ' This example uses the "downtown.jpg" found in the sample
    ' directory. If you do not have this image, or it is located
    ' in a different directory, insert a valid path and filename
    ' for the imageName variable below.
    
    Dim insertionPoint(0 To 2) As Double
    Dim scalefactor As Double
    Dim rotationAngle As Double
    Dim imageName As String
    Dim rasterObj As AcadRasterImage
    imageName = "C:/AutoCAD/sample/downtown.jpg"
    insertionPoint(0) = 5#: insertionPoint(1) = 5#: insertionPoint(2) = 0#
    scalefactor = 1#
    rotationAngle = 0
    
    On Error Resume Next
    ' Creates a raster image in model space
    Set rasterObj = ThisDrawing.ModelSpace.AddRaster(imageName, insertionPoint, scalefactor, rotationAngle)
    
    If Err.Description = "File error" Then
        MsgBox imageName & " could not be found."
        Exit Sub
    End If
End Sub
Sub Example_ImageHeight()
    ' This example adds a raster image in model space and then finds
    ' the height and width of the image.
    
    ' This example uses the "downtown.jpg" found in the sample
    ' directory. If you do not have this image, or it is located
    ' in a different directory, insert a valid path and filename
    ' for the imageName variable below.
    
    Dim insertionPoint(0 To 2) As Double
    Dim scalefactor As Double
    Dim rotationAngle As Double
    Dim imageName As String
    Dim rasterObj As AcadRasterImage
    imageName = "C:/AutoCAD/sample/downtown.jpg"
    insertionPoint(0) = 5#: insertionPoint(1) = 5#: insertionPoint(2) = 0#
    scalefactor = 1#
    rotationAngle = 0
    
    ' Creates a raster image in model space
    Set rasterObj = ThisDrawing.ModelSpace.AddRaster(imageName, insertionPoint, scalefactor, rotationAngle)
    
    ' Find the height and width of the raster image
    Dim height As Variant
    Dim width As Variant
    
    height = rasterObj.ImageHeight
    width = rasterObj.ImageWidth
    
    MsgBox "Raster image: " & rasterObj.ImageFile & vbCrLf & _
            "ImageHeight: " & str(height) & vbCrLf & _
            "ImageWidth: " & str(width)
            
End Sub
Sub Example_ImageWidth()
    ' This example adds a raster image in model space and then finds
    ' the height and width of the image.
    
    ' This example uses the "downtown.jpg" found in the sample
    ' directory. If you do not have this image, or it is located
    ' in a different directory, insert a valid path and filename
    ' for the imageName variable below.
    
    Dim insertionPoint(0 To 2) As Double
    Dim scalefactor As Double
    Dim rotationAngle As Double
    Dim imageName As String
    Dim rasterObj As AcadRasterImage
    imageName = "C:/AutoCAD/sample/downtown.jpg"
    insertionPoint(0) = 5#: insertionPoint(1) = 5#: insertionPoint(2) = 0#
    scalefactor = 1#
    rotationAngle = 0
    
    ' Creates a raster image in model space
    Set rasterObj = ThisDrawing.ModelSpace.AddRaster(imageName, insertionPoint, scalefactor, rotationAngle)
    
    ' Find the height and width of the raster image
    Dim height As Variant
    Dim width As Variant
    
    height = rasterObj.ImageHeight
    width = rasterObj.ImageWidth
    
    MsgBox "Raster image: " & rasterObj.ImageFile & vbCrLf & _
            "ImageHeight: " & str(height) & vbCrLf & _
            "ImageWidth: " & str(width)
            
End Sub
Sub Example_AddRay()
    ' This example creates a ray in model space.
    
    Dim rayObj As AcadRay
    Dim basePoint(0 To 2) As Double
    Dim SecondPoint(0 To 2) As Double
    
    ' Define the ray
    basePoint(0) = 3#: basePoint(1) = 3#: basePoint(2) = 0#
    SecondPoint(0) = 4#: SecondPoint(1) = 4#: SecondPoint(2) = 0#
    
    ' Creates a Ray object in model space
    Set rayObj = ThisDrawing.ModelSpace.AddRay(basePoint, SecondPoint)
    ZoomAll
    
End Sub

Sub Example_AddSolid()
    ' This example creates a solid in model space.
    
    Dim solidObj As AcadSolid
    Dim point1(0 To 2) As Double
    Dim point2(0 To 2) As Double
    Dim point3(0 To 2) As Double
    Dim point4(0 To 2) As Double
    
    ' Define the solid
    point1(0) = 0#: point1(1) = 1#: point1(2) = 0#
    point2(0) = 5#: point2(1) = 1#: point2(2) = 0#
    point3(0) = 8#: point3(1) = 8#: point3(2) = 0#
    point4(0) = 4#: point4(1) = 6#: point4(2) = 0#

    ' Create the solid object in model space
    Set solidObj = ThisDrawing.ModelSpace.AddSolid(point1, point2, point3, point4)
    ZoomAll
    
End Sub
Sub Example_AddVertex()
    ' This example creates a light weight polyline in model space.
    ' It then adds a vertex to the polyline.

    Dim plineObj As AcadLWPolyline
    Dim points(0 To 9) As Double
    
    
    ' Define the 2D polyline points
    points(0) = 1: points(1) = 1
    points(2) = 1: points(3) = 2
    points(4) = 2: points(5) = 2
    points(6) = 3: points(7) = 2
    points(8) = 4: points(9) = 4
        
    ' Create a light weight Polyline object in model space
    Set plineObj = ThisDrawing.ModelSpace.AddLightWeightPolyline(points)
    ZoomAll
    MsgBox "Add a vertex to the end of the polyline.", , "AddVertex Example"
    
    ' Define the new vertex
    Dim newVertex(0 To 1) As Double
    newVertex(0) = 4: newVertex(1) = 1
    
    ' Add the vertex to the polyline
    plineObj.AddVertex 5, newVertex
    plineObj.Update
    MsgBox "Vertex added.", , "AddVertex Example"
    
End Sub
Sub Example_GetBulge()
    ' This example creates a light weight polyline in model space.
    ' It then finds and changes the bulge for a given segment.
    
    Dim plineObj As AcadLWPolyline
    Dim points(0 To 11) As Double
    
    ' Define the 2D polyline points
    points(0) = 1: points(1) = 1
    points(2) = 1: points(3) = 2
    points(4) = 2: points(5) = 2
    points(6) = 3: points(7) = 2
    points(8) = 4: points(9) = 4
    points(10) = 4: points(11) = 1
        
    ' Create a light weight Polyline object in model space
    Set plineObj = ThisDrawing.ModelSpace.AddLightWeightPolyline(points)
    ZoomAll
    
    ' Find the bulge of the 3rd segment
    Dim currentBulge As Double
    currentBulge = plineObj.GetBulge(3)
    MsgBox "The bulge for the third segment is " & plineObj.GetBulge(3), , "GetBulge Example"
    
    ' Change the bulge of the 3rd segment
    plineObj.SetBulge 3, -0.5
    plineObj.Update
    MsgBox "The bulge for the third segment is now " & plineObj.GetBulge(3), , "GetBulge Example"
    
End Sub
Sub Example_SetBulge()
    ' This example creates a light weight polyline in model space.
    ' It then finds and changes the bulge for a given segment.
    
    Dim plineObj As AcadLWPolyline
    Dim points(0 To 11) As Double
    
    ' Define the 2D polyline points
    points(0) = 1: points(1) = 1
    points(2) = 1: points(3) = 2
    points(4) = 2: points(5) = 2
    points(6) = 3: points(7) = 2
    points(8) = 4: points(9) = 4
    points(10) = 4: points(11) = 1
        
    ' Create a light weight Polyline object in model space
    Set plineObj = ThisDrawing.ModelSpace.AddLightWeightPolyline(points)
    ZoomAll
    
    ' Find the bulge of the 3rd segment
    Dim currentBulge As Double
    currentBulge = plineObj.GetBulge(3)
    MsgBox "The bulge for the third segment is " & plineObj.GetBulge(3), , "SetBulge Example"
    
    ' Change the bulge of the 3rd segment
    plineObj.SetBulge 3, -0.5
    plineObj.Update
    MsgBox "The bulge for the third segment is now " & plineObj.GetBulge(3), , "SetBulge Example"
    
End Sub
Sub Example_Explode()
    ' This example creates a light weight polyline in model space.
    ' It then explodes the polyline.
    
    Dim plineObj As AcadLWPolyline
    Dim points(0 To 11) As Double
    
    ' Define the 2D polyline points
    points(0) = 1: points(1) = 1
    points(2) = 1: points(3) = 2
    points(4) = 2: points(5) = 2
    points(6) = 3: points(7) = 2
    points(8) = 4: points(9) = 4
    points(10) = 4: points(11) = 1
        
    ' Create a light weight Polyline object in model space
    Set plineObj = ThisDrawing.ModelSpace.AddLightWeightPolyline(points)
    
    ' Set the bulge on one segment to vary the
    ' type of objects in the polyline
    plineObj.SetBulge 3, -0.5
    ZoomAll
    
    ' Explode the polyline
    MsgBox "Explode the polyline.", , "Explode Example"
    Dim explodedObjects As Variant
    explodedObjects = plineObj.Explode
    
    ' Loop through the exploded objects
    Dim I As Integer
    For I = 0 To UBound(explodedObjects)
        explodedObjects(I).Color = acRed
        explodedObjects(I).Update
        MsgBox "Exploded Object " & I & ": " & explodedObjects(I).ObjectName, , "Explode Example"
        explodedObjects(I).Color = acByLayer
        explodedObjects(I).Update
    Next
    
End Sub
Sub Example_AngleToReal()
    ' This example passes several different strings representing
    ' an angle in different units to be converted to radians.
    
    Dim angAsStr As String
    Dim unit As Integer
    Dim angAsReal As Double
    
    ' Convert the angle given in degrees unit to a real
    angAsStr = "45"
    unit = acDegrees
    angAsReal = ThisDrawing.Utility.AngleToReal(angAsStr, unit)
    MsgBox "45 degrees converts to " & angAsReal & " radians.", , "AngleAsReal Example"
    
    ' Convert the angle given in degrees/minutes/seconds unit to Radians
    angAsStr = "45d0' 0"""
    unit = acDegreeMinuteSeconds
    angAsReal = ThisDrawing.Utility.AngleToReal(angAsStr, unit)
    MsgBox "45 degrees, 0 minutes, 0 seconds converts to " & angAsReal & " radians.", , "AngleAsReal Example"
    
    ' Convert the angle given in grads unit to Radians
    angAsStr = "50"
    unit = acGrads
    angAsReal = ThisDrawing.Utility.AngleToReal(angAsStr, unit)
    MsgBox "50 grads converts to " & angAsReal & " radians.", , "AngleAsReal Example"
    
End Sub
Sub Example_AngleToString()
    ' This example converts a radian value to several different
    ' strings representing the value in different units.
    
    Dim angAsRad As Double
    Dim unit As Integer
    Dim precision As Long
    Dim angAsString As String
    angAsRad = 0.785398163397448
    unit = acDegrees
    precision = 6
    
    ' Convert the radian value to degrees with a precision of 6
    angAsString = ThisDrawing.Utility.AngleToString(angAsRad, unit, precision)
    MsgBox "0.785398163397448 radians =  " & angAsString & " degrees", , "AngleAsString Example"
    
    ' Convert the radian value to degrees/Minutes/Seconds with a precision of 6
    unit = acDegreeMinuteSeconds
    angAsString = ThisDrawing.Utility.AngleToString(angAsRad, unit, precision)
    MsgBox "0.785398163397448 radians =  " & angAsString, , "AngleAsString Example"
    
    ' Convert the radian value to grads with a precision of 6
    unit = acGrads
    angAsString = ThisDrawing.Utility.AngleToString(angAsRad, unit, precision)
    MsgBox "0.785398163397448 radians =  " & angAsString, , "AngleAsString Example"
    
End Sub
Sub Example_ArrayPolar()
    ' This example creates a circle and then performs a polar array
    ' on that circle.
    
    ' Create the circle
    Dim circleObj As AcadCircle
    Dim center(0 To 2) As Double
    Dim radius As Double
    center(0) = 2#: center(1) = 2#: center(2) = 0#
    radius = 1
    Set circleObj = ThisDrawing.ModelSpace.AddCircle(center, radius)
    ZoomAll
    MsgBox "Perform the polar array on the circle.", , "ArrayPolar Example"
    
    ' Define the polar array
    Dim noOfObjects As Integer
    Dim angleToFill As Double
    Dim basePnt(0 To 2) As Double
    noOfObjects = 4
    angleToFill = 3.14          ' 180 degrees
    basePnt(0) = 4#: basePnt(1) = 4#: basePnt(2) = 0#
    
    ' The following example will create 4 copies of an object
    ' by rotating and copying it about the point (3,3,0).
    Dim retObj As Variant
    retObj = circleObj.ArrayPolar(noOfObjects, angleToFill, basePnt)
    
    ZoomAll
    MsgBox "Polar array completed.", , "ArrayPolar Example"
    
End Sub
Sub Example_ArrayRectangular()
    ' This example creates a circle and then performs
    ' a rectangular array on that circle.
    
    ' Create the circle
    Dim circleObj As AcadCircle
    Dim center(0 To 2) As Double
    Dim radius As Double
    center(0) = 2#: center(1) = 2#: center(2) = 0#
    radius = 0.5
    Set circleObj = ThisDrawing.ModelSpace.AddCircle(center, radius)
    ThisDrawing.Application.ZoomAll
    MsgBox "Perform the rectangular array on the circle.", , "ArrayRectangular Example"
    
    ' Define the rectangular array
    Dim numberOfRows As Long
    Dim numberOfColumns As Long
    Dim numberOfLevels As Long
    Dim distanceBwtnRows As Double
    Dim distanceBwtnColumns As Double
    Dim distanceBwtnLevels As Double
    numberOfRows = 5
    numberOfColumns = 5
    numberOfLevels = 2
    distanceBwtnRows = 1
    distanceBwtnColumns = 1
    distanceBwtnLevels = 1
    
    ' Create the array of objects
    Dim retObj As Variant
    retObj = circleObj.ArrayRectangular(numberOfRows, numberOfColumns, numberOfLevels, distanceBwtnRows, distanceBwtnColumns, distanceBwtnLevels)
    
    ZoomAll
    MsgBox "Rectangular array completed.", , "ArrayRectangular Example"
    
End Sub
Sub Example_Move()
    ' This example creates a circle and then performs
    ' a move on that circle.
    
    ' Create the circle
    Dim circleObj As AcadCircle
    Dim center(0 To 2) As Double
    Dim radius As Double
    center(0) = 2#: center(1) = 2#: center(2) = 0#
    radius = 0.5
    Set circleObj = ThisDrawing.ModelSpace.AddCircle(center, radius)
    ZoomAll
    
    ' Define the points that make up the move vector
    Dim point1(0 To 2) As Double
    Dim point2(0 To 2) As Double
    point1(0) = 0: point1(1) = 0: point1(2) = 0
    point2(0) = 2: point2(1) = 0: point2(2) = 0
        
    MsgBox "Move the circle 2 units in the X direction.", , "Move Example"
    
    ' Move the circle
    circleObj.Move point1, point2
    
    ZoomAll
    MsgBox "Move completed.", , "Move Example"
    
End Sub
Sub Example_Copy()
    ' This example creates a circle and then copies
    ' that circle. The new circle is then moved
    ' and colored red.
    
    ' Create the circle
    Dim circleObj As AcadCircle
    Dim center(0 To 2) As Double
    Dim radius As Double
    center(0) = 2#: center(1) = 2#: center(2) = 0#
    radius = 0.5
    Set circleObj = ThisDrawing.ModelSpace.AddCircle(center, radius)
    ZoomAll
    MsgBox "Copy the circle.", , "Copy Example"
    
    ' Copy the circle
    Dim copyCircleObj As AcadCircle
    Set copyCircleObj = circleObj.Copy()
    
    ' Define the points that make up the move vector
    Dim point1(0 To 2) As Double
    Dim point2(0 To 2) As Double
    point1(0) = 0: point1(1) = 0: point1(2) = 0
    point2(0) = 2: point2(1) = 0: point2(2) = 0
        
    MsgBox "Move the copied circle 2 units in the X direction.", , "Copy Example"
    
    ' Move the circle and color it
    copyCircleObj.Move point1, point2
    copyCircleObj.Color = acRed
    
    ZoomAll
    MsgBox "Move completed.", , "Copy Example"
    
End Sub
Sub Example_Mirror()
    ' This example creates a light weight polyline
    ' and then mirrors that polyline.
    
    ' Create the polyline
    Dim plineObj As AcadLWPolyline
    Dim points(0 To 11) As Double
    points(0) = 1: points(1) = 1
    points(2) = 1: points(3) = 2
    points(4) = 2: points(5) = 2
    points(6) = 3: points(7) = 2
    points(8) = 4: points(9) = 4
    points(10) = 4: points(11) = 1
    Set plineObj = ThisDrawing.ModelSpace.AddLightWeightPolyline(points)
    plineObj.Closed = True
    ZoomAll
    
    ' Define the mirror axis
    Dim point1(0 To 2) As Double
    Dim point2(0 To 2) As Double
    point1(0) = 0: point1(1) = 4.25: point1(2) = 0
    point2(0) = 4: point2(1) = 4.25: point2(2) = 0
        
    MsgBox "Mirror the polyline.", , "Mirror Example"
    
    ' Mirror the polyline
    Dim mirrorObj As AcadLWPolyline
    Set mirrorObj = plineObj.Mirror(point1, point2)
    mirrorObj.Color = acRed
    
    ZoomAll
    MsgBox "Mirror completed.", , "Mirror Example"
    
End Sub
Sub Example_Offset()
    ' This example creates a light weight polyline
    ' and then offsets that polyline.
    
    ' Create the polyline
    Dim plineObj As AcadLWPolyline
    Dim points(0 To 11) As Double
    points(0) = 1: points(1) = 1
    points(2) = 1: points(3) = 2
    points(4) = 2: points(5) = 2
    points(6) = 3: points(7) = 2
    points(8) = 4: points(9) = 4
    points(10) = 4: points(11) = 1
    Set plineObj = ThisDrawing.ModelSpace.AddLightWeightPolyline(points)
    plineObj.Closed = True
    ZoomAll
            
    MsgBox "Offset the polyline by 0.25.", , "Offset Example"
    
    ' Offset the polyline
    Dim offsetObj As Variant
    offsetObj = plineObj.offset(0.25)
    offsetObj(0).Color = acRed
    
    ZoomAll
    MsgBox "Offset completed.", , "Offset Example"
    
End Sub
Sub Example_Rotate()
    ' This example creates a light weight polyline
    ' and then rotates that polyline.
    
    ' Create the polyline
    Dim plineObj As AcadLWPolyline
    Dim points(0 To 11) As Double
    points(0) = 1: points(1) = 2
    points(2) = 1: points(3) = 3
    points(4) = 2: points(5) = 3
    points(6) = 3: points(7) = 3
    points(8) = 4: points(9) = 4
    points(10) = 4: points(11) = 2
    Set plineObj = ThisDrawing.ModelSpace.AddLightWeightPolyline(points)
    plineObj.Closed = True
    ZoomAll
            
    MsgBox "Rotate the polyline by 45 degrees.", , "Rotate Example"
    
    ' Define the rotation
    Dim basePoint(0 To 2) As Double
    Dim rotationAngle As Double
    basePoint(0) = 4: basePoint(1) = 4.25: basePoint(2) = 0
    rotationAngle = 0.7853981   ' 45 degrees
    
    ' Rotate the polyline
    plineObj.Rotate basePoint, rotationAngle
    
    ZoomAll
    MsgBox "Rotation completed.", , "Rotate Example"
    
End Sub
Sub Example_ScaleEntity()
    ' This example creates a light weight polyline
    ' and then scales that polyline.
    
    ' Create the polyline
    Dim plineObj As AcadLWPolyline
    Dim points(0 To 11) As Double
    points(0) = 1: points(1) = 2
    points(2) = 1: points(3) = 3
    points(4) = 2: points(5) = 3
    points(6) = 3: points(7) = 3
    points(8) = 4: points(9) = 4
    points(10) = 4: points(11) = 2
    Set plineObj = ThisDrawing.ModelSpace.AddLightWeightPolyline(points)
    plineObj.Closed = True
    ZoomAll
            
    MsgBox "Scale the polyline by 0.5", , "ScaleEntity Example"
    
    ' Define the scale
    Dim basePoint(0 To 2) As Double
    Dim scalefactor As Double
    basePoint(0) = 4: basePoint(1) = 4.25: basePoint(2) = 0
    scalefactor = 0.5
    
    ' Scale the polyline
    plineObj.ScaleEntity basePoint, scalefactor
    
    ZoomAll
    MsgBox "Scale completed.", , "ScaleEntity Example"
    
End Sub
Sub Example_Clear()
    ' This example creates a selection set and several objects.
    ' It then adds the objects to the selection set. It then
    ' clears the objects from the selection set.
    
    ' Create the new selection set
    Dim ssetObj As AcadSelectionSet
    Set ssetObj = ThisDrawing.SelectionSets.Add("TEST_SELECTIONSET")
    
    ' Create a Ray object in model space
    Dim rayObj As AcadRay
    Dim basePoint(0 To 2) As Double
    Dim SecondPoint(0 To 2) As Double
    basePoint(0) = 3#: basePoint(1) = 3#: basePoint(2) = 0#
    SecondPoint(0) = 1#: SecondPoint(1) = 3#: SecondPoint(2) = 0#
    Set rayObj = ThisDrawing.ModelSpace.AddRay(basePoint, SecondPoint)
    
    ' Create a polyline object in model space
    Dim plineObj As AcadLWPolyline
    Dim points(0 To 5) As Double
    points(0) = 3: points(1) = 7
    points(2) = 9: points(3) = 2
    points(4) = 3: points(5) = 5
    Set plineObj = ThisDrawing.ModelSpace.AddLightWeightPolyline(points)
    plineObj.Closed = True

    ' Create a line object in model space
    Dim lineObj As AcadLine
    Dim startPoint(0 To 2) As Double
    Dim endPoint(0 To 2) As Double
    startPoint(0) = 0: startPoint(1) = 0: startPoint(2) = 0
    endPoint(0) = 2: endPoint(1) = 2: endPoint(2) = 0
    Set lineObj = ThisDrawing.ModelSpace.AddLine(startPoint, endPoint)
    
    ' Create a circle object in model space
    Dim circObj As AcadCircle
    Dim centerPt(0 To 2) As Double
    Dim radius As Double
    centerPt(0) = 20: centerPt(1) = 30: centerPt(2) = 0
    radius = 3
    Set circObj = ThisDrawing.ModelSpace.AddCircle(centerPt, radius)

    ' Create an ellipse object in model space
    Dim ellObj As AcadEllipse
    Dim majAxis(0 To 2) As Double
    Dim center(0 To 2) As Double
    Dim radRatio As Double
    center(0) = 5#: center(1) = 5#: center(2) = 0#
    majAxis(0) = 10: majAxis(1) = 20#: majAxis(2) = 0#
    radRatio = 0.3
    Set ellObj = ThisDrawing.ModelSpace.AddEllipse(center, majAxis, radRatio)

    ZoomAll
    
    ' Iterate through the model space collection.
    ' Collect the objects found into an array of objects
    ' to be added to the selection set.
    ReDim ssobjs(0 To ThisDrawing.ModelSpace.count - 1) As AcadEntity
    Dim I As Integer
    For I = 0 To ThisDrawing.ModelSpace.count - 1
        Set ssobjs(I) = ThisDrawing.ModelSpace.Item(I)
    Next
    
    ' Add the array of objects to the selection set
    ssetObj.AddItems ssobjs
    GoSub LISTOBJS
    
    ' Clear the selection set
    ssetObj.Clear
    
    ThisDrawing.Regen acActiveViewport
    GoSub LISTOBJS
Exit Sub
LISTOBJS:
    
        ' List all the objects in the selection set
        If ssetObj.count = 0 Then
            MsgBox "The selection set is empty"
        Else
            For I = 0 To ssetObj.count - 1
                MsgBox "The selection set contains: " & ssetObj.Item(I).ObjectName
            Next
        End If
        Return
    
End Sub
Sub Example_RemoveItems()
    ' This example creates a selection set and several objects.
    ' It then adds the objects to the selection set. It then
    ' removes two of the objects from the selection set.
    
    ' Create the new selection set
    Dim ssetObj As AcadSelectionSet
    Set ssetObj = ThisDrawing.SelectionSets.Add("TEST_SELECTIONSET")
    
    ' Create a Ray object in model space
    Dim rayObj As AcadRay
    Dim basePoint(0 To 2) As Double
    Dim SecondPoint(0 To 2) As Double
    basePoint(0) = 3#: basePoint(1) = 3#: basePoint(2) = 0#
    SecondPoint(0) = 1#: SecondPoint(1) = 3#: SecondPoint(2) = 0#
    Set rayObj = ThisDrawing.ModelSpace.AddRay(basePoint, SecondPoint)
    
    ' Create a polyline object in model space
    Dim plineObj As AcadLWPolyline
    Dim points(0 To 5) As Double
    points(0) = 3: points(1) = 7
    points(2) = 9: points(3) = 2
    points(4) = 3: points(5) = 5
    Set plineObj = ThisDrawing.ModelSpace.AddLightWeightPolyline(points)
    plineObj.Closed = True

    ' Create a line object in model space
    Dim lineObj As AcadLine
    Dim startPoint(0 To 2) As Double
    Dim endPoint(0 To 2) As Double
    startPoint(0) = 0: startPoint(1) = 0: startPoint(2) = 0
    endPoint(0) = 2: endPoint(1) = 2: endPoint(2) = 0
    Set lineObj = ThisDrawing.ModelSpace.AddLine(startPoint, endPoint)
    
    ' Create a circle object in model space
    Dim circObj As AcadCircle
    Dim centerPt(0 To 2) As Double
    Dim radius As Double
    centerPt(0) = 20: centerPt(1) = 30: centerPt(2) = 0
    radius = 3
    Set circObj = ThisDrawing.ModelSpace.AddCircle(centerPt, radius)

    ' Create an ellipse object in model space
    Dim ellObj As AcadEllipse
    Dim majAxis(0 To 2) As Double
    Dim center(0 To 2) As Double
    Dim radRatio As Double
    center(0) = 5#: center(1) = 5#: center(2) = 0#
    majAxis(0) = 10: majAxis(1) = 20#: majAxis(2) = 0#
    radRatio = 0.3
    Set ellObj = ThisDrawing.ModelSpace.AddEllipse(center, majAxis, radRatio)

    ZoomAll
    
    ' Iterate through the model space collection.
    ' Collect the objects found into an array of objects
    ' to be added to the selection set.
    ReDim ssobjs(0 To ThisDrawing.ModelSpace.count - 1) As AcadEntity
    Dim I As Integer
    For I = 0 To ThisDrawing.ModelSpace.count - 1
        Set ssobjs(I) = ThisDrawing.ModelSpace.Item(I)
    Next
    
    ' Add the array of objects to the selection set
    ssetObj.AddItems ssobjs
    GoSub LISTOBJS
    
    ' Remove two of the objects from the selection set
    Dim removeObjects(0 To 1) As AcadEntity
    Set removeObjects(0) = ellObj
    Set removeObjects(1) = circObj
    ssetObj.RemoveItems removeObjects
    MsgBox "The ellipse and circle have been removed from the selection set."
    GoSub LISTOBJS
Exit Sub
LISTOBJS:
    
        ' List all the objects in the selection set
        If ssetObj.count = 0 Then
            MsgBox "The selection set is empty"
        Else
            For I = 0 To ssetObj.count - 1
                MsgBox "The selection set contains: " & ssetObj.Item(I).ObjectName
            Next
        End If
        Return
    
End Sub

Sub Example_GetAttributes()
    ' This example creates a block. It then adds attributes to that
    ' block. The block is then inserted into the drawing to create
    ' a block reference.
    
    ' Create the block
    Dim blockObj As AcadBlock
    Dim insertionPnt(0 To 2) As Double
    insertionPnt(0) = 0#: insertionPnt(1) = 0#: insertionPnt(2) = 0#
    Set blockObj = ThisDrawing.Blocks.Add(insertionPnt, "TESTBLOCK")
    
    ' Define the attribute definition
    Dim attributeObj As AcadAttribute
    Dim height As Double
    Dim mode As Long
    Dim prompt As String
    Dim insertionPoint(0 To 2) As Double
    Dim tag As String
    Dim value As String
    height = 1#
    mode = acAttributeModeVerify
    prompt = "Attribute Prompt"
    insertionPoint(0) = 5#: insertionPoint(1) = 5#: insertionPoint(2) = 0
    tag = "Attribute Tag"
    value = "Attribute Value"
    
    ' Create the attribute definition object in model space
    Set attributeObj = blockObj.AddAttribute(height, mode, prompt, insertionPoint, tag, value)
    
   
    ' Insert the block
    Dim blockRefObj As AcadBlockReference
    insertionPnt(0) = 2#: insertionPnt(1) = 2#: insertionPnt(2) = 0
    Set blockRefObj = ThisDrawing.ModelSpace.InsertBlock(insertionPnt, "TESTBLOCK", 1#, 1#, 1#, 0)
    ZoomAll
    
    ' Get the attributes for the block reference
    Dim varAttributes As Variant
    varAttributes = blockRefObj.GetAttributes
    
    ' Move the attribute tags and values into a string to be displayed in a Msgbox
    Dim strAttributes As String
    Dim I As Integer
    For I = LBound(varAttributes) To UBound(varAttributes)
        strAttributes = strAttributes & "  Tag: " & varAttributes(I).TagString & _
                        "   Value: " & varAttributes(I).textString & "    "
    Next
    MsgBox "The attributes for blockReference " & blockRefObj.name & " are: " & strAttributes, , "GetAttributes Example"
    
    ' Change the value of the attribute
    ' Note: There is no SetAttributes. Once you have the variant array, you have the objects.
    ' Changing them changes the objects in the drawing.
    varAttributes(0).textString = "NEW VALUE!"
    
    ' Get the attributes
    Dim newvarAttributes As Variant
    newvarAttributes = blockRefObj.GetAttributes
    
    ' Again, display the tags and values
    strAttributes = ""
    For I = LBound(varAttributes) To UBound(varAttributes)
        strAttributes = strAttributes & "  Tag: " & varAttributes(I).TagString & _
                        "   Value: " & varAttributes(I).textString & "    "
    Next
    MsgBox "The attributes for blockReference " & blockRefObj.name & " are: " & strAttributes, , "GetAttributes Example"
    
End Sub
Sub Example_ClipBoundary()
    ' This example adds a raster image in model space.
    ' It then clips the image based on a clip boundary.
    
    ' This example uses the "downtown.jpg" found in the sample
    ' directory. If you do not have the image, or it is located
    ' in a different directory, insert a valid path and name for the
    ' imageName variable below.
    
    Dim insertionPoint(0 To 2) As Double
    Dim scalefactor As Double
    Dim rotationAngle As Double
    Dim imageName As String
    Dim rasterObj As AcadRasterImage
    
    imageName = "C:\AutoCAD\sample\downtown.jpg"
    insertionPoint(0) = 5#: insertionPoint(1) = 5#: insertionPoint(2) = 0#
    scalefactor = 2#
    rotationAngle = 0
    
    On Error Resume Next
    ' Creates a raster image in model space
    Set rasterObj = ThisDrawing.ModelSpace.AddRaster(imageName, insertionPoint, scalefactor, rotationAngle)
    
    If Err.Description = "Filer error" Then
        MsgBox imageName & " could not be found."
        Exit Sub
    End If
    
    ZoomAll
    MsgBox "Clip the image?", , "ClipBoundary Example"
    
    ' Establish the clip boundary with an array of points
    Dim clipPoints(0 To 9) As Double
    clipPoints(0) = 6: clipPoints(1) = 6.75
    clipPoints(2) = 7: clipPoints(3) = 6
    clipPoints(4) = 6: clipPoints(5) = 5
    clipPoints(6) = 5: clipPoints(7) = 6
    clipPoints(8) = 6: clipPoints(9) = 6.75
    
    ' Clip the image
    rasterObj.ClipBoundary clipPoints
    
    ' Enable the display of the clip
    rasterObj.ClippingEnabled = True
    ThisDrawing.Regen acActiveViewport
    MsgBox "The image has been clipped.", , "ClipBoundary Example"
End Sub
Sub Example_ClippingEnabled()
    ' This example adds a raster image in model space.
    ' It then clips the image based on a clip boundary,
    ' and toggles the display of the clipping.
    
    Dim insertionPoint(0 To 2) As Double
    Dim scalefactor As Double
    Dim rotationAngle As Double
    Dim imageName As String
    Dim rasterObj As AcadRasterImage
    
    imageName = "C:\AutoCAD\sample\downtown.jpg"
    insertionPoint(0) = 5#: insertionPoint(1) = 5#: insertionPoint(2) = 0#
    scalefactor = 2#
    rotationAngle = 0
    
    On Error Resume Next
    ' Creates a raster image in model space
    Set rasterObj = ThisDrawing.ModelSpace.AddRaster(imageName, insertionPoint, scalefactor, rotationAngle)
    
    If Err.Description = "Filer error" Then
        MsgBox imageName & " could not be found."
        Exit Sub
    End If
    
    ZoomAll
    MsgBox "Clip the image?", , "ClipBoundary Example"
    
    ' Establish the clip boundary with an array of points
    Dim clipPoints(0 To 9) As Double
    clipPoints(0) = 6: clipPoints(1) = 6.75
    clipPoints(2) = 7: clipPoints(3) = 6
    clipPoints(4) = 6: clipPoints(5) = 5
    clipPoints(6) = 5: clipPoints(7) = 6
    clipPoints(8) = 6: clipPoints(9) = 6.75
    
    ' Clip the image
    rasterObj.ClipBoundary clipPoints
    
    ' Enable the display of the clip
    rasterObj.ClippingEnabled = True
     ThisDrawing.Regen acActiveViewport
   MsgBox "Turn off the display of the clipped image.", , "ClippingEnabled Example"
    
    ' Disable the display of the clip
    rasterObj.ClippingEnabled = False
    ThisDrawing.Regen acActiveViewport
    MsgBox "Display off.", , "ClippingEnabled Example"
    
End Sub
Sub Example_Delete()
    ' This example creates a Layer named "TEST".
    ' It then iterates the Layers collection and displays
    ' the names of the available layers.
    ' It then deletes the layer "TEST", and again iterates
    ' the layers collection and displays the names of
    ' available layers.
    
    Dim layerObj As AcadLayer
    
    ' Create the new layer
    Set layerObj = ThisDrawing.Layers.Add("TEST")
    
    ' Display the names of the layers in the drawing
    GoSub DISPLAYLAYERS
    
    ' Delete the layer "TEST"
    layerObj.Delete
    
    ' Display the names of the layers remaining in the drawing
    GoSub DISPLAYLAYERS
    
    Exit Sub
    
DISPLAYLAYERS:
    Dim entry As AcadLayer
    Dim layerNames As String
    layerNames = ""
    For Each entry In ThisDrawing.Layers
       layerNames = layerNames & entry.name & ", "
    Next
    MsgBox "The drawing consists of the following layers:" & Chr(13) & Chr(10) & layerNames, , "Delete Example"
    Return
    
End Sub

Sub Example_DeleteFitPoint()
    ' This example creates a spline object in model space.
    ' It then deletes a fit point from the spline.

    ' Create the spline
    Dim splineObj As AcadSpline
    Dim noOfPoints As Integer
    Dim startTan(0 To 2) As Double
    Dim endTan(0 To 2) As Double
    Dim fitPoints(0 To 8) As Double
    
    noOfPoints = 3
    startTan(0) = 0.5: startTan(1) = 0.5: startTan(2) = 0
    endTan(0) = 0.5: endTan(1) = 0.5: endTan(2) = 0
    fitPoints(0) = 1: fitPoints(1) = 1: fitPoints(2) = 0
    fitPoints(3) = 5: fitPoints(4) = 5: fitPoints(5) = 0
    fitPoints(6) = 10: fitPoints(7) = 0: fitPoints(8) = 0
    Set splineObj = ThisDrawing.ModelSpace.AddSpline(fitPoints, startTan, endTan)
    ZoomAll
    MsgBox "Delete the first fit point", , "DeleteFitPoint Example"
    
    ' Delete the first fit point in the spline
    splineObj.DeleteFitPoint 0
    ThisDrawing.Regen True
    MsgBox "A fit point has been deleted at Index:0", , "DeleteFitPoint Example"

End Sub
Sub Example_DisplayMethod()
    ' This example creates a paperspace viewport and makes it active.
    
    Dim newPViewport As AcadPViewport
    Dim centerPoint(0 To 2) As Double
    Dim height As Double
    Dim width As Double
    height = 30#
    width = 40#
    centerPoint(0) = 30#: centerPoint(1) = 30#: centerPoint(2) = 0#
    
    ' Create a paperspace Viewport object
    ThisDrawing.ActiveSpace = acPaperSpace
    Set newPViewport = ThisDrawing.PaperSpace.AddPViewport(centerPoint, width, height)
    ZoomAll
    newPViewport.DISPLAY True
    
    ' Before making a pViewport active,
    ' the mspace property needs to be True
    ThisDrawing.mspace = True
    ThisDrawing.ActivePViewport = newPViewport
End Sub
Sub Example_DistanceToReal()
    ' This example passes several different distances in
    ' different units to be converted to real values.
    
    Dim distAsString As String
    Dim unit As Long
    Dim distAsReal As Double
    
    ' Convert the distance to a real in scientific units
    unit = acScientific
    distAsString = "1.75E+01"
    distAsReal = ThisDrawing.Utility.DistanceToReal(distAsString, unit)
    MsgBox "1.75E+01 converts to " & distAsReal & " in scientific units.", , "DistanceToReal Example"
    
    ' Convert the distance to a real in decimal units
    unit = acDecimal
    distAsString = "17.5"
    distAsReal = ThisDrawing.Utility.DistanceToReal(distAsString, unit)
    MsgBox "1.75 converts to " & distAsReal & " in decimal units.", , "DistanceToReal Example"
    
    ' Convert the distance to a real in engineering units
    unit = acEngineering
    distAsString = "1'-5.50"""
    distAsReal = ThisDrawing.Utility.DistanceToReal(distAsString, unit)
    MsgBox "1'-5.50"" converts to " & distAsReal & " in engineering units.", , "DistanceToReal Example"
    
    
    ' Convert the distance to a real in architectural units
    unit = acArchitectural
    distAsString = "1'-5 1/2"""
    distAsReal = ThisDrawing.Utility.DistanceToReal(distAsString, unit)
    MsgBox "1'-5 1/2"" converts to " & distAsReal & " in architectural units.", , "DistanceToReal Example"
    
    ' Convert the distance to a real in fractional units
    unit = acFractional
    distAsString = "17 1/2"
    distAsReal = ThisDrawing.Utility.DistanceToReal(distAsString, unit)
    MsgBox "1'-5 1/2"" converts to " & distAsReal & " in fractional units.", , "DistanceToReal Example"
    
End Sub
Sub Example_ElevateOrder()
    ' This example creates a spline object in model space.
    ' It then elevates the order of the spline.

    ' Create the spline
    Dim splineObj As AcadSpline
    Dim noOfPoints As Integer
    Dim startTan(0 To 2) As Double
    Dim endTan(0 To 2) As Double
    Dim fitPoints(0 To 8) As Double
    
    noOfPoints = 3
    startTan(0) = 0.5: startTan(1) = 0.5: startTan(2) = 0
    endTan(0) = 0.5: endTan(1) = 0.5: endTan(2) = 0
    fitPoints(0) = 1: fitPoints(1) = 1: fitPoints(2) = 0
    fitPoints(3) = 5: fitPoints(4) = 5: fitPoints(5) = 0
    fitPoints(6) = 10: fitPoints(7) = 0: fitPoints(8) = 0
    Set splineObj = ThisDrawing.ModelSpace.AddSpline(fitPoints, startTan, endTan)
    ZoomAll
    MsgBox "The current order of the spline is " & splineObj.Degree + 1, , "ElevateOrder Example"
    
    ' Elevate the order of the spline
    splineObj.ElevateOrder (splineObj.Degree + 10)
    ThisDrawing.Regen True
    MsgBox "The order of the spline has been raised to " & splineObj.Degree + 1, , "ElevateOrder Example"
    
End Sub
Sub Example_Export()
    ' This example exports the current drawing to DXF format.
    ' Note that a valid selection set must be provided, even
    ' though the contents of the selection set are ignored.
    
    
    ' Define the name for the exported file
    Dim exportFile As String
    exportFile = "C:\AutoCAD\DXFExprt"     ' Adjust path to match your system
    
    ' Create an empty selection set
    Dim sset As AcadSelectionSet
    Set sset = ThisDrawing.SelectionSets.Add("TEST")
    
    ' Export the current drawing to the file specified above.
    ThisDrawing.Export exportFile, "DXF", sset
    
End Sub
Sub Example_GetAngle()
    ' This example demonstrates 4 different ways to retrieve
    ' an angle from the user using the GetAngle method.
    
    Dim retAngle As Double
    
    ' Return the angle in radians with a prompt
    retAngle = ThisDrawing.Utility.GetAngle(, "Enter an angle: ")
    MsgBox "The angle entered was " & retAngle, , "GetAngle Example"
    
    ' Return the angle in radians without any prompt
    retAngle = ThisDrawing.Utility.GetAngle()
    MsgBox "The angle entered was " & retAngle, , "GetAngle Example"
    
    ' Return the angle in radians with a prompt and an angle base point
    Dim basePnt(0 To 2) As Double
    basePnt(0) = 2#: basePnt(1) = 2#: basePnt(2) = 0#
    retAngle = ThisDrawing.Utility.GetAngle(basePnt, "Enter an angle: ")
    MsgBox "The angle entered was " & retAngle, , "GetAngle Example"
    
    ' Return the angle in radians with an angle base point but no prompt
    retAngle = ThisDrawing.Utility.GetAngle(basePnt)
    MsgBox "The angle entered was " & retAngle, , "GetAngle Example"
    
End Sub
Sub Example_AngleFromXAxis()
    ' This example finds the angle, in radians, between the X axis
    ' and a line defined by two points.
    
    Dim pt1(0 To 2) As Double
    Dim pt2(0 To 2) As Double
    Dim retAngle As Double
    
    pt1(0) = 2: pt1(1) = 5: pt1(2) = 0
    pt2(0) = 5: pt2(1) = 2: pt2(2) = 0
    
    ' Return the angle
    retAngle = ThisDrawing.Utility.AngleFromXAxis(pt1, pt2)
    
    ' Create the line for a visual reference
    Dim lineObj As AcadLine
    Set lineObj = ThisDrawing.ModelSpace.AddLine(pt1, pt2)
    ZoomAll
    
    ' Display the angle found
    MsgBox "The angle in radians between the X axis and the line is " & retAngle, , "AngleFromXAxis Example"
    
End Sub
Sub Example_GetBoundingBox()
    ' This example creates a line in model space. It then finds the
    ' bounding box for the line and displays the corners of the box.
    
    Dim startPoint(0 To 2) As Double
    Dim endPoint(0 To 2) As Double
    Dim lineObj As AcadLine

    ' Create the Line object in model space
    startPoint(0) = 2#: startPoint(1) = 2#: startPoint(2) = 0#
    endPoint(0) = 4#: endPoint(1) = 4#: endPoint(2) = 0#
    Set lineObj = ThisDrawing.ModelSpace.AddLine(startPoint, endPoint)
    ZoomAll
    
    Dim minExt As Variant
    Dim maxExt As Variant
    
    ' Return the bounding box for the line and return the minimum
    ' and maximum extents of the box in the minExt and maxExt variables.
    lineObj.GetBoundingBox minExt, maxExt
    
    ' Print the min and max extents
    MsgBox "The extents of the bounding box for the line are:" & vbCrLf _
         & "Min Extent: " & minExt(0) & "," & minExt(1) & "," & minExt(2) _
         & vbCrLf & "Max Extent: " & maxExt(0) & "," & maxExt(1) & "," & maxExt(2), vbInformation, "GetBoundingBox Example"
         
End Sub
Sub Example_GetCorner()
    ' This example provides a base point and prompts the user to
    ' input the second point to make a rectangle.
    
    Dim returnPnt As Variant
    Dim basePnt(0 To 2) As Double
    basePnt(0) = 2#: basePnt(1) = 2#: basePnt(2) = 0#
    
    ' Prompt the user to pick second point and returns the point
    returnPnt = ThisDrawing.Utility.GetCorner(basePnt, "Enter Other corner: ")
    
    ' Display the point picked
    MsgBox "The point picked was " & returnPnt(0) & ", " & returnPnt(1) & ", " & returnPnt(2), , "GetCorner Example"
    
End Sub
Sub Example_GetDistance()
    ' This example returns the distance entered by the user.
    
    Dim returnDist As Double
    Dim basePnt(0 To 2) As Double
    basePnt(0) = 0#: basePnt(1) = 0#: basePnt(2) = 0#
    
    ' Return the value entered by user. A prompt is provided.
    returnDist = ThisDrawing.Utility.GetDistance(, "Enter distance: ")
    MsgBox "The distance entered was " & returnDist & vbCrLf & _
            "(Enter the next value without prompting.)", , "GetDistance Example"
    
    ' Return the value entered by user. No prompt is provided.
    returnDist = ThisDrawing.Utility.GetDistance()
    MsgBox "The distance entered was " & returnDist, , "GetDistance Example"
    
    ' Return the value entered by user. A base point and prompt is provided.
    returnDist = ThisDrawing.Utility.GetDistance(basePnt, "Enter a distance: ")
    MsgBox "The distance entered was " & returnDist, , "GetDistance Example"
    
End Sub
Sub Example_GetEntity()
    ' This example creates several objects in model space. It then
    ' prompts the user to select an object. The example continues to
    ' have the user select objects until the user selects in empty space.
    
    ' Create a Ray object in model space
    Dim rayObj As AcadRay
    Dim basePoint(0 To 2) As Double
    Dim SecondPoint(0 To 2) As Double
    basePoint(0) = 3#: basePoint(1) = 3#: basePoint(2) = 0#
    SecondPoint(0) = 1#: SecondPoint(1) = 3#: SecondPoint(2) = 0#
    Set rayObj = ThisDrawing.ModelSpace.AddRay(basePoint, SecondPoint)
    
    ' Create a polyline object in model space
    Dim plineObj As AcadLWPolyline
    Dim points(0 To 5) As Double
    points(0) = 3: points(1) = 7
    points(2) = 9: points(3) = 2
    points(4) = 3: points(5) = 5
    Set plineObj = ThisDrawing.ModelSpace.AddLightWeightPolyline(points)
    plineObj.Closed = True

    ' Create a line object in model space
    Dim lineObj As AcadLine
    Dim startPoint(0 To 2) As Double
    Dim endPoint(0 To 2) As Double
    startPoint(0) = 0: startPoint(1) = 0: startPoint(2) = 0
    endPoint(0) = 2: endPoint(1) = 2: endPoint(2) = 0
    Set lineObj = ThisDrawing.ModelSpace.AddLine(startPoint, endPoint)
    
    ' Create a circle object in model space
    Dim circObj As AcadCircle
    Dim centerPt(0 To 2) As Double
    Dim radius As Double
    centerPt(0) = 20: centerPt(1) = 30: centerPt(2) = 0
    radius = 3
    Set circObj = ThisDrawing.ModelSpace.AddCircle(centerPt, radius)

    ' Create an ellipse object in model space
    Dim ellObj As AcadEllipse
    Dim majAxis(0 To 2) As Double
    Dim center(0 To 2) As Double
    Dim radRatio As Double
    center(0) = 5#: center(1) = 5#: center(2) = 0#
    majAxis(0) = 10: majAxis(1) = 20#: majAxis(2) = 0#
    radRatio = 0.3
    Set ellObj = ThisDrawing.ModelSpace.AddEllipse(center, majAxis, radRatio)

    ZoomAll
    
    ' Begin the selection
    Dim returnObj As AcadObject
    Dim basePnt As Variant
    
    On Error Resume Next
    
    ' The following example waits for a selection from the user
RETRY:
    ThisDrawing.Utility.GetEntity returnObj, basePnt, "Select an object"
    
    If Err <> 0 Then
        Err.Clear
        MsgBox "Good Bye.", , "GetEntity Example"
        Exit Sub
    Else
        returnObj.Color = acRed
        returnObj.Update
        MsgBox "The object type is: " & returnObj.EntityName, , "GetEntity Example"
        returnObj.Color = acByLayer
        returnObj.Update
    End If
    
    GoTo RETRY
End Sub
Sub Example_GetGridSpacing()
    ' This example turns on the grid for the current viewport.
    ' It then finds the current grid spacing, and changes that spacing.
    
    ' Find the current active viewport
    Dim viewportObj As AcadViewport
    Set viewportObj = ThisDrawing.ActiveViewport
    
    ' Turn on the grid and reset the viewport to see it come on.
    viewportObj.GridOn = True
    ThisDrawing.ActiveViewport = viewportObj
    
    ' Find the current grid spacing
    Dim XSpacing As Double
    Dim YSpacing As Double
    
    viewportObj.GetGridSpacing XSpacing, YSpacing
    MsgBox "X =" & XSpacing & ", Y =" & YSpacing, , "GetGridSpacing Example"
    
    ' Change the grid spacing
    XSpacing = XSpacing * 0.5
    YSpacing = YSpacing * 0.5
    viewportObj.SetGridSpacing XSpacing, YSpacing
    ThisDrawing.ActiveViewport = viewportObj
    MsgBox "X =" & XSpacing & ", Y =" & YSpacing, , "GetGridSpacing Example"
   
End Sub
Sub Example_GetInput()
    ' This example prompts for user input of a point. By using the
    ' InitializeUserInput method to define a keyword list, it can also
    ' return keywords entered by the user.
    
    On Error Resume Next
    
    ' Define the valid keywords
    Dim keywordList As String
    keywordList = "Keyword1 Keyword2"
    
    ' Call InitializeUserInput to setup the keywords
    ThisDrawing.Utility.InitializeUserInput 128, keywordList
    
    ' Get the user input
    Dim returnPnt As Variant
    returnPnt = ThisDrawing.Utility.GetPoint(, "Enter a point(Keyword1, Keyword2): ")
    If Err Then
         If StrComp(Err.Description, "User input is a keyword", 1) = 0 Then
         ' One of the keywords was entered
             Dim inputString As String
             Err.Clear
             inputString = ThisDrawing.Utility.GetInput
             MsgBox "You entered the keyword: " & inputString
         Else
             MsgBox "Error selecting the point: " & Err.Description
             Err.Clear
         End If
    Else
        ' Display point coordinates
        MsgBox "The WCS of the point is: " & returnPnt(0) & ", " & returnPnt(1) & ", " & returnPnt(2), , "GetInput Example"
    End If
    
End Sub
Sub Example_InitializeUserInput()
    ' This example prompts for user input of a point. By using the
    ' InitializeUserInput method to define a keyword list, it can also
    ' return keywords entered by the user.
    
    On Error Resume Next
    
    ' Define the valid keywords
    Dim keywordList As String
    keywordList = "Keyword1 Keyword2"
    
    ' Call InitializeUserInput to setup the keywords
    ThisDrawing.Utility.InitializeUserInput 128, keywordList
    
    ' Get the user input
    Dim returnPnt As Variant
    returnPnt = ThisDrawing.Utility.GetPoint(, "Enter a point(Keyword1, Keyword2): ")
    If Err Then
         If StrComp(Err.Description, "User input is a keyword", 1) = 0 Then
         ' One of the keywords was entered
             Dim inputString As String
             Err.Clear
             inputString = ThisDrawing.Utility.GetInput
             MsgBox "You entered the keyword: " & inputString
         Else
             MsgBox "Error selecting the point: " & Err.Description
             Err.Clear
         End If
    Else
        ' Display point coordinates
        MsgBox "The WCS of the point is: " & returnPnt(0) & ", " & returnPnt(1) & ", " & returnPnt(2), , "GetInput Example"
    End If
    
End Sub
Sub Example_GetInteger()
    ' This example returns the integer entered by the user.
    
    Dim returnInt As Integer
    
    ' Return the value entered by user. A prompt is provided.
    returnInt = ThisDrawing.Utility.GetInteger("Enter an integer: ")
    MsgBox "The integer entered was " & returnInt & vbCrLf & _
            "(Enter the next value without prompting.)", , "GetInteger Example"
    
    ' Return the value entered by user. No prompt is provided.
    returnInt = ThisDrawing.Utility.GetInteger()
    MsgBox "The integer entered was " & returnInt, , "GetInteger Example"
    
End Sub
Sub Example_GetInterfaceObject()
    ' This example returns top level object of another application.
    On Error GoTo ERRORHANDLER
    
    Dim poly As Object
    Set poly = ThisDrawing.Application.GetInterfaceObject("Polycad.Application")

ERRORHANDLER:
    MsgBox Err.Description, , "GetInterfaceObject Example"
    
End Sub

Sub Example_GetKeyword()
    ' This example uses Getkeyword to return a keyword entered by the user.
    ' InitializeUserInput establishes the valid keywords.
    
    ' Define the list of valid keywords
    Dim kwordList As String
    kwordList = "Width Height Depth"
    ThisDrawing.Utility.InitializeUserInput 1, kwordList
            
    ' Prompt the user to input any of the keywords. Return "Width", "Height" or "Depth" in
    ' the returnString variable depending on whether the user input "W", "H" or "D".
    Dim returnString As String
    returnString = ThisDrawing.Utility.GetKeyword("Enter a keyword (Height)(Width)(Depth): ")
    MsgBox "You entered " & returnString, , "GetKeyword Example"
    
End Sub
Sub Example_GetLoopAt()
    ' This example creates an associative hatch in model space.
    ' It then finds the objects that make up the first loop of the hatch.
    
    Dim hatchObj As AcadHatch
    Dim patternName As String
    Dim PatternType As Long
    Dim bAssociativity As Boolean
    
    ' Define the hatch
    patternName = "ANSI31"
    PatternType = 0
    bAssociativity = True
    
    ' Create the associative Hatch object
    Set hatchObj = ThisDrawing.ModelSpace.AddHatch(PatternType, patternName, bAssociativity)
    
    ' Create the outer loop for the hatch.
    ' An arc and a line are used to create a closed loop.
    Dim outerLoop(0 To 1) As AcadEntity
    Dim center(0 To 2) As Double
    Dim radius As Double
    Dim startAngle As Double
    Dim endAngle As Double
    center(0) = 5: center(1) = 3: center(2) = 0
    radius = 3
    startAngle = 0
    endAngle = 3.141592
    Set outerLoop(0) = ThisDrawing.ModelSpace.AddArc(center, radius, startAngle, endAngle)
    Set outerLoop(1) = ThisDrawing.ModelSpace.AddLine(outerLoop(0).startPoint, outerLoop(0).endPoint)
        
    ' Append the outer loop to the hatch object
    hatchObj.AppendOuterLoop (outerLoop)
    
    ' Append the first circle as one inner loop
    Dim innerLoop1(0) As AcadEntity
    center(0) = 5: center(1) = 4.5: center(2) = 0
    radius = 1
    Set innerLoop1(0) = ThisDrawing.ModelSpace.AddCircle(center, radius)
    hatchObj.AppendInnerLoop (innerLoop1)
    
    ' Append the second circle as the other inner loop
    Dim innerLoop2(0) As AcadEntity
    radius = 0.5
    Set innerLoop2(0) = ThisDrawing.ModelSpace.AddCircle(center, radius)
    hatchObj.AppendInnerLoop (innerLoop2)
    
    ' Evaluate and display the hatch
    hatchObj.Evaluate
    ThisDrawing.Regen True
    
    ' Find the objects that make up the first loop
    Dim loopObjs As Variant
    hatchObj.GetLoopAt 0, loopObjs
    
    ' Find the types of the objects in the loop
    Dim I As Integer
    Dim objName As String
    objName = ""
    For I = LBound(loopObjs) To UBound(loopObjs)
        objName = objName & loopObjs(I).EntityName & ", "
    Next
    
    MsgBox "The objects in the first loop of the hatch are: " & objName, , "GetLoopAt Example"
       
End Sub
Sub Example_GetName()
    ' This example creates a dictionary and adds
    ' a custom object to that dictionary. It then
    ' finds the name of the object in the dictionary.
    
    Dim dictObj As AcadDictionary
    Set dictObj = ThisDrawing.Dictionaries.Add("TEST_DICTIONARY")
    
    ' Load the ARX application that defines the custom object.
    ' Note: The application listed here does not exist and
    ' will cause an error when run. Change the application name
    ' to the path and name of your ARX Application.
    ThisDrawing.Application.LoadArx ("MyARXApp.dll")
    
    ' Create the custom object in the dictionary
    Dim keyName As String
    Dim className As String
    Dim customObj As AcadObject
    
    keyName = "OBJ1"
    className = "CAsdkDictObject"
    
    Set customObj = dictObj.AddObject(keyName, className)
    
    ' Find the keyword name of an object in the dictionary
    keyName = dictObj.GetName(customObj)
    
End Sub
Sub Example_GetInvisibleEdge()
    ' This example creates a 3D face in model space.
    ' It then toggles the visibility of the  first edge.

    Dim faceObj As Acad3DFace
    Dim point1(0 To 2) As Double
    Dim point2(0 To 2) As Double
    Dim point3(0 To 2) As Double
    Dim point4(0 To 2) As Double
    
    ' Define the four coordinates of the face
    point1(0) = 1#: point1(1) = 1#: point1(2) = 0#
    point2(0) = 5#: point2(1) = 1#: point2(2) = 1#
    point3(0) = 1#: point3(1) = 10#: point3(2) = 0#
    point4(0) = 5#: point4(1) = 5#: point4(2) = 1#
    
    ' Create the 3DFace object in model space
    Set faceObj = ThisDrawing.ModelSpace.Add3DFace(point1, point2, point3, point4)
    ZoomAll
    
    ' Find the current visibility status of the first edge of the face
    Dim visStatus As Boolean
    visStatus = faceObj.GetInvisibleEdge(0)
    MsgBox "The first face is currently " & IIf(faceObj.GetInvisibleEdge(0), "visible.", "invisible."), , "GetInvisibleEdge Example"
    
    ' Toggle the visibility of the first edge of the face
    faceObj.SetInvisibleEdge 0, Not (visStatus)
    ThisDrawing.Regen False
    MsgBox "The first face is now " & IIf(faceObj.GetInvisibleEdge(0), "visible.", "invisible."), , "GetInvisibleEdge Example"
    
End Sub
Sub Example_SetInvisibleEdge()
    ' This example creates a 3D face in model space.
    ' It then toggles the visibility of the  first edge.

    Dim faceObj As Acad3DFace
    Dim point1(0 To 2) As Double
    Dim point2(0 To 2) As Double
    Dim point3(0 To 2) As Double
    Dim point4(0 To 2) As Double
    
    ' Define the four coordinates of the face
    point1(0) = 1#: point1(1) = 1#: point1(2) = 0#
    point2(0) = 5#: point2(1) = 1#: point2(2) = 1#
    point3(0) = 1#: point3(1) = 10#: point3(2) = 0#
    point4(0) = 5#: point4(1) = 5#: point4(2) = 1#
    
    ' Create the 3DFace object in model space
    Set faceObj = ThisDrawing.ModelSpace.Add3DFace(point1, point2, point3, point4)
    ZoomAll
    
    ' Find the current visibility status of the first edge of the face
    Dim visStatus As Boolean
    visStatus = faceObj.GetInvisibleEdge(0)
    MsgBox "The first face is currently " & IIf(faceObj.GetInvisibleEdge(0), "visible.", "invisible."), , "GetInvisibleEdge Example"
    
    ' Toggle the visibility of the first edge of the face
    faceObj.SetInvisibleEdge 0, Not (visStatus)
    ThisDrawing.Regen False
    MsgBox "The first face is now " & IIf(faceObj.GetInvisibleEdge(0), "visible.", "invisible."), , "GetInvisibleEdge Example"
    
End Sub
Sub Example_GetOrientation()
    ' This example demonstrates 3 different ways to retrieve
    ' an orientation from the user using the GetOrientation method.
    
    Dim retOrientation As Double
    
    ' Return the Orientation in radians with a prompt
    retOrientation = ThisDrawing.Utility.GetOrientation(, "Enter an Orientation: ")
    MsgBox "The Orientation entered was " & retOrientation & vbCrLf & _
            "(Enter the next value without prompting.)", , "GetOrientation Example"
    
    ' Return the Orientation in radians without any prompt
    retOrientation = ThisDrawing.Utility.GetOrientation()
    MsgBox "The Orientation entered was " & retOrientation, , "GetOrientation Example"
    
    ' Return the Orientation in radians with a prompt and an Orientation base point
    Dim basePnt(0 To 2) As Double
    basePnt(0) = 2#: basePnt(1) = 2#: basePnt(2) = 0#
    retOrientation = ThisDrawing.Utility.GetOrientation(basePnt, "Enter an Orientation: ")
    MsgBox "The Orientation entered was " & retOrientation, , "GetOrientation Example"
        
End Sub
Sub Example_GetPoint()
    ' This example returns a point entered by the user.
    
    Dim returnPnt As Variant
    
    ' Return a point using a prompt
    returnPnt = ThisDrawing.Utility.GetPoint(, "Enter a point: ")
    MsgBox "The WCS of the point is: " & returnPnt(0) & ", " & returnPnt(1) & ", " & returnPnt(2) & vbCrLf & _
            "(Enter the next value without prompting.)", , "GetPoint Example"
    
    ' Return a point, no prompt
    returnPnt = ThisDrawing.Utility.GetPoint
    MsgBox "The WCS of the point is: " & returnPnt(0) & ", " & returnPnt(1) & ", " & returnPnt(2), , "GetPoint Example"
    
    ' Return a point using a base point and a prompt
    Dim basePnt(0 To 2) As Double
    basePnt(0) = 2#: basePnt(1) = 2#: basePnt(2) = 0#
    returnPnt = ThisDrawing.Utility.GetPoint(basePnt, "Enter a point: ")
    MsgBox "The WCS of the point is: " & returnPnt(0) & ", " & returnPnt(1) & ", " & returnPnt(2)
    
    ' Create a line from the base point and the last point entered
    Dim lineObj As AcadLine
    Set lineObj = ThisDrawing.ModelSpace.AddLine(basePnt, returnPnt)
    ZoomAll
    
End Sub
Sub Example_GetProjectFilePath()
    ' This example finds the current project file information.
    
    Dim preferences As AcadPreferences
    Set preferences = ThisDrawing.Application.preferences
    
    ' Get the current project file information
    Dim currProjPath As String
    Dim currProjName As Variant
    currProjName = ThisDrawing.GetVariable("PROJECTNAME")
    If currProjName <> "" Then
        currProjPath = preferences.Files.GetProjectFilePath(currProjName)
    End If
    If currProjPath = "" Then
        MsgBox "There is no current project file or path. ", , "GetProjectFilePath Example"
    Else
        MsgBox "The current project file path is: " & currProjPath, , "GetProjectFilePath Example"
    End If
        
End Sub
Sub Example_SetProjectFilePath()
    ' This example finds the current project file information, changes
    ' that information, and finally resets the information back to the
    ' original values.
    
    Dim preferences As AcadPreferences
    Set preferences = ThisDrawing.Application.preferences
    
    ' Get the current project file information
    Dim currProjPath As String
    Dim currProjName As Variant
    currProjName = ThisDrawing.GetVariable("PROJECTNAME")
    If currProjName <> "" Then
        currProjPath = preferences.GetProjectFilePath(currProjName)
    End If
    If currProjPath = "" Then
        MsgBox "There is no current project file or path. ", , "SetProjectFilePath Example"
    Else
        MsgBox "The current project file path is: " & currProjPath, , "SetProjectFilePath Example"
        ' Set new project file information.
        ' Change drive/path as necessary to match your system
        Dim newProjPath As String
        newProjPath = "C:/AutoCAD/"
        
        preferences.SetProjectFilePath currProjName, newProjPath
        MsgBox "The new project file path is: " & newProjPath, , "GetProjectFilePath Example"
        
        ' Reset the project file information
        preferences.SetProjectFilePath currProjName, currProjPath
        MsgBox "The project file path has been reset to: " & currProjPath, , "GetProjectFilePath Example"
    End If
    
End Sub

Sub Example_PolarPoint()
    ' This example finds the coordinate of a point that is a given
    ' distance and angle from a base point.
    
    Dim polarPnt As Variant
    Dim basePnt(0 To 2) As Double
    Dim angle As Double
    Dim distance As Double
    
    basePnt(0) = 2#: basePnt(1) = 2#: basePnt(2) = 0#
    angle = 0.1744444   ' 45 degrees
    distance = 5
    polarPnt = ThisDrawing.Utility.PolarPoint(basePnt, angle, distance)
    
    ' Create a line from the base point to the polar point
    Dim lineObj As AcadLine
    Set lineObj = ThisDrawing.ModelSpace.AddLine(basePnt, polarPnt)
    ZoomAll
    
End Sub
Sub Example_GetReal()
    ' This example returns the Real entered by the user.
    
    Dim returnReal As Double
    
    ' Return the value entered by user. A prompt is provided.
    returnReal = ThisDrawing.Utility.GetReal("Enter an Real: ")
    MsgBox "The real entered was " & returnReal & vbCrLf & _
            "(Enter the next value without prompting.)", , "GetReal Example"
    
    ' Return the value entered by user. No prompt is provided.
    returnReal = ThisDrawing.Utility.GetReal()
    MsgBox "The real entered was " & returnReal, , "GetReal Example"
    
End Sub
Sub Example_GetSnapSpacing()
    ' This example finds the current Snap spacing, and changes that spacing.
    
    ' Find the current active viewport
    Dim viewportObj As AcadViewport
    Set viewportObj = ThisDrawing.ActiveViewport
    
    ' Turn on Snaping and reset the viewport.
    viewportObj.SnapOn = True
    ThisDrawing.ActiveViewport = viewportObj
    
    ' Find the current Snap spacing
    Dim XSpacing As Double
    Dim YSpacing As Double
    
    viewportObj.GetSnapSpacing XSpacing, YSpacing
    MsgBox "X =" & XSpacing & ", Y =" & YSpacing, Title:="GetSnapSpacing Example"
    
    ' Change the Snap spacing
    XSpacing = XSpacing * 0.5
    YSpacing = YSpacing * 0.5
    viewportObj.SetSnapSpacing XSpacing, YSpacing
    ThisDrawing.ActiveViewport = viewportObj
    MsgBox "X =" & XSpacing & ", Y =" & YSpacing, Title:="GetSnapSpacing Example"
   
End Sub
Sub Example_SetSnapSpacing()
    ' This example finds the current Snap spacing, and changes that spacing.
    
    ' Find the current active viewport
    Dim viewportObj As AcadViewport
    Set viewportObj = ThisDrawing.ActiveViewport
    
    ' Turn on Snaping and reset the viewport.
    viewportObj.SnapOn = True
    ThisDrawing.ActiveViewport = viewportObj
    
    ' Find the current Snap spacing
    Dim XSpacing As Double
    Dim YSpacing As Double
    
    viewportObj.GetSnapSpacing XSpacing, YSpacing
    MsgBox "X =" & XSpacing & ", Y =" & YSpacing, Title:="SetSnapSpacing Example"
    
    ' Change the Snap spacing
    XSpacing = XSpacing * 0.5
    YSpacing = YSpacing * 0.5
    viewportObj.SetSnapSpacing XSpacing, YSpacing
    ThisDrawing.ActiveViewport = viewportObj
    MsgBox "X =" & XSpacing & ", Y =" & YSpacing, Title:="SetSnapSpacing Example"
   
End Sub
Sub Example_SetGridSpacing()
    ' This example turns on the grid for the current viewport.
    ' It then finds the current grid spacing, and changes that spacing.
    
    ' Find the current active viewport
    Dim viewportObj As AcadViewport
    Set viewportObj = ThisDrawing.ActiveViewport
    
    ' Turn on the grid and reset the viewport to see it come on.
    viewportObj.GridOn = True
    ThisDrawing.ActiveViewport = viewportObj
    
    ' Find the current grid spacing
    Dim XSpacing As Double
    Dim YSpacing As Double
    
    viewportObj.GetGridSpacing XSpacing, YSpacing
    MsgBox "X =" & XSpacing & ", Y =" & YSpacing, , "SetGridSpacing Example"
    
    ' Change the grid spacing
    XSpacing = XSpacing * 0.5
    YSpacing = YSpacing * 0.5
    viewportObj.SetGridSpacing XSpacing, YSpacing
    ThisDrawing.ActiveViewport = viewportObj
    MsgBox "X =" & XSpacing & ", Y =" & YSpacing, , "SetGridSpacing Example"
   
End Sub
Sub Example_GetString()
    ' This example demonstrates different ways of returning a string
    ' entered by a user.
    
    Dim returnString As String
    
    ' Prompt & Input cannot contain blanks
    returnString = ThisDrawing.Utility.GetString(False, "Enter text (a space or <enter> terminates input): ")
    MsgBox "The string entered was '" & returnString & "'", , "GetString Example"
    
    ' Prompt & Input can contain blanks
    returnString = ThisDrawing.Utility.GetString(True, "Enter text (<enter> terminates input):")
    MsgBox "The string entered was '" & returnString & "'", , "GetString Example"
    
    ' Prompt & Input can contain blanks, but not an empty string
    Dim NoNull As Integer
    NoNull = 1    ' Disallow null
    ThisDrawing.Utility.InitializeUserInput NoNull
    returnString = ThisDrawing.Utility.GetString(True, "Enter text (<enter> terminates input): ")
    MsgBox "The string entered was '" & returnString & "'", , "GetString Example"

End Sub
Sub Example_SetXdata()
    ' This example creates a line and attaches extended data to that line.
    
    ' Create the line
    Dim lineObj As AcadLine
    Dim startPt(0 To 2) As Double, endPt(0 To 2) As Double
    startPt(0) = 1#: startPt(1) = 1#: startPt(2) = 0#
    endPt(0) = 5#: endPt(1) = 5#: endPt(2) = 0#
    Set lineObj = ThisDrawing.ModelSpace.AddLine(startPt, endPt)
    ZoomAll

    ' Initialize all the xdata values. Note that first data in the list should be
    ' application name and first datatype code should be 1001
    Dim DataType(0 To 9) As Integer
    Dim Data(0 To 9) As Variant
    Dim reals3(0 To 2) As Double
    Dim worldPos(0 To 2) As Double
    
    DataType(0) = 1001: Data(0) = "Test_Application"
    DataType(1) = 1000: Data(1) = "This is a test for xdata"

    DataType(2) = 1003: Data(2) = "0"                   ' layer
    DataType(3) = 1040: Data(3) = 1.23479137438413E+40  ' real
    DataType(4) = 1041: Data(4) = 1237324938            ' distance
    DataType(5) = 1070: Data(5) = 32767                 ' 16 bit Integer
    DataType(6) = 1071: Data(6) = 32767                 ' 32 bit Integer
    DataType(7) = 1042: Data(7) = 10                    ' scaleFactor

    reals3(0) = -2.95: reals3(1) = 100: reals3(2) = -20
    DataType(8) = 1010: Data(8) = reals3                ' real
    
    worldPos(0) = 4: worldPos(1) = 400.99999999: worldPos(2) = 2.798989
    DataType(9) = 1011: Data(9) = worldPos              ' world space position
    
    ' Attach the xdata to the line
    lineObj.SetXData DataType, Data
    
    ' Return the xdata for the line
    Dim xdataOut As Variant
    Dim xtypeOut As Variant
    lineObj.GetXData "", xtypeOut, xdataOut
    
End Sub
Sub Example_GetXData()
    ' This example creates a line and attaches extended data to that line.
    
    ' Create the line
    Dim lineObj As AcadLine
    Dim startPt(0 To 2) As Double, endPt(0 To 2) As Double
    startPt(0) = 1#: startPt(1) = 1#: startPt(2) = 0#
    endPt(0) = 5#: endPt(1) = 5#: endPt(2) = 0#
    Set lineObj = ThisDrawing.ModelSpace.AddLine(startPt, endPt)
    ZoomAll

    ' Initialize all the xdata values. Note that first data in the list should be
    ' application name and first datatype code should be 1001
    Dim DataType(0 To 9) As Integer
    Dim Data(0 To 9) As Variant
    Dim reals3(0 To 2) As Double
    Dim worldPos(0 To 2) As Double
    
    DataType(0) = 1001: Data(0) = "Test_Application"
    DataType(1) = 1000: Data(1) = "This is a test for xdata"

    DataType(2) = 1003: Data(2) = "0"                   ' layer
    DataType(3) = 1040: Data(3) = 1.23479137438413E+40  ' real
    DataType(4) = 1041: Data(4) = 1237324938            ' distance
    DataType(5) = 1070: Data(5) = 32767                 ' 16 bit Integer
    DataType(6) = 1071: Data(6) = 32767                 ' 32 bit Integer
    DataType(7) = 1042: Data(7) = 10                    ' scaleFactor

    reals3(0) = -2.95: reals3(1) = 100: reals3(2) = -20
    DataType(8) = 1010: Data(8) = reals3                ' real
    
    worldPos(0) = 4: worldPos(1) = 400.99999999: worldPos(2) = 2.798989
    DataType(9) = 1011: Data(9) = worldPos              ' world space position
    
    ' Attach the xdata to the line
    lineObj.SetXData DataType, Data
    
    ' Return the xdata for the line
    Dim xdataOut As Variant
    Dim xtypeOut As Variant
    lineObj.GetXData "", xtypeOut, xdataOut
    
End Sub
Sub Example_HasAttributes()
    ' This example first creates a block without attributes.
    ' It then inserts the block and checks if it has attributes.
    ' It then adds attributes to the block and inserts it again.
    ' Then it checks the new block reference for attributes.
    
    ' Create the block
    Dim blockObj As AcadBlock
    Dim insertionPnt(0 To 2) As Double
    insertionPnt(0) = 0#: insertionPnt(1) = 0#: insertionPnt(2) = 0#
    Set blockObj = ThisDrawing.Blocks.Add(insertionPnt, "CircleBlock")
    
    ' Add a circle to the block
    Dim circleObj As AcadCircle
    Dim center(0 To 2) As Double
    Dim radius As Double
    center(0) = 0: center(1) = 0: center(2) = 0
    radius = 1
    Set circleObj = blockObj.AddCircle(center, radius)
   
    ' Insert the block
    Dim blockRefObj As AcadBlockReference
    insertionPnt(0) = 2#: insertionPnt(1) = 2#: insertionPnt(2) = 0
    Set blockRefObj = ThisDrawing.ModelSpace.InsertBlock(insertionPnt, "CircleBlock", 1#, 1#, 1#, 0)
    ThisDrawing.Application.ZoomAll
    MsgBox "This block reference " & IIf(blockRefObj.HasAttributes, "has attributes.", "does not have attributes."), , "Has Attributes Example"
    
    
    ' Add attributes to the block definition.
    ' Define the attribute definition.
    Dim attributeObj As AcadAttribute
    Dim height As Double
    Dim mode As Long
    Dim prompt As String
    Dim insertionPoint(0 To 2) As Double
    Dim tag As String
    Dim value As String
    height = 1#
    mode = acAttributeModeVerify
    prompt = "Attribute Prompt"
    insertionPoint(0) = 1#: insertionPoint(1) = 1#: insertionPoint(2) = 0
    tag = "Attribute Tag"
    value = "Attribute Value"
    
    ' Create the attribute definition
    Set attributeObj = blockObj.AddAttribute(height, mode, prompt, insertionPoint, tag, value)
       
    ' Insert the block again
    Dim blockRefObj2 As AcadBlockReference
    insertionPnt(0) = 3#: insertionPnt(1) = 3#: insertionPnt(2) = 0
    Set blockRefObj2 = ThisDrawing.ModelSpace.InsertBlock(insertionPnt, "CircleBlock", 1#, 1#, 1#, 0)
    ZoomAll
    MsgBox "The first block reference " & IIf(blockRefObj.HasAttributes, "has attributes.", "does not have attributes.") & vbCrLf & _
            "The second block reference " & IIf(blockRefObj2.HasAttributes, "has attributes.", "does not have attributes."), , "Has Attributes Example"

End Sub
Sub Example_Import()
    ' This example will create a new drawing. Be sure to save
    ' your work and start a new drawing before running this example.
    ' This example creates a circle. It then exports the drawing
    ' to a file called DXFExprt.DXF. It then opens a new drawing
    ' and imports the file.
    
    ' Create the circle for visual representation
    Dim circleObj As AcadCircle
    Dim centerPt(0 To 2) As Double
    Dim radius As Double
    centerPt(0) = 2: centerPt(1) = 2: centerPt(2) = 0
    radius = 1
    Set circleObj = ThisDrawing.ModelSpace.AddCircle(centerPt, radius)
    ZoomAll
    
    ' Create an empty selection set
    Dim sset As AcadSelectionSet
    Set sset = ThisDrawing.SelectionSets.Add("TEST")
    
    ' Export the current drawing to the file specified above.
    Dim exportFile As String
    exportFile = "C:\AutoCAD\DXFExprt"     ' Adjust path to match your system
    ThisDrawing.Export exportFile, "DXF", sset
    
    ' Open a new drawing
    ThisDrawing.New "acad.dwt"
    
    ' Define the import
    Dim importFile As String
    Dim InsertPoint(0 To 2) As Double
    Dim scalefactor As Double
    importFile = "C:\AutoCAD\DXFExprt.dxf"   ' Adjust path to match your system
    InsertPoint(0) = 0#: InsertPoint(1) = 0#: InsertPoint(2) = 0#
    scalefactor = 2#
    
    ' Import the file
    ThisDrawing.Import importFile, InsertPoint, scalefactor
    ZoomAll
    
End Sub
Sub Example_ImportProfile()
    ' This example imports a profile.
    ' NOTE: A dummy profile name is used so that your existing
    ' profiles are not changed.
    
    Dim preferences As AcadPreferences
    Dim strProfileToImport As String
    
    Set preferences = ThisDrawing.Application.preferences
    
    ' Specify the profile to delete.
    strProfileToImport = "TestProfile"
    
    ' Delete the profile
    ' The call will fail if "TestProfile" does not exist
    On Error GoTo Error
    preferences.Profiles.ImportProfile strProfileToImport, "TESTPROFILE.ARG", True
    
    Exit Sub
Error:
        MsgBox "ImportProfile of " & strProfileToImport & " failed. " & Err.Description, , "ImportProfile Example"
        
End Sub
Sub Example_ExportProfile()
    ' This example exports the active profile to a new name.
    
    Dim preferences As AcadPreferences
    Dim currActiveProfile As String
    
    Set preferences = ThisDrawing.Application.preferences
    
    ' Retrieve the current ActiveProfile value
    currActiveProfile = preferences.Profiles.ActiveProfile
    MsgBox "The current ActiveProfile is: " & preferences.Profiles.ActiveProfile, , "ExportProfile Example"
    
    ' Export the active profile
    preferences.Profiles.ExportProfile currActiveProfile, "TestProfile.arg"
    MsgBox "The ActiveProfile has been exported to: TestProfile.arg", , "ExportProfile Example"
    
End Sub
Sub Example_ResetProfile()
    ' This example resets a profile to the default values.
    ' NOTE: A dummy profile name is used so that your existing
    ' profiles are not changed.
    
    Dim preferences As AcadPreferences
    Dim strProfileToReset As String
    
    Set preferences = ThisDrawing.Application.preferences
    
    ' Specify the profile to delete.
    strProfileToReset = "TestProfile"
    
    ' Delete the profile
    ' The call will fail if "TestProfile" does not exist
    On Error GoTo Error
    preferences.Profiles.ResetProfile strProfileToReset
    Exit Sub
Error:
        MsgBox "ResetProfile of " & strProfileToReset & " failed. " & Err.Description, , "ResetProfile Example"
        
End Sub
Sub Example_Preferences()
    ' This example returns the current setting of
    ' LogFilePath from the preferences object.
    
    Dim preferences As AcadPreferences
    Set preferences = ThisDrawing.Application.preferences
    
    ' Retrieve the current LogFilePath value
    MsgBox "The current value for LogFilePath is " & preferences.Files.LogFilePath, , "Preferences Example"
    
End Sub

Sub Example_InsertLoopAt()
    ' This example creates an associative hatch in model space.
    ' A Loop is then inserted into the hatch.
    Dim hatchObj As AcadHatch
    Dim patternName As String
    Dim PatternType As Long
    Dim bAssociativity As Boolean
    
    ' Define the hatch
    patternName = "ANSI31"
    PatternType = 0
    bAssociativity = True
    
    ' Create the associative Hatch object
    Set hatchObj = ThisDrawing.ModelSpace.AddHatch(PatternType, patternName, bAssociativity)
    
    ' Create the outer loop for the hatch.
    ' An arc and a line are used to create a closed loop.
    Dim outerLoop(0 To 1) As AcadEntity
    Dim center(0 To 2) As Double
    Dim radius As Double
    Dim startAngle As Double
    Dim endAngle As Double
    center(0) = 5: center(1) = 3: center(2) = 0
    radius = 3
    startAngle = 0
    endAngle = 3.141592
    Set outerLoop(0) = ThisDrawing.ModelSpace.AddArc(center, radius, startAngle, endAngle)
    Set outerLoop(1) = ThisDrawing.ModelSpace.AddLine(outerLoop(0).startPoint, outerLoop(0).endPoint)
        
    ' Append the outer loop to the hatch object
    hatchObj.AppendOuterLoop (outerLoop)
    
    ' Append the first circle as one inner loop
    Dim innerLoop1(0) As AcadEntity
    center(0) = 5: center(1) = 4.5: center(2) = 0
    radius = 1
    Set innerLoop1(0) = ThisDrawing.ModelSpace.AddCircle(center, radius)
    hatchObj.AppendInnerLoop (innerLoop1)
    
    ' Evaluate and display the hatch
    hatchObj.Evaluate
    ThisDrawing.Regen True
    
    
    MsgBox "Insert another loop.", , "InsertLoopAt Example"
    
    ' Insert the second circle as the other inner loop
    Dim LoopObj(0) As AcadEntity
    radius = 0.5
    Set LoopObj(0) = ThisDrawing.ModelSpace.AddCircle(center, radius)
    hatchObj.InsertLoopAt hatchObj.NumberOfLoops, acHatchLoopTypeDefault, LoopObj
    
    ' Evaluate and display the hatch
    hatchObj.Evaluate
    ThisDrawing.Regen True
    
    MsgBox "Loop inserted.", , "InsertLoopAt Example"
                       
End Sub
Sub Example_IntersectWith()
    ' This example creates a line and circle and finds the points at
    ' which they intersect.
    
    ' Create the line
    Dim lineObj As AcadLine
    Dim startPt(0 To 2) As Double
    Dim endPt(0 To 2) As Double
    startPt(0) = 1: startPt(1) = 1: startPt(2) = 0
    endPt(0) = 5: endPt(1) = 5: endPt(2) = 0
    Set lineObj = ThisDrawing.ModelSpace.AddLine(startPt, endPt)
        
    ' Create the circle
    Dim circleObj As AcadCircle
    Dim centerPt(0 To 2) As Double
    Dim radius As Double
    centerPt(0) = 3: centerPt(1) = 3: centerPt(2) = 0
    radius = 1
    Set circleObj = ThisDrawing.ModelSpace.AddCircle(centerPt, radius)
    ZoomAll
      
    ' Find the intersection points between the line and the circle
    Dim intPoints As Variant
    intPoints = lineObj.IntersectWith(circleObj, acExtendNone)
    
    ' Print all the intersection points
    Dim I As Integer, j As Integer, k As Integer
    Dim str As String
    If VarType(intPoints) <> vbEmpty Then
        For I = LBound(intPoints) To UBound(intPoints)
            str = "Intersection Point[" & k & "] is: " & intPoints(j) & "," & intPoints(j + 1) & "," & intPoints(j + 2)
            MsgBox str, , "IntersectWith Example"
            str = ""
            I = I + 2
            j = j + 3
            k = k + 1
        Next
    End If
End Sub

Sub Example_LoadShapeFile()
    ' This example loads a shape file
    
    Dim shapeFileToLoad As String
    shapeFileToLoad = "C:/AutoCAD/Support/ltypeshp.shx"
    
    ' Load the shape file
    On Error GoTo ERRORHANDLE
    ThisDrawing.LoadShapeFile shapeFileToLoad
    Exit Sub
ERRORHANDLE:
    MsgBox Err.Description, Title:="LoadShapeFile"
    
End Sub
Sub Example_New()
    ' This example creates a new drawing based on the template ansi-a.dwt.
    ' Note: The path to the template file is included with its name. Adjust
    ' this path for your installation location before running this example.
    
    Dim templateFileName As String
    templateFileName = "c:\AutoCAD\template\ansi-a.dwt"
    
    ThisDrawing.New templateFileName
    
End Sub
Sub Example_Open()
    ' The following example opens "C:\AutoCAD\Sample\downtown.dwg" file.
    ' This drawing may not exist on your system. Change the drawing
    ' path and name to reflect a valid AutoCAD drawing on your system.
    
    ThisDrawing.Application.Documents.Open ("C:\AutoCAD\Sample\downtown.dwg")
    
End Sub
Sub Example_PurgeAll()
    ' This example removes all unused named references from the database
    
    ThisDrawing.PurgeAll
    
End Sub
Sub Example_PurgeFitData()
    ' This example creates a spline object in model space.
    ' It then returns the current number of fit points,
    ' and then purges the fit data.

    Dim noOfPoints As Integer
    Dim splineObj As AcadSpline
    Dim startTan(0 To 2) As Double
    Dim endTan(0 To 2) As Double
    Dim fitPoints(0 To 8) As Double
    
    noOfPoints = 3
    startTan(0) = 0.5: startTan(1) = 0.5: startTan(2) = 0
    endTan(0) = 0.5: endTan(1) = 0.5: endTan(2) = 0
    fitPoints(0) = 0: fitPoints(1) = 0: fitPoints(2) = 0
    fitPoints(3) = 5: fitPoints(4) = 5: fitPoints(5) = 0
    fitPoints(6) = 10: fitPoints(7) = 0: fitPoints(8) = 0
    Set splineObj = ThisDrawing.ModelSpace.AddSpline(fitPoints, startTan, endTan)
    ZoomAll
    
    MsgBox "Before the purge there are " & splineObj.NumberOfFitPoints & " fit points.", , "PurgeFitData Example"

    ' Purge the fit data
    splineObj.PurgeFitData

    ThisDrawing.Regen True
    MsgBox "After the purge there are " & splineObj.NumberOfFitPoints & " fit points.", , "PurgeFitData Example"
    
End Sub
Sub Example_Quit()
    ' Warning: This example will quit AutoCAD and VBA.
    
    ThisDrawing.Application.Quit
    
End Sub
Sub Example_RealToString()
    ' This example converts values in a given format to their string equivalents.
    
    Dim unit As Long
    Dim valueAsStr As String
    Dim precision As Integer
    Dim valueAsReal As Double
    precision = 6
    
    ' Convert a real value 17.5 using Scientific mode to a String
    unit = acScientific
    valueAsStr = ThisDrawing.Utility.RealToString(17.5, unit, precision)
    MsgBox "17.5 in scientific format is " & valueAsStr, , "RealToString Example"
    
    ' Convert a real value 17.5 using Decimal mode to a String
    unit = acDecimal
    valueAsStr = ThisDrawing.Utility.RealToString(17.5, unit, precision)
    MsgBox "17.5 in decimal format is " & valueAsStr, , "RealToString Example"
    
    ' Convert a real value 17.5 using Engineering mode to a String
    unit = acEngineering
    valueAsStr = ThisDrawing.Utility.RealToString(17.5, unit, precision)
    MsgBox "17.5 in engineering format is " & valueAsStr, , "RealToString Example"
    
    ' Convert a real value 17.5 using Architectural mode to a String
    unit = acArchitectural
    valueAsStr = ThisDrawing.Utility.RealToString(17.5, unit, precision)
    MsgBox "17.5 in architectural format is " & valueAsStr, , "RealToString Example"
    
    ' Converts a real value 17.5 using fractional mode to a String
    unit = acFractional
    valueAsStr = ThisDrawing.Utility.RealToString(17.5, unit, precision)
    MsgBox "17.5 in fractional format is " & valueAsStr, , "RealToString Example"
    
End Sub
Sub Example_Remove()
    ' This example creates a dictionary and adds
    ' a custom object to that dictionary. It then
    ' removes the object from the dictionary.
    
    Dim dictObj As AcadDictionary
    Set dictObj = ThisDrawing.Dictionaries.Add("TEST_DICTIONARY")
    
    ' Load the ARX application that defines the custom object.
    ' Note: The application listed here does not exist and
    ' will cause an error when run. Change the application name
    ' to the path and name of your ARX Application.
    ThisDrawing.Application.LoadArx ("MyARXApp.dll")
    
    ' Create the custom object in the dictionary
    Dim keyName As String
    Dim className As String
    Dim customObj As AcadObject
    
    keyName = "OBJ1"
    className = "CAsdkDictObject"
    
    Set customObj = dictObj.AddObject(keyName, className)
    
    ' Remove the object from the dictionary using the keyName
    dictObj.Remove (keyName)
    
End Sub
Sub Example_Replace()
    ' This example creates a dictionary and adds
    ' a custom object to that dictionary. It then
    ' replaces the object in the dictionary.
    
    Dim dictObj As AcadDictionary
    Set dictObj = ThisDrawing.Dictionaries.Add("TEST_DICTIONARY")
    
    ' Load the ARX application that defines the custom object.
    ' Note: The application listed here does not exist and
    ' will cause an error when run. Change the application name
    ' to the path and name of your ARX Application.
    ThisDrawing.Application.LoadArx ("MyARXApp.dll")
    
    ' Create the custom object in the dictionary
    Dim keyName As String
    Dim className As String
    Dim customObj As AcadObject
    
    keyName = "OBJ1"
    className = "CAsdkDictObject"
    
    Set customObj = dictObj.AddObject(keyName, className)
    
    ' Replace the object from the dictionary with a different object
    Dim newCustomObject As AcadObject
    dictObj.Replace keyName, newCustomObject
    
End Sub
Sub Example_Rename()
    ' This example creates a dictionary and adds
    ' a custom object to that dictionary. It then
    ' renames the object in the dictionary.
    
    Dim dictObj As AcadDictionary
    Set dictObj = ThisDrawing.Dictionaries.Add("TEST_DICTIONARY")
    
    ' Load the ARX application that defines the custom object.
    ' Note: The application listed here does not exist and
    ' will cause an error when run. Change the application name
    ' to the path and name of your ARX Application.
    ThisDrawing.Application.LoadArx ("MyARXApp.dll")
    
    ' Create the custom object in the dictionary
    Dim keyName As String
    Dim className As String
    Dim customObj As AcadObject
    
    keyName = "OBJ1"
    className = "CAsdkDictObject"
    
    Set customObj = dictObj.AddObject(keyName, className)
    
    ' Rename the object
    dictObj.Rename keyName, "NewKeyName"
    
End Sub
Sub Example_Reverse()
    ' This example creates a spline in model space.
    ' It then reverses the spline and therefore the
    ' control point data.
    
    Dim noOfPoints As Integer
    Dim splineObj As AcadSpline
    Dim startTan(0 To 2) As Double
    Dim endTan(0 To 2) As Double
    Dim fitPoints(0 To 8) As Double
    Dim msg As String
    
    noOfPoints = 3
    startTan(0) = 0.5: startTan(1) = 0.5: startTan(2) = 0
    endTan(0) = 0.5: endTan(1) = 0.5: endTan(2) = 0
    fitPoints(0) = 0: fitPoints(1) = 0: fitPoints(2) = 0
    fitPoints(3) = 5: fitPoints(4) = 5: fitPoints(5) = 0
    fitPoints(6) = 10: fitPoints(7) = 0: fitPoints(8) = 0
    Set splineObj = ThisDrawing.ModelSpace.AddSpline(fitPoints, startTan, endTan)
    
    ZoomAll
    GoSub GETPOINTS
    MsgBox "Before the reverse the first control point is " & msg

    ' Reverse the Spline and therefore control point data
    splineObj.Reverse

    ThisDrawing.Regen True
    GoSub GETPOINTS
    MsgBox "After the reverse the first control point is " & msg

    Exit Sub
GETPOINTS:
    msg = ""
    ' Get the coordinates from the first control point again
    Dim count As Integer
    For count = 0 To 2
        msg = msg & splineObj.GetControlPoint(0)(count) & ", "
    Next
    msg = VBA.Left(msg, Len(msg) - 2)
    Return
    
End Sub
Sub Example_Save()
    ' The following example saves current drawing
    
    ThisDrawing.Save
    
End Sub
Sub Example_SaveAs()
    ' The following example saves current drawing as "test.dwg"
    
    ThisDrawing.SaveAs ("test.dwg")
    
End Sub
Sub Example_Select()
    ' This example adds members to a selection set first by crossing and
    ' then by filtering for circles.
    
    ' Create the selection set
    Dim ssetObj As AcadSelectionSet
    Set ssetObj = ThisDrawing.SelectionSets.Add("SSET")
    
    
    ' Add all entities that lie within a crossing of (28,17,0) and
    ' (-3.3, -3.6,0) to the selection set
    Dim mode As Integer
    Dim corner1(0 To 2) As Double
    Dim corner2(0 To 2) As Double
    
    mode = acSelectionSetCrossing
    corner1(0) = 28: corner1(1) = 17: corner1(2) = 0
    corner2(0) = -3.3: corner2(1) = -3.6: corner2(2) = 0
    ssetObj.Select mode, corner1, corner2
    
    ' Add all the Circles that lie within the crossing of (28,17,0) and
    ' (-3.3, -3.6,0) to the selection set by filtering from the current drawing
    Dim gpCode(0) As Integer
    Dim dataValue(0) As Variant
    gpCode(0) = 0
    dataValue(0) = "Circle"
    
    Dim groupCode As Variant, dataCode As Variant
    groupCode = gpCode
    dataCode = dataValue
    
    ssetObj.Select mode, corner1, corner2, groupCode, dataCode
    
End Sub
Sub Example_SelectAtPoint()
    ' This example adds entities to a selection set by identifying a point.
    ' At first all entities at the point are added to the selection set. Then
    ' only circle entities at the point are added to the selection set.
    
    ' Create the selection set
    Dim ssetObj As AcadSelectionSet
    Set ssetObj = ThisDrawing.SelectionSets.Add("TEST_SSET1")
   
    ' Add all the entities that lie at point(6.8,9.4,0) to the selection set
    Dim point(0 To 2) As Double
    point(0) = 6.8: point(1) = 9.4: point(2) = 0
    ssetObj.SelectAtPoint point
    
    ' Add all the Circles that lie at point (6.8,9.4,0) to the selection set
    Dim gpCode(0) As Integer
    Dim dataValue(0) As Variant
    gpCode(0) = 0
    dataValue(0) = "Circle"
    
    Dim groupCode As Variant, dataCode As Variant
    groupCode = gpCode
    dataCode = dataValue
    
    ssetObj.SelectAtPoint point, groupCode, dataCode
    
End Sub
Sub Example_SelectByPolygon()
    ' This example adds entities to a selection set by defining a polygon.
    
    Dim ssetObj As AcadSelectionSet
    Set ssetObj = ThisDrawing.SelectionSets.Add("TEST_SSET2")
     
    ' Add all the entities that lie within a fence to the selection set
    Dim mode As Integer
    Dim pointsArray(0 To 11) As Double
    mode = acSelectionSetFence
    pointsArray(0) = 28.2: pointsArray(1) = 17.2: pointsArray(2) = 0
    pointsArray(3) = -5: pointsArray(4) = 13: pointsArray(5) = 0
    pointsArray(6) = -3.3: pointsArray(7) = -3.6: pointsArray(8) = 0
    pointsArray(9) = 28: pointsArray(10) = -3: pointsArray(11) = 0
    
    ssetObj.SelectByPolygon mode, pointsArray
    
    ' Add all the Circles that lie within fence to the selection set
    ReDim gpCode(0 To 1) As Integer
    gpCode(0) = 0
    gpCode(1) = 10
    
    Dim pnt(0 To 2) As Double
    pnt(0) = 3: pnt(1) = 6: pnt(2) = 0
    
    ReDim dataValue(0 To 1) As Variant
    dataValue(0) = "Circle"
    dataValue(1) = pnt
    
    Dim groupCode As Variant, dataCode As Variant
    groupCode = gpCode
    dataCode = dataValue
    
    ssetObj.SelectByPolygon mode, pointsArray, groupCode, dataCode
    
End Sub
Sub Example_SelectOnScreen()
    ' This example adds entities to a selection set by prompting the user
    ' to select entities to add.
    
    ' Create the selection set
    Dim ssetObj As AcadSelectionSet
    Set ssetObj = ThisDrawing.SelectionSets.Add("TEST_SSET")
    
    ' Add entities to a selection set by prompting user to select on the screen
    ssetObj.SelectOnScreen
    
End Sub
Sub Example_SetPattern()
    ' This example creates an associative hatch in model space.
    ' The hatch pattern is then changed.
    
    Dim hatchObj As AcadHatch
    Dim patternName As String
    Dim PatternType As Long
    Dim bAssociativity As Boolean
    
    ' Define the hatch
    patternName = "ANSI31"
    PatternType = 0
    bAssociativity = True
    
    ' Create the associative Hatch object
    Set hatchObj = ThisDrawing.ModelSpace.AddHatch(PatternType, patternName, bAssociativity)
    
    ' Create the outer loop for the hatch.
    ' An arc and a line are used to create a closed loop.
    
    Dim outerLoop(0 To 1) As AcadEntity
    Dim center(0 To 2) As Double
    Dim radius As Double
    Dim startAngle As Double
    Dim endAngle As Double
    center(0) = 5: center(1) = 3: center(2) = 0
    radius = 3
    startAngle = 0
    endAngle = 3.141592
    Set outerLoop(0) = ThisDrawing.ModelSpace.AddArc(center, radius, startAngle, endAngle)
    Set outerLoop(1) = ThisDrawing.ModelSpace.AddLine(outerLoop(0).startPoint, outerLoop(0).endPoint)
        
    ' Append the outer loop to the hatch object
    hatchObj.AppendOuterLoop (outerLoop)
    
    ' Append the first circle as one inner loop
    Dim innerLoop1(0) As AcadEntity
    center(0) = 5: center(1) = 4.5: center(2) = 0
    radius = 1
    Set innerLoop1(0) = ThisDrawing.ModelSpace.AddCircle(center, radius)
    hatchObj.AppendInnerLoop (innerLoop1)
    
    ' Append the second circle as the other inner loop
    Dim innerLoop2(0) As AcadEntity
    radius = 0.5
    Set innerLoop2(0) = ThisDrawing.ModelSpace.AddCircle(center, radius)
    hatchObj.AppendInnerLoop (innerLoop2)
    
    ' Evaluate and display the hatch
    hatchObj.Evaluate
    ZoomAll
    
    ' Find the name of the hatch pattern
    patternName = hatchObj.patternName
    MsgBox "The hatch pattern is " & hatchObj.patternName, , "SetPattern Example"
                   
    ' Change the hatch pattern
    hatchObj.SetPattern acHatchPatternTypePreDefined, "BRICK"
    hatchObj.Evaluate
    ThisDrawing.Regen True
    MsgBox "The hatch pattern is now " & hatchObj.patternName, , "SetPattern Example"
    
End Sub
Sub Example_ZoomWindow()
    ' This example creates several objects in model space and
    ' then performs a variety of zooms on the drawing.
    
    ' Create a Ray object in model space
    Dim rayObj As AcadRay
    Dim basePoint(0 To 2) As Double
    Dim SecondPoint(0 To 2) As Double
    basePoint(0) = 3#: basePoint(1) = 3#: basePoint(2) = 0#
    SecondPoint(0) = 1#: SecondPoint(1) = 3#: SecondPoint(2) = 0#
    Set rayObj = ThisDrawing.ModelSpace.AddRay(basePoint, SecondPoint)
    
    ' Create a polyline object in model space
    Dim plineObj As AcadLWPolyline
    Dim points(0 To 5) As Double
    points(0) = 3: points(1) = 7
    points(2) = 9: points(3) = 2
    points(4) = 3: points(5) = 5
    Set plineObj = ThisDrawing.ModelSpace.AddLightWeightPolyline(points)
    plineObj.Closed = True

    ' Create a line object in model space
    Dim lineObj As AcadLine
    Dim startPoint(0 To 2) As Double
    Dim endPoint(0 To 2) As Double
    startPoint(0) = 0: startPoint(1) = 0: startPoint(2) = 0
    endPoint(0) = 2: endPoint(1) = 2: endPoint(2) = 0
    Set lineObj = ThisDrawing.ModelSpace.AddLine(startPoint, endPoint)
    
    ' Create a circle object in model space
    Dim circObj As AcadCircle
    Dim centerPt(0 To 2) As Double
    Dim radius As Double
    centerPt(0) = 20: centerPt(1) = 30: centerPt(2) = 0
    radius = 3
    Set circObj = ThisDrawing.ModelSpace.AddCircle(centerPt, radius)

    ' Create an ellipse object in model space
    Dim ellObj As AcadEllipse
    Dim majAxis(0 To 2) As Double
    Dim center(0 To 2) As Double
    Dim radRatio As Double
    center(0) = 5#: center(1) = 5#: center(2) = 0#
    majAxis(0) = 10: majAxis(1) = 20#: majAxis(2) = 0#
    radRatio = 0.3
    Set ellObj = ThisDrawing.ModelSpace.AddEllipse(center, majAxis, radRatio)
 
' ZoomAll
    MsgBox "Perform a ZoomAll", , "ZoomWindow Example"
    ZoomAll
    
' ZoomWindow
    MsgBox "Perform a ZoomWindow using the following coordinates:" & vbCrLf & _
           "1.3, 7.8, 0" & vbCrLf & _
           "13.7, -2.6, 0", , "ZoomWindow Example"
           
    Dim point1(0 To 2) As Double
    Dim point2(0 To 2) As Double
    point1(0) = 1.3: point1(1) = 7.8: point1(2) = 0
    point2(0) = 13.7: point2(1) = -2.6: point2(2) = 0
    ZoomWindow point1, point2
    
' ZoomScaled
    MsgBox "Perform a ZoomScaled using:" & vbCrLf & _
           "Scale Type: acZoomScaledRelative" & vbCrLf & _
           "Scale Factor: 2", , "ZoomWindow Example"
    Dim scalefactor As Double
    Dim scaletype As Integer
    scalefactor = 2
    scaletype = acZoomScaledRelative
    ZoomScaled scalefactor, scaletype
    
' ZoomExtents
    MsgBox "Perform a ZoomExtents", , "ZoomWindow Example"
    ZoomExtents
    
' ZoomPickWindow
    MsgBox "Perform a ZoomPickWindow", , "ZoomWindow Example"
    ZoomPickWindow
    
' ZoomCenter
    MsgBox "Perform a ZoomCenter using:" & vbCrLf & _
           "Center 3, 3, 0" & vbCrLf & _
           "Magnification: 10", , "ZoomWindow Example"
    Dim zcenter(0 To 2) As Double
    Dim magnification As Double
    zcenter(0) = 3: zcenter(1) = 3: zcenter(2) = 0
    magnification = 10
    ZoomCenter zcenter, magnification
   
End Sub
Sub Example_ZoomCenter()
    ' This example creates several objects in model space and
    ' then performs a variety of zooms on the drawing.
    
    ' Create a Ray object in model space
    Dim rayObj As AcadRay
    Dim basePoint(0 To 2) As Double
    Dim SecondPoint(0 To 2) As Double
    basePoint(0) = 3#: basePoint(1) = 3#: basePoint(2) = 0#
    SecondPoint(0) = 1#: SecondPoint(1) = 3#: SecondPoint(2) = 0#
    Set rayObj = ThisDrawing.ModelSpace.AddRay(basePoint, SecondPoint)
    
    ' Create a polyline object in model space
    Dim plineObj As AcadLWPolyline
    Dim points(0 To 5) As Double
    points(0) = 3: points(1) = 7
    points(2) = 9: points(3) = 2
    points(4) = 3: points(5) = 5
    Set plineObj = ThisDrawing.ModelSpace.AddLightWeightPolyline(points)
    plineObj.Closed = True

    ' Create a line object in model space
    Dim lineObj As AcadLine
    Dim startPoint(0 To 2) As Double
    Dim endPoint(0 To 2) As Double
    startPoint(0) = 0: startPoint(1) = 0: startPoint(2) = 0
    endPoint(0) = 2: endPoint(1) = 2: endPoint(2) = 0
    Set lineObj = ThisDrawing.ModelSpace.AddLine(startPoint, endPoint)
    
    ' Create a circle object in model space
    Dim circObj As AcadCircle
    Dim centerPt(0 To 2) As Double
    Dim radius As Double
    centerPt(0) = 20: centerPt(1) = 30: centerPt(2) = 0
    radius = 3
    Set circObj = ThisDrawing.ModelSpace.AddCircle(centerPt, radius)

    ' Create an ellipse object in model space
    Dim ellObj As AcadEllipse
    Dim majAxis(0 To 2) As Double
    Dim center(0 To 2) As Double
    Dim radRatio As Double
    center(0) = 5#: center(1) = 5#: center(2) = 0#
    majAxis(0) = 10: majAxis(1) = 20#: majAxis(2) = 0#
    radRatio = 0.3
    Set ellObj = ThisDrawing.ModelSpace.AddEllipse(center, majAxis, radRatio)

' ZoomAll
    MsgBox "Perform a ZoomAll", , "ZoomWindow Example"
    ZoomAll
    
' ZoomWindow
    MsgBox "Perform a ZoomWindow using the following coordinates:" & vbCrLf & _
           "1.3, 7.8, 0" & vbCrLf & _
           "13.7, -2.6, 0", , "ZoomWindow Example"
           
    Dim point1(0 To 2) As Double
    Dim point2(0 To 2) As Double
    point1(0) = 1.3: point1(1) = 7.8: point1(2) = 0
    point2(0) = 13.7: point2(1) = -2.6: point2(2) = 0
    ZoomWindow point1, point2
    
' ZoomScaled
    MsgBox "Perform a ZoomScaled using:" & vbCrLf & _
           "Scale Type: acZoomScaledRelative" & vbCrLf & _
           "Scale Factor: 2", , "ZoomWindow Example"
    Dim scalefactor As Double
    Dim scaletype As Integer
    scalefactor = 2
    scaletype = acZoomScaledRelative
    ZoomScaled scalefactor, scaletype
    
' ZoomExtents
    MsgBox "Perform a ZoomExtents", , "ZoomWindow Example"
    ZoomExtents
    
' ZoomPickWindow
    MsgBox "Perform a ZoomPickWindow", , "ZoomWindow Example"
    ZoomPickWindow
    
' ZoomCenter
    MsgBox "Perform a ZoomCenter using:" & vbCrLf & _
           "Center 3, 3, 0" & vbCrLf & _
           "Magnification: 10", , "ZoomWindow Example"
    Dim zcenter(0 To 2) As Double
    Dim magnification As Double
    zcenter(0) = 3: zcenter(1) = 3: zcenter(2) = 0
    magnification = 10
    ZoomCenter zcenter, magnification
   
End Sub
Sub Example_ZoomScaled()
    ' This example creates several objects in model space and
    ' then performs a variety of zooms on the drawing.
    
    ' Create a Ray object in model space
    Dim rayObj As AcadRay
    Dim basePoint(0 To 2) As Double
    Dim SecondPoint(0 To 2) As Double
    basePoint(0) = 3#: basePoint(1) = 3#: basePoint(2) = 0#
    SecondPoint(0) = 1#: SecondPoint(1) = 3#: SecondPoint(2) = 0#
    Set rayObj = ThisDrawing.ModelSpace.AddRay(basePoint, SecondPoint)
    
    ' Create a polyline object in model space
    Dim plineObj As AcadLWPolyline
    Dim points(0 To 5) As Double
    points(0) = 3: points(1) = 7
    points(2) = 9: points(3) = 2
    points(4) = 3: points(5) = 5
    Set plineObj = ThisDrawing.ModelSpace.AddLightWeightPolyline(points)
    plineObj.Closed = True

    ' Create a line object in model space
    Dim lineObj As AcadLine
    Dim startPoint(0 To 2) As Double
    Dim endPoint(0 To 2) As Double
    startPoint(0) = 0: startPoint(1) = 0: startPoint(2) = 0
    endPoint(0) = 2: endPoint(1) = 2: endPoint(2) = 0
    Set lineObj = ThisDrawing.ModelSpace.AddLine(startPoint, endPoint)
    
    ' Create a circle object in model space
    Dim circObj As AcadCircle
    Dim centerPt(0 To 2) As Double
    Dim radius As Double
    centerPt(0) = 20: centerPt(1) = 30: centerPt(2) = 0
    radius = 3
    Set circObj = ThisDrawing.ModelSpace.AddCircle(centerPt, radius)

    ' Create an ellipse object in model space
    Dim ellObj As AcadEllipse
    Dim majAxis(0 To 2) As Double
    Dim center(0 To 2) As Double
    Dim radRatio As Double
    center(0) = 5#: center(1) = 5#: center(2) = 0#
    majAxis(0) = 10: majAxis(1) = 20#: majAxis(2) = 0#
    radRatio = 0.3
    Set ellObj = ThisDrawing.ModelSpace.AddEllipse(center, majAxis, radRatio)

' ZoomAll
    MsgBox "Perform a ZoomAll", , "ZoomWindow Example"
    ZoomAll
    
' ZoomWindow
    MsgBox "Perform a ZoomWindow using the following coordinates:" & vbCrLf & _
           "1.3, 7.8, 0" & vbCrLf & _
           "13.7, -2.6, 0", , "ZoomWindow Example"
           
    Dim point1(0 To 2) As Double
    Dim point2(0 To 2) As Double
    point1(0) = 1.3: point1(1) = 7.8: point1(2) = 0
    point2(0) = 13.7: point2(1) = -2.6: point2(2) = 0
    ZoomWindow point1, point2
    
' ZoomScaled
    MsgBox "Perform a ZoomScaled using:" & vbCrLf & _
           "Scale Type: acZoomScaledRelative" & vbCrLf & _
           "Scale Factor: 2", , "ZoomWindow Example"
    Dim scalefactor As Double
    Dim scaletype As Integer
    scalefactor = 2
    scaletype = acZoomScaledRelative
    ZoomScaled scalefactor, scaletype
    
' ZoomExtents
    MsgBox "Perform a ZoomExtents", , "ZoomWindow Example"
    ZoomExtents
    
' ZoomPickWindow
    MsgBox "Perform a ZoomPickWindow", , "ZoomWindow Example"
    ZoomPickWindow
    
' ZoomCenter
    MsgBox "Perform a ZoomCenter using:" & vbCrLf & _
           "Center 3, 3, 0" & vbCrLf & _
           "Magnification: 10", , "ZoomWindow Example"
    Dim zcenter(0 To 2) As Double
    Dim magnification As Double
    zcenter(0) = 3: zcenter(1) = 3: zcenter(2) = 0
    magnification = 10
    ZoomCenter zcenter, magnification
   
End Sub
Sub Example_ZoomAll()
    ' This example creates several objects in model space and
    ' then performs a variety of zooms on the drawing.
    
    ' Create a Ray object in model space
    Dim rayObj As AcadRay
    Dim basePoint(0 To 2) As Double
    Dim SecondPoint(0 To 2) As Double
    basePoint(0) = 3#: basePoint(1) = 3#: basePoint(2) = 0#
    SecondPoint(0) = 1#: SecondPoint(1) = 3#: SecondPoint(2) = 0#
    Set rayObj = ThisDrawing.ModelSpace.AddRay(basePoint, SecondPoint)
    
    ' Create a polyline object in model space
    Dim plineObj As AcadLWPolyline
    Dim points(0 To 5) As Double
    points(0) = 3: points(1) = 7
    points(2) = 9: points(3) = 2
    points(4) = 3: points(5) = 5
    Set plineObj = ThisDrawing.ModelSpace.AddLightWeightPolyline(points)
    plineObj.Closed = True

    ' Create a line object in model space
    Dim lineObj As AcadLine
    Dim startPoint(0 To 2) As Double
    Dim endPoint(0 To 2) As Double
    startPoint(0) = 0: startPoint(1) = 0: startPoint(2) = 0
    endPoint(0) = 2: endPoint(1) = 2: endPoint(2) = 0
    Set lineObj = ThisDrawing.ModelSpace.AddLine(startPoint, endPoint)
    
    ' Create a circle object in model space
    Dim circObj As AcadCircle
    Dim centerPt(0 To 2) As Double
    Dim radius As Double
    centerPt(0) = 20: centerPt(1) = 30: centerPt(2) = 0
    radius = 3
    Set circObj = ThisDrawing.ModelSpace.AddCircle(centerPt, radius)

    ' Create an ellipse object in model space
    Dim ellObj As AcadEllipse
    Dim majAxis(0 To 2) As Double
    Dim center(0 To 2) As Double
    Dim radRatio As Double
    center(0) = 5#: center(1) = 5#: center(2) = 0#
    majAxis(0) = 10: majAxis(1) = 20#: majAxis(2) = 0#
    radRatio = 0.3
    Set ellObj = ThisDrawing.ModelSpace.AddEllipse(center, majAxis, radRatio)

' ZoomAll
    MsgBox "Perform a ZoomAll", , "ZoomWindow Example"
    ZoomAll
    
' ZoomWindow
    MsgBox "Perform a ZoomWindow using the following coordinates:" & vbCrLf & _
           "1.3, 7.8, 0" & vbCrLf & _
           "13.7, -2.6, 0", , "ZoomWindow Example"
           
    Dim point1(0 To 2) As Double
    Dim point2(0 To 2) As Double
    point1(0) = 1.3: point1(1) = 7.8: point1(2) = 0
    point2(0) = 13.7: point2(1) = -2.6: point2(2) = 0
    ZoomWindow point1, point2
    
' ZoomScaled
    MsgBox "Perform a ZoomScaled using:" & vbCrLf & _
           "Scale Type: acZoomScaledRelative" & vbCrLf & _
           "Scale Factor: 2", , "ZoomWindow Example"
    Dim scalefactor As Double
    Dim scaletype As Integer
    scalefactor = 2
    scaletype = acZoomScaledRelative
    ZoomScaled scalefactor, scaletype
    
' ZoomExtents
    MsgBox "Perform a ZoomExtents", , "ZoomWindow Example"
    ZoomExtents
    
' ZoomPickWindow
    MsgBox "Perform a ZoomPickWindow", , "ZoomWindow Example"
    ZoomPickWindow
    
' ZoomCenter
    MsgBox "Perform a ZoomCenter using:" & vbCrLf & _
           "Center 3, 3, 0" & vbCrLf & _
           "Magnification: 10", , "ZoomWindow Example"
    Dim zcenter(0 To 2) As Double
    Dim magnification As Double
    zcenter(0) = 3: zcenter(1) = 3: zcenter(2) = 0
    magnification = 10
    ZoomCenter zcenter, magnification
   
End Sub
Sub Example_ZoomPickWindow()
    ' This example creates several objects in model space and
    ' then performs a variety of zooms on the drawing.
    
    ' Create a Ray object in model space
    Dim rayObj As AcadRay
    Dim basePoint(0 To 2) As Double
    Dim SecondPoint(0 To 2) As Double
    basePoint(0) = 3#: basePoint(1) = 3#: basePoint(2) = 0#
    SecondPoint(0) = 1#: SecondPoint(1) = 3#: SecondPoint(2) = 0#
    Set rayObj = ThisDrawing.ModelSpace.AddRay(basePoint, SecondPoint)
    
    ' Create a polyline object in model space
    Dim plineObj As AcadLWPolyline
    Dim points(0 To 5) As Double
    points(0) = 3: points(1) = 7
    points(2) = 9: points(3) = 2
    points(4) = 3: points(5) = 5
    Set plineObj = ThisDrawing.ModelSpace.AddLightWeightPolyline(points)
    plineObj.Closed = True

    ' Create a line object in model space
    Dim lineObj As AcadLine
    Dim startPoint(0 To 2) As Double
    Dim endPoint(0 To 2) As Double
    startPoint(0) = 0: startPoint(1) = 0: startPoint(2) = 0
    endPoint(0) = 2: endPoint(1) = 2: endPoint(2) = 0
    Set lineObj = ThisDrawing.ModelSpace.AddLine(startPoint, endPoint)
    
    ' Create a circle object in model space
    Dim circObj As AcadCircle
    Dim centerPt(0 To 2) As Double
    Dim radius As Double
    centerPt(0) = 20: centerPt(1) = 30: centerPt(2) = 0
    radius = 3
    Set circObj = ThisDrawing.ModelSpace.AddCircle(centerPt, radius)

    ' Create an ellipse object in model space
    Dim ellObj As AcadEllipse
    Dim majAxis(0 To 2) As Double
    Dim center(0 To 2) As Double
    Dim radRatio As Double
    center(0) = 5#: center(1) = 5#: center(2) = 0#
    majAxis(0) = 10: majAxis(1) = 20#: majAxis(2) = 0#
    radRatio = 0.3
    Set ellObj = ThisDrawing.ModelSpace.AddEllipse(center, majAxis, radRatio)

' ZoomAll
    MsgBox "Perform a ZoomAll", , "ZoomWindow Example"
    ZoomAll
    
' ZoomWindow
    MsgBox "Perform a ZoomWindow using the following coordinates:" & vbCrLf & _
           "1.3, 7.8, 0" & vbCrLf & _
           "13.7, -2.6, 0", , "ZoomWindow Example"
           
    Dim point1(0 To 2) As Double
    Dim point2(0 To 2) As Double
    point1(0) = 1.3: point1(1) = 7.8: point1(2) = 0
    point2(0) = 13.7: point2(1) = -2.6: point2(2) = 0
    ZoomWindow point1, point2
    
' ZoomScaled
    MsgBox "Perform a ZoomScaled using:" & vbCrLf & _
           "Scale Type: acZoomScaledRelative" & vbCrLf & _
           "Scale Factor: 2", , "ZoomWindow Example"
    Dim scalefactor As Double
    Dim scaletype As Integer
    scalefactor = 2
    scaletype = acZoomScaledRelative
    ZoomScaled scalefactor, scaletype
    
' ZoomExtents
    MsgBox "Perform a ZoomExtents", , "ZoomWindow Example"
    ZoomExtents
    
' ZoomPickWindow
    MsgBox "Perform a ZoomPickWindow", , "ZoomWindow Example"
    ZoomPickWindow
    
' ZoomCenter
    MsgBox "Perform a ZoomCenter using:" & vbCrLf & _
           "Center 3, 3, 0" & vbCrLf & _
           "Magnification: 10", , "ZoomWindow Example"
    Dim zcenter(0 To 2) As Double
    Dim magnification As Double
    zcenter(0) = 3: zcenter(1) = 3: zcenter(2) = 0
    magnification = 10
    ZoomCenter zcenter, magnification
   
End Sub
Sub Example_ZoomExtents()
    ' This example creates several objects in model space and
    ' then performs a variety of zooms on the drawing.
    
    ' Create a Ray object in model space
    Dim rayObj As AcadRay
    Dim basePoint(0 To 2) As Double
    Dim SecondPoint(0 To 2) As Double
    basePoint(0) = 3#: basePoint(1) = 3#: basePoint(2) = 0#
    SecondPoint(0) = 1#: SecondPoint(1) = 3#: SecondPoint(2) = 0#
    Set rayObj = ThisDrawing.ModelSpace.AddRay(basePoint, SecondPoint)
    
    ' Create a polyline object in model space
    Dim plineObj As AcadLWPolyline
    Dim points(0 To 5) As Double
    points(0) = 3: points(1) = 7
    points(2) = 9: points(3) = 2
    points(4) = 3: points(5) = 5
    Set plineObj = ThisDrawing.ModelSpace.AddLightWeightPolyline(points)
    plineObj.Closed = True

    ' Create a line object in model space
    Dim lineObj As AcadLine
    Dim startPoint(0 To 2) As Double
    Dim endPoint(0 To 2) As Double
    startPoint(0) = 0: startPoint(1) = 0: startPoint(2) = 0
    endPoint(0) = 2: endPoint(1) = 2: endPoint(2) = 0
    Set lineObj = ThisDrawing.ModelSpace.AddLine(startPoint, endPoint)
    
    ' Create a circle object in model space
    Dim circObj As AcadCircle
    Dim centerPt(0 To 2) As Double
    Dim radius As Double
    centerPt(0) = 20: centerPt(1) = 30: centerPt(2) = 0
    radius = 3
    Set circObj = ThisDrawing.ModelSpace.AddCircle(centerPt, radius)

    ' Create an ellipse object in model space
    Dim ellObj As AcadEllipse
    Dim majAxis(0 To 2) As Double
    Dim center(0 To 2) As Double
    Dim radRatio As Double
    center(0) = 5#: center(1) = 5#: center(2) = 0#
    majAxis(0) = 10: majAxis(1) = 20#: majAxis(2) = 0#
    radRatio = 0.3
    Set ellObj = ThisDrawing.ModelSpace.AddEllipse(center, majAxis, radRatio)

' ZoomAll
    MsgBox "Perform a ZoomAll", , "ZoomWindow Example"
    ZoomAll
    
' ZoomWindow
    MsgBox "Perform a ZoomWindow using the following coordinates:" & vbCrLf & _
           "1.3, 7.8, 0" & vbCrLf & _
           "13.7, -2.6, 0", , "ZoomWindow Example"
           
    Dim point1(0 To 2) As Double
    Dim point2(0 To 2) As Double
    point1(0) = 1.3: point1(1) = 7.8: point1(2) = 0
    point2(0) = 13.7: point2(1) = -2.6: point2(2) = 0
    ZoomWindow point1, point2
    
' ZoomScaled
    MsgBox "Perform a ZoomScaled using:" & vbCrLf & _
           "Scale Type: acZoomScaledRelative" & vbCrLf & _
           "Scale Factor: 2", , "ZoomWindow Example"
    Dim scalefactor As Double
    Dim scaletype As Integer
    scalefactor = 2
    scaletype = acZoomScaledRelative
    ZoomScaled scalefactor, scaletype
    
' ZoomExtents
    MsgBox "Perform a ZoomExtents", , "ZoomWindow Example"
    ZoomExtents
    
' ZoomPickWindow
    MsgBox "Perform a ZoomPickWindow", , "ZoomWindow Example"
    ZoomPickWindow
    
' ZoomCenter
    MsgBox "Perform a ZoomCenter using:" & vbCrLf & _
           "Center 3, 3, 0" & vbCrLf & _
           "Magnification: 10", , "ZoomWindow Example"
    Dim zcenter(0 To 2) As Double
    Dim magnification As Double
    zcenter(0) = 3: zcenter(1) = 3: zcenter(2) = 0
    magnification = 10
    ZoomCenter zcenter, magnification
   
End Sub
Sub Example_Add3DPoly()
    
    Dim polyObj As Acad3DPolyline
    Dim points(0 To 8) As Double
    
    ' Create the array of points
    points(0) = 0: points(1) = 0: points(2) = 0
    points(3) = 10: points(4) = 10: points(5) = 10
    points(6) = 30: points(7) = 20: points(8) = 30
    
    ' Create a 3DPolyline in model space
    Set polyObj = ThisDrawing.ModelSpace.Add3DPoly(points)
    ZoomAll
    
End Sub
Sub Example_TranslateCoordinates()
    ' This example creates a UCS with an origin at 2, 2, 2.
    ' Next, a point is entered by the user. The WCS and UCS
    ' coordinates of that point are output in a Msgbox.
    
    ' Create a UCS named "New_UCS" in current drawing
    Dim ucsObj As AcadUCS
    Dim origin(0 To 2) As Double
    Dim xAxisPnt(0 To 2) As Double
    Dim yAxisPnt(0 To 2) As Double
    
    ' Define the UCS
    origin(0) = 2#: origin(1) = 2#: origin(2) = 2#
    xAxisPnt(0) = 5#: xAxisPnt(1) = 2#: xAxisPnt(2) = 2#
    yAxisPnt(0) = 2#: yAxisPnt(1) = 6#: yAxisPnt(2) = 2#
    
    ' Add the UCS to the UserCoordinatesSystems collection
    Set ucsObj = ThisDrawing.UserCoordinateSystems.Add(origin, xAxisPnt, yAxisPnt, "New_UCS")
    ThisDrawing.ActiveUCS = ucsObj
    
    ' Get the active viewport and make sure the UCS icon is on
    Dim viewportObj As AcadViewport
    Set viewportObj = ThisDrawing.ActiveViewport
    viewportObj.UCSIconOn = True
    viewportObj.UCSIconAtOrigin = True
    ThisDrawing.ActiveViewport = viewportObj
   
    ' Have the user enter a points
    Dim pointWCS As Variant
    pointWCS = ThisDrawing.Utility.GetPoint(, "Enter a point to translate:")
    
    ' Translate the point into UCS coordinates
    Dim pointUCS As Variant
    pointUCS = ThisDrawing.Utility.TranslateCoordinates(pointWCS, acWorld, acUCS, False)
    
    ' Display the coordinates of the point
    MsgBox "The point has the following coordinates:" & vbCrLf & _
            "WCS: " & pointWCS(0) & ", " & pointWCS(1) & ", " & pointWCS(2) & vbCrLf & _
            "UCS: " & pointUCS(0) & ", " & pointUCS(1) & ", " & pointUCS(2), , "TranslateCoordinates Example"

End Sub
Sub Example_UnLoadARX()
    ' This example unloads an arx application from the AutoCAD session.
    
    ' Note: The application listed here does not exist and
    ' will cause an error when run. Change the application name
    ' to the name of your ARX Application.
    On Error GoTo ERRORHANDLER
    ThisDrawing.Application.UnloadArx ("MyARXApp.dll")
        
ERRORHANDLER:
    MsgBox Err.Description, , "UnloadARX"
    
End Sub
Sub Example_Update()
    ' This example creates a line in model space. It displays a
    ' Msgbox immediately before the call to update the line and
    ' again after the call.
    Dim lineObj As AcadLine
    Dim startPoint(0 To 2) As Double
    Dim endPoint(0 To 2) As Double

    ' Create a Line object in model space
    startPoint(0) = 2#: startPoint(1) = 2#: startPoint(2) = 0#
    endPoint(0) = 4#: endPoint(1) = 4#: endPoint(2) = 0#
    Set lineObj = ThisDrawing.ModelSpace.AddLine(startPoint, endPoint)
    lineObj.Color = acRed
    
    MsgBox "Before the update.", , "Update Example"
    ' The following code draws an object in AutoCAD window
    lineObj.Update
    MsgBox "After the update.", , "Update Example"
    
    ' The following call updates the entire drawing
    ThisDrawing.Application.Update
    
End Sub
Sub Example_WBlock()
    ' This example creates several objects in model space and
    ' adds them to a selection set. This selection set is then
    ' output as a new drawing file.
    
    ' Create a Ray object in model space
    Dim rayObj As AcadRay
    Dim basePoint(0 To 2) As Double
    Dim SecondPoint(0 To 2) As Double
    basePoint(0) = 3#: basePoint(1) = 3#: basePoint(2) = 0#
    SecondPoint(0) = 1#: SecondPoint(1) = 3#: SecondPoint(2) = 0#
    Set rayObj = ThisDrawing.ModelSpace.AddRay(basePoint, SecondPoint)
    
    ' Create a polyline object in model space
    Dim plineObj As AcadLWPolyline
    Dim points(0 To 5) As Double
    points(0) = 3: points(1) = 7
    points(2) = 9: points(3) = 2
    points(4) = 3: points(5) = 5
    Set plineObj = ThisDrawing.ModelSpace.AddLightWeightPolyline(points)
    plineObj.Closed = True

    ' Create a line object in model space
    Dim lineObj As AcadLine
    Dim startPoint(0 To 2) As Double
    Dim endPoint(0 To 2) As Double
    startPoint(0) = 0: startPoint(1) = 0: startPoint(2) = 0
    endPoint(0) = 2: endPoint(1) = 2: endPoint(2) = 0
    Set lineObj = ThisDrawing.ModelSpace.AddLine(startPoint, endPoint)
    
    ' Create a circle object in model space
    Dim circObj As AcadCircle
    Dim centerPt(0 To 2) As Double
    Dim radius As Double
    centerPt(0) = 20: centerPt(1) = 30: centerPt(2) = 0
    radius = 3
    Set circObj = ThisDrawing.ModelSpace.AddCircle(centerPt, radius)

    ' Create an ellipse object in model space
    Dim ellObj As AcadEllipse
    Dim majAxis(0 To 2) As Double
    Dim center(0 To 2) As Double
    Dim radRatio As Double
    center(0) = 5#: center(1) = 5#: center(2) = 0#
    majAxis(0) = 10: majAxis(1) = 20#: majAxis(2) = 0#
    radRatio = 0.3
    Set ellObj = ThisDrawing.ModelSpace.AddEllipse(center, majAxis, radRatio)

    ZoomAll
    
    ' Create a selection set
    Dim ssetObj As AcadSelectionSet
    Set ssetObj = ThisDrawing.SelectionSets.Add("WBLOCKSET")
    
    ' Iterate through the model space collection and add
    ' each item found to an array of objects
    ReDim objsInModelSpace(0 To ThisDrawing.ModelSpace.count - 1) As AcadEntity
    Dim I As Integer
    For I = 0 To ThisDrawing.ModelSpace.count - 1
        Set objsInModelSpace(I) = ThisDrawing.ModelSpace.Item(I)
    Next
    
    ' Add the array of objects into the selection set
    ssetObj.AddItems objsInModelSpace
    
    ' Output the selection set to a new file
    ThisDrawing.Wblock "C:\AutoCAD\WBlock_example.dwg", ssetObj
    
End Sub
Sub Example_LensLength()
    ' This example creates a new paperspace viewport.
    ' It then displays the lens length of the viewport.
    
    Dim pviewportObj As AcadPViewport
    Dim center(0 To 2) As Double
    Dim width As Double
    Dim height As Double
    
    ' Define the pviewport
    center(0) = 3: center(1) = 3: center(2) = 0
    width = 40
    height = 40
    
    ' Change from model space to paperspace
    ThisDrawing.ActiveSpace = acPaperSpace

    ' Create the pviewport
    Set pviewportObj = ThisDrawing.PaperSpace.AddPViewport(center, width, height)
    pviewportObj.DISPLAY True
    ThisDrawing.mspace = True
    ThisDrawing.ActivePViewport = pviewportObj
    ThisDrawing.Regen acAllViewports
    
    ' Find the Lens Length for the viewport
    Dim lenslgnth As Double
    lenslgnth = pviewportObj.LensLength
    MsgBox "The lens length of the paperspace viewport is " & pviewportObj.LensLength, , "LensLength Example"

End Sub
Sub Example_AddShape()
    ' This example creates a BAT shape from the ltypeshp.shx file.
    
    ' Load the shape file containing the shape you wish to create.
    ' Note: Replace the ltypeshp.shx file name
    ' with a valid shape file for your system.
    On Error GoTo ERRORHANDLER
    ThisDrawing.LoadShapeFile ("C:/Program Files/ACAD2000/Support/ltypeshp.shx")

    
    Dim shapeObj As AcadShape
    Dim shapeName As String
    Dim insertionPoint(0 To 2) As Double
    Dim scalefactor As Double
    Dim rotation As Double
    
    ' "diode" is defined in es.shx file
    shapeName = "BAT"
    insertionPoint(0) = 2#: insertionPoint(1) = 2#: insertionPoint(2) = 0#
    scalefactor = 1#
    rotation = 0#       ' Radians
    
    ' Create the diode shape object in model space
    Set shapeObj = ThisDrawing.ModelSpace.AddShape(shapeName, insertionPoint, scalefactor, rotation)
    Exit Sub
    
ERRORHANDLER:
    MsgBox "Cannot find the shape file.", , "AddShape Example"
    
End Sub

Sub Example_GetWidth()
    ' This example creates an MText object in model space.
    ' It then changes the width of the MText object.
    
    Dim MTextObj As AcadMText
    Dim corner(0 To 2) As Double
    Dim width As Double
    Dim text As String
    corner(0) = 0#: corner(1) = 5#: corner(2) = 0#
    width = 10
    text = "This is the text String for the mtext Object"

    ' Creates the mtext Object
    Set MTextObj = ThisDrawing.ModelSpace.AddMText(corner, width, text)
    ZoomAll
    
    ' Find the current width of the mtext object
    width = MTextObj.width
    MsgBox "The current width of the mtext object is " & MTextObj.width, , "Width Example"
    
    ' Change the width of the mtext object
    MTextObj.width = width / 2
    MTextObj.Update
    MsgBox "The new width of the mtext object is " & MTextObj.width, , "Width Example"
    
End Sub
Sub Example_SetView()
    ' This example creates a new view.
    ' It then changes the active viewport to
    ' the newly created view.
    
    ' First, open a sample drawing.
    ThisDrawing.Application.Documents.Open "C:\AutoCAD\Sample\campus.dwg"
    
    ' Create a new view
    Dim viewObj As AcadView
    Set viewObj = ThisDrawing.Views.Add("TESTVIEW")
    
    ' Set the view characteristics
    viewObj.center(0) = 374: viewObj.center(1) = 313
    viewObj.width = 450
    viewObj.height = 354
    
    ' Get the current active viewport
    Dim viewportObj As AcadViewport
    Set viewportObj = ThisDrawing.ActiveViewport
    MsgBox "Change to the saved view.", , "SetView Example"
       
    ' Set the view in the viewport
    viewportObj.SetView viewObj
    ThisDrawing.ActiveViewport = viewportObj
        
    ThisDrawing.Regen True
    
End Sub
Sub Example_DeleteProfile()
    ' This example deletes a profile.
    
    Dim preferences As AcadPreferences
    Dim strProfileToDelete As String
    
    Set preferences = ThisDrawing.Application.preferences
    
    ' Specify the profile to delete.
    strProfileToDelete = "TestProfile"
    
    ' Delete the profile
    ' The call will fail if "TestProfile" does not exist or
    ' if "TestProfile" is the current profile.
    On Error GoTo Error
    preferences.Profiles.DeleteProfile strProfileToDelete
    Exit Sub
Error:
        MsgBox "DeleteProfile of " & strProfileToDelete & " failed. " & Err.Description, , "DeleteProfile Example"
        
End Sub
Sub Example_AutoSavePath()
    ' This example returns the current setting of
    ' AutoSavePath. It then changes the value, and finally
    ' it resets the value back to the original setting.
    
    Dim preferences As AcadPreferences
    Dim currAutoSavePath As String
    Dim newAutoSavePath As String
    
    Set preferences = ThisDrawing.Application.preferences
    
    ' Retrieve the current AutoSavePath value
    currAutoSavePath = preferences.Files.AutoSavePath
    If currAutoSavePath = "" Then
        MsgBox "AutoSavePath is not currently set.", vbInformation, "AutoSavePath Example"
    Else
        MsgBox "The current value for AutoSavePath is " & currAutoSavePath, vbInformation, "AutoSavePath Example"
    End If
    
    ' Change the value for AutoSavePath
    newAutoSavePath = "C:\AutoCAD\"
    preferences.Files.AutoSavePath = newAutoSavePath
    MsgBox "The new value for AutoSavePath is " & newAutoSavePath, vbInformation, "AutoSavePath Example"
    
    ' Reset AutoSavePath to its original value
    preferences.Files.AutoSavePath = currAutoSavePath
    If currAutoSavePath = "" Then
        MsgBox "AutoSavePath is reset to Null.", vbInformation, "AutoSavePath Example"
    Else
        MsgBox "The AutoSavePath value is reset to " & currAutoSavePath, vbInformation, "AutoSavePath Example"
    End If
End Sub
Sub Example_TextString()
    ' This example creates a text object in model space.
    ' It then returns the text string for that object.
    
    Dim textObj As AcadText
    Dim text As String
    Dim insertionPoint(0 To 2) As Double
    Dim height As Double
    
    ' Define the text object
    text = "Hello, World."
    insertionPoint(0) = 2: insertionPoint(1) = 2: insertionPoint(2) = 0
    height = 0.5
    
    ' Create the text object in model space
    Set textObj = ThisDrawing.ModelSpace.AddText(text, insertionPoint, height)
    ZoomAll
    
    ' Return the current text string for the object
    text = textObj.textString
    MsgBox "The TextString property equals: " & text, vbInformation, "TextString Example"
        
End Sub
Sub Example_RemoveHiddenLines()
    ' This example creates a new paperspace viewport.
    ' It then displays the value of RemoveHiddenLines for the viewport.
    
    Dim pviewportObj As AcadPViewport
    Dim center(0 To 2) As Double
    Dim width As Double
    Dim height As Double
    
    ' Define the pviewport
    center(0) = 3: center(1) = 3: center(2) = 0
    width = 40
    height = 40
    
    ' Change from model space to paperspace
    ThisDrawing.ActiveSpace = acPaperSpace

    ' Create the pviewport
    Set pviewportObj = ThisDrawing.PaperSpace.AddPViewport(center, width, height)
    pviewportObj.DISPLAY True
    ThisDrawing.mspace = True
    ThisDrawing.ActivePViewport = pviewportObj
    ThisDrawing.Regen acAllViewports
    
    ' Find the value for RemoveHiddenLines for the viewport
    Dim removeHidden As Boolean
    removeHidden = pviewportObj.RemoveHiddenLines
    MsgBox "The value of the RemoveHiddenLines property for the paperspace viewport is " & pviewportObj.RemoveHiddenLines, , "RemoveHiddenLines Example"

End Sub
Sub Example_TwistAngle()
    ' This example creates a new paperspace viewport.
    ' It then displays the twist angle of the viewport.
    
    Dim pviewportObj As AcadPViewport
    Dim center(0 To 2) As Double
    Dim width As Double
    Dim height As Double
    
    ' Define the pviewport
    center(0) = 3: center(1) = 3: center(2) = 0
    width = 40
    height = 40
    
    ' Change from model space to paperspace
    ThisDrawing.ActiveSpace = acPaperSpace

    ' Create the pviewport
    Set pviewportObj = ThisDrawing.PaperSpace.AddPViewport(center, width, height)
    pviewportObj.DISPLAY True
    ThisDrawing.mspace = True
    ThisDrawing.ActivePViewport = pviewportObj
    ThisDrawing.Regen acAllViewports
    
    ' Find the twist angle for the viewport
    Dim twistAngle As Double
    twistAngle = pviewportObj.twistAngle
    MsgBox "The twist angle of the paperspace viewport is " & pviewportObj.twistAngle, , "TwistAngle Example"

End Sub
Sub Example_MSpace()
    ' This example creates a new paperspace viewport.
    ' It then toggles the ability to edit in modelspace using
    ' the MSpace property.
    
    Dim pviewportObj As AcadPViewport
    Dim center(0 To 2) As Double
    Dim width As Double
    Dim height As Double
    
    ' Define the pviewport
    center(0) = 3: center(1) = 3: center(2) = 0
    width = 40
    height = 40
    
    ' Change from model space to paperspace
    ThisDrawing.ActiveSpace = acPaperSpace

    ' Create the pviewport
    Set pviewportObj = ThisDrawing.PaperSpace.AddPViewport(center, width, height)
    pviewportObj.DISPLAY True
    ThisDrawing.mspace = True
    ThisDrawing.ActivePViewport = pviewportObj
    ThisDrawing.Regen acAllViewports
    
    ' Find the current MSpace value
    MsgBox "The ability to edit modelspace from this PViewport is " & IIf(ThisDrawing.mspace, "on.", "off."), , "MSpace Example"
    
    ' Toggle the setting of MSpace
    ThisDrawing.mspace = False
    MsgBox "The ability to edit modelspace from this PViewport is now " & IIf(ThisDrawing.mspace, "on.", "off."), , "MSpace Example"

End Sub
Sub Example_AppendItems()
    ' This example creates a group and several objects.
    ' It then appends the objects to the group.
    
    ' Create the new group
    Dim groupObj As AcadGroup
    Set groupObj = ThisDrawing.Groups.Add("TEST_GROUP")
            
    ' Create a Ray object in model space
    Dim rayObj As AcadRay
    Dim basePoint(0 To 2) As Double
    Dim SecondPoint(0 To 2) As Double
    basePoint(0) = 3#: basePoint(1) = 3#: basePoint(2) = 0#
    SecondPoint(0) = 1#: SecondPoint(1) = 3#: SecondPoint(2) = 0#
    Set rayObj = ThisDrawing.ModelSpace.AddRay(basePoint, SecondPoint)
    
    ' Create a polyline object in model space
    Dim plineObj As AcadLWPolyline
    Dim points(0 To 5) As Double
    points(0) = 3: points(1) = 7
    points(2) = 9: points(3) = 2
    points(4) = 3: points(5) = 5
    Set plineObj = ThisDrawing.ModelSpace.AddLightWeightPolyline(points)
    plineObj.Closed = True

    ' Create a line object in model space
    Dim lineObj As AcadLine
    Dim startPoint(0 To 2) As Double
    Dim endPoint(0 To 2) As Double
    startPoint(0) = 0: startPoint(1) = 0: startPoint(2) = 0
    endPoint(0) = 2: endPoint(1) = 2: endPoint(2) = 0
    Set lineObj = ThisDrawing.ModelSpace.AddLine(startPoint, endPoint)
    
    ' Create a circle object in model space
    Dim circObj As AcadCircle
    Dim centerPt(0 To 2) As Double
    Dim radius As Double
    centerPt(0) = 20: centerPt(1) = 30: centerPt(2) = 0
    radius = 3
    Set circObj = ThisDrawing.ModelSpace.AddCircle(centerPt, radius)

    ' Create an ellipse object in model space
    Dim ellObj As AcadEllipse
    Dim majAxis(0 To 2) As Double
    Dim center(0 To 2) As Double
    Dim radRatio As Double
    center(0) = 5#: center(1) = 5#: center(2) = 0#
    majAxis(0) = 10: majAxis(1) = 20#: majAxis(2) = 0#
    radRatio = 0.3
    Set ellObj = ThisDrawing.ModelSpace.AddEllipse(center, majAxis, radRatio)

    ZoomAll
    
    ' Iterate through the model space collection.
    ' Collect the objects found into an array of objects
    ' to be added to the group.
    ReDim appendObjs(0 To ThisDrawing.ModelSpace.count - 1) As AcadEntity
    Dim I As Integer
    For I = 0 To ThisDrawing.ModelSpace.count - 1
        Set appendObjs(I) = ThisDrawing.ModelSpace.Item(I)
    Next
    
    ' Add the array of objects to the group
    groupObj.AppendItems appendObjs
    
    ThisDrawing.Regen acActiveViewport
    
End Sub
Sub Example_Utility()
    ' This example creates a spline in model space using the
    ' CreateTypedArray method off of the utility object.
        
    ' Create the spline
    Dim splineObj As AcadSpline
    Dim noOfPoints As Integer
    Dim startTan As Variant
    Dim endTan As Variant
    Dim fitPoints As Variant
    Dim utilObj As Object   ' CreateTypedArray needs to be a late bound object
    Set utilObj = ThisDrawing.Utility
    
    noOfPoints = 3
    utilObj.CreateTypedArray startTan, vbDouble, 0.5, 0.5, 0
    utilObj.CreateTypedArray endTan, vbDouble, 0.5, 0.5, 0
    utilObj.CreateTypedArray fitPoints, vbDouble, 1, 1, 0, 5, 5, 0, 10, 0, 0
    Set splineObj = ThisDrawing.ModelSpace.AddSpline(fitPoints, startTan, endTan)
    
    ZoomAll
    
End Sub
Sub Example_GetObject()
    ' This example creates a dictionary and adds
    ' a custom object to that dictionary. It then
    ' returns the object using GetObject.
    
    Dim dictObj As AcadDictionary
    Set dictObj = ThisDrawing.Dictionaries.Add("TEST_DICTIONARY")
    
    ' Load the ARX application that defines the custom object.
    ' Note: The application listed here does not exist and
    ' will cause an error when run. Change the application name
    ' to the path and name of your ARX Application.
    On Error GoTo ERRORHANDLER
    ThisDrawing.Application.LoadArx ("MyARXApp.dll")
    
    ' Create the custom object in the dictionary
    Dim keyName As String
    Dim className As String
    Dim customObj As AcadObject
    
    keyName = "OBJ1"
    className = "CAsdkDictObject"
    
    Set customObj = dictObj.AddObject(keyName, className)
    
    ' Find the object
    Dim tempObj As Object
    Set tempObj = dictObj.GetObject(keyName)
    
ERRORHANDLER:
    MsgBox Err.Description, , "GetObject Example"
    
End Sub
Sub Example_AddMenuItem()
    ' This example creates a new menu called TestMenu and inserts a menu item
    ' into it. The menu is then displayed on the menu bar.
    ' To remove the menu after execution of this macro, use the Customize Menu
    ' option from the Tools menu.
    
    Dim currMenuGroup As acadMenuGroup
    Set currMenuGroup = ThisDrawing.Application.MenuGroups.Item(0)
    
    ' Create the new menu
    Dim newMenu As AcadPopupMenu
    Set newMenu = currMenuGroup.Menus.Add("TestMenu")
    
    ' Add a menu item to the new menu
    Dim newMenuItem As AcadPopupMenuItem
    Dim openMacro As String
    ' Assign the macro string the VB equivalent of "ESC ESC _open "
    openMacro = Chr(3) & Chr(3) & Chr(95) & "open" & Chr(32)
    
    Set newMenuItem = newMenu.AddMenuItem(newMenu.count + 1, "Open", openMacro)
    
    ' Display the menu on the menu bar
    newMenu.InsertInMenuBar (ThisDrawing.Application.MenuBar.count + 1)
    
End Sub
Sub Example_Macro()
    ' This example creates a new menu called TestMenu and inserts a menu item
    ' into it. The menu is then displayed on the menu bar.
    ' To remove the menu after execution of this macro, use the Customize Menu
    ' option from the Tools menu.
    
    Dim currMenuGroup As acadMenuGroup
    Set currMenuGroup = ThisDrawing.Application.MenuGroups.Item(0)
    
    ' Create the new menu
    Dim newMenu As AcadPopupMenu
    Set newMenu = currMenuGroup.Menus.Add("TestMenu")
    
    ' Add a menu item to the new menu
    Dim newMenuItem As AcadPopupMenuItem
    Dim openMacro As String
    ' Assign the macro string the VB equivalent of "ESC ESC _open "
    openMacro = Chr(3) & Chr(3) & Chr(95) & "open" & Chr(32)
    
    Set newMenuItem = newMenu.AddMenuItem(newMenu.count + 1, "Open", openMacro)
    
    ' Display the menu on the menu bar
    newMenu.InsertInMenuBar (ThisDrawing.Application.MenuBar.count + 1)
    
    MsgBox "The macro for the Open menu item is: " & newMenuItem.Macro
    
End Sub
Sub Example_MenuFileName()
    ' This example finds the file name for the all loaded menu groups.
    
    Dim fileNames As String
    Dim menuGroup As acadMenuGroup
    
    fileNames = ""
    For Each menuGroup In ThisDrawing.Application.MenuGroups
        fileNames = fileNames & menuGroup.name & "  " & menuGroup.MenuFileName & vbCrLf
    Next menuGroup
    MsgBox fileNames
End Sub
Sub Example_Menus()
    ' This example finds the names of the all menus in the first menu group.
    
    Dim menuNames As String
    Dim menuCollection As AcadPopupMenus
    Dim menu As AcadPopupMenu
    
    Set menuCollection = ThisDrawing.Application.MenuGroups.Item(0).Menus
    menuNames = ""
    For Each menu In menuCollection
        menuNames = menuNames & menu.name & vbCrLf
    Next menu
    MsgBox menuNames
End Sub
Sub Example_Toolbars()
    ' This example finds the names of the all toolbars in the first menu group.
    
    Dim toolbarNames As String
    Dim toolbarCollection As AcadToolbars
    Dim toolbar As AcadToolbar
    
    Set toolbarCollection = ThisDrawing.Application.MenuGroups.Item(0).Toolbars
    toolbarNames = ""
    For Each toolbar In toolbarCollection
        toolbarNames = toolbarNames & toolbar.name & vbCrLf
    Next toolbar
    MsgBox toolbarNames
End Sub
Sub Example_Enable()
    ' This example creates a new menu called TestMenu and inserts two menu items
    ' into it. The second menu item is then disabled.
    ' The menu is displayed on the menu bar.
    ' To remove the menu after execution of this macro, use the Customize Menu
    ' option from the Tools menu.
    
    Dim currMenuGroup As acadMenuGroup
    Set currMenuGroup = ThisDrawing.Application.MenuGroups.Item(0)
    
    ' Create the new menu
    Dim newMenu As AcadPopupMenu
    Set newMenu = currMenuGroup.Menus.Add("TestMenu")
    
    ' Add two menu items to the new menu
    Dim MenuEnable As AcadPopupMenuItem
    Dim MenuDisable As AcadPopupMenuItem
    Dim MenuSeparator As AcadPopupMenuItem
    Dim openMacro As String
    
    ' Assign the macro string the VB equivalent of "ESC ESC _open "
    openMacro = Chr(3) & Chr(3) & Chr(95) & "open" & Chr(32)
    
    Set MenuEnable = newMenu.AddMenuItem(newMenu.count + 1, "OpenEnabled", openMacro)
    Set MenuSeparator = newMenu.AddSeparator("")
    Set MenuDisable = newMenu.AddMenuItem(newMenu.count + 1, "OpenDisabled", openMacro)
    
    ' Disable the new menu item
    MenuDisable.Enable = False
    
    ' Display the menu on the menu bar
    newMenu.InsertInMenuBar (ThisDrawing.Application.MenuBar.count + 1)
    
End Sub
Sub Example_Check()
    ' This example creates a new menu called TestMenu and inserts two menu items
    ' into it. The second menu item is then checked.
    ' The menu is displayed on the menu bar.
    ' To remove the menu after execution of this macro, use the Customize Menu
    ' option from the Tools menu.
    
    Dim currMenuGroup As acadMenuGroup
    Set currMenuGroup = ThisDrawing.Application.MenuGroups.Item(0)
    
    ' Create the new menu
    Dim newMenu As AcadPopupMenu
    Set newMenu = currMenuGroup.Menus.Add("TestMenu")
    
    ' Add two menu items to the new menu
    Dim Menu1 As AcadPopupMenuItem
    Dim Menu2 As AcadPopupMenuItem
    Dim MenuSeparator As AcadPopupMenuItem
    Dim openMacro As String
    
    ' Assign the macro string the VB equivalent of "ESC ESC _open "
    openMacro = Chr(3) & Chr(3) & Chr(95) & "open" & Chr(32)
    
    Set Menu1 = newMenu.AddMenuItem(newMenu.count + 1, "Open1", openMacro)
    Set MenuSeparator = newMenu.AddSeparator("")
    Set Menu2 = newMenu.AddMenuItem(newMenu.count + 1, "Open2", openMacro)
    
    ' Disable the new menu item
    Menu2.Check = True
    
    ' Display the menu on the menu bar
    newMenu.InsertInMenuBar (ThisDrawing.Application.MenuBar.count + 1)
    
End Sub
Sub Example_AddSeparator()
    ' This example creates a new menu called TestMenu and inserts a menu item
    ' and a separator into it. The menu is then displayed on the menu bar.
    ' To remove the menu after execution of this macro, use the Customize Menu
    ' option from the Tools menu.
    
    Dim currMenuGroup As acadMenuGroup
    Set currMenuGroup = ThisDrawing.Application.MenuGroups.Item(0)
    
    ' Create the new menu
    Dim newMenu As AcadPopupMenu
    Set newMenu = currMenuGroup.Menus.Add("TestMenu")
    
    ' Add a menu item to the new menu
    Dim newMenuItem As AcadPopupMenuItem
    Dim openMacro As String
    
    ' Assign the macro string the VB equivalent of "ESC ESC _open "
    openMacro = Chr(3) & Chr(3) & Chr(95) & "open" & Chr(32)
    
    Set newMenuItem = newMenu.AddMenuItem(newMenu.count + 1, "Open", openMacro)
    
    ' Add a separator to the end of the menu
    Dim newMenuSeparator As AcadPopupMenuItem
    Set newMenuSeparator = newMenu.AddSeparator("")
    
    ' Display the menu on the menu bar
    newMenu.InsertInMenuBar (ThisDrawing.Application.MenuBar.count + 1)
    
End Sub
Sub Example_AddSubMenu()
    ' This example creates a new menu called TestMenu and inserts a submenu item
    ' called NewFile. It then creates a menu item, called open,
    ' on the submenu.
    
    ' The menu is then displayed on the menu bar.
    ' To remove the menu after execution of this macro, use the Customize Menu
    ' option from the Tools menu.
    
    Dim currMenuGroup As acadMenuGroup
    Set currMenuGroup = ThisDrawing.Application.MenuGroups.Item(0)
    
    ' Create the new menu
    Dim newMenu As AcadPopupMenu
    Set newMenu = currMenuGroup.Menus.Add("TestMenu")
    
    ' Add the submenu
    Dim FileSubMenu As AcadPopupMenu
    Set FileSubMenu = newMenu.AddSubMenu("", "NewFile")
    
    
    ' Add a menu item to the sub menu
    Dim newMenuItem As AcadPopupMenuItem
    Dim openMacro As String
    
    ' Assign the macro string the VB equivalent of "ESC ESC _open "
    openMacro = Chr(3) & Chr(3) & Chr(95) & "open" & Chr(32)
    
    Set newMenuItem = FileSubMenu.AddMenuItem(newMenu.count + 1, "Open", openMacro)
    
    ' Display the menu on the menu bar
    newMenu.InsertInMenuBar (ThisDrawing.Application.MenuBar.count + 1)
    
End Sub
Sub Example_InsertInMenuBar()
    ' This example creates a new menu called TestMenu and inserts a menu item
    ' into it. The menu is then displayed on the menu bar.
    ' To remove the menu after execution of this macro, use the Customize Menu
    ' option from the Tools menu.
    
    Dim currMenuGroup As acadMenuGroup
    Set currMenuGroup = ThisDrawing.Application.MenuGroups.Item(0)
    
    ' Create the new menu
    Dim newMenu As AcadPopupMenu
    Set newMenu = currMenuGroup.Menus.Add("TestMenu")
    
    ' Add a menu item to the new menu
    Dim newMenuItem As AcadPopupMenuItem
    Dim openMacro As String
    ' Assign the macro string the VB equivalent of "ESC ESC _open "
    openMacro = Chr(3) & Chr(3) & Chr(95) & "open" & Chr(32)
    
    Set newMenuItem = newMenu.AddMenuItem(newMenu.count + 1, "Open", openMacro)
    
    ' Display the menu on the menu bar
    newMenu.InsertInMenuBar (ThisDrawing.Application.MenuBar.count + 1)
    
End Sub
Sub Example_RemoveFromMenuBar()
    ' This example creates a new menu called TestMenu and inserts a menu item
    ' into it. The menu is then displayed on the menu bar, and then
    ' removed from the menu bar.
    
    Dim currMenuGroup As acadMenuGroup
    Set currMenuGroup = ThisDrawing.Application.MenuGroups.Item(0)
    
    ' Create the new menu
    Dim newMenu As AcadPopupMenu
    Set newMenu = currMenuGroup.Menus.Add("TestMenu")
    
    ' Add a menu item to the new menu
    Dim newMenuItem As AcadPopupMenuItem
    Dim openMacro As String
    ' Assign the macro string the VB equivalent of "ESC ESC _open "
    openMacro = Chr(3) & Chr(3) & Chr(95) & "open" & Chr(32)
    
    Set newMenuItem = newMenu.AddMenuItem(newMenu.count + 1, "Open", openMacro)
    
    ' Display the menu on the menu bar
    newMenu.InsertInMenuBar (ThisDrawing.Application.MenuBar.count + 1)
    GoSub QUERYMENU
    
    ' Remove the menu from the menu bar
    newMenu.RemoveFromMenuBar
    GoSub QUERYMENU
    Exit Sub
    
QUERYMENU:
    If newMenu.OnMenuBar Then
        MsgBox "The menu called " & newMenu.name & " is on the menu bar."
    Else
        MsgBox "The menu called " & newMenu.name & " is not on the menu bar."
    End If
    Return
        
End Sub
Sub Example_RemoveMenuFromMenuBar()
    ' This example creates a new menu called TestMenu and inserts a menu item
    ' into it. The menu is then displayed on the menu bar, and then
    ' removed from the menu bar.
    
    Dim currMenuGroup As acadMenuGroup
    Set currMenuGroup = ThisDrawing.Application.MenuGroups.Item(0)
    
    ' Create the new menu
    Dim newMenu As AcadPopupMenu
    Set newMenu = currMenuGroup.Menus.Add("TestMenu")
    
    ' Add a menu item to the new menu
    Dim newMenuItem As AcadPopupMenuItem
    Dim openMacro As String
    ' Assign the macro string the VB equivalent of "ESC ESC _open "
    openMacro = Chr(3) & Chr(3) & Chr(95) & "open" & Chr(32)
    
    Set newMenuItem = newMenu.AddMenuItem(newMenu.count + 1, "Open", openMacro)
    
    ' Display the menu on the menu bar
    newMenu.InsertInMenuBar (ThisDrawing.Application.MenuBar.count + 1)
    GoSub QUERYMENU
    
    ' Remove the menu from the menu bar
    currMenuGroup.Menus.RemoveMenuFromMenuBar ("TestMenu")
    GoSub QUERYMENU
    Exit Sub
    
QUERYMENU:
    If newMenu.OnMenuBar Then
        MsgBox "The menu called " & newMenu.name & " is on the menu bar."
    Else
        MsgBox "The menu called " & newMenu.name & " is not on the menu bar."
    End If
    Return
        
End Sub
Sub Example_InsertMenuInMenuBar()
    ' This example creates a new menu called TestMenu and inserts a menu item
    ' into it. The menu is then displayed on the menu bar.
    
    Dim currMenuGroup As acadMenuGroup
    Set currMenuGroup = ThisDrawing.Application.MenuGroups.Item(0)
    
    ' Create the new menu
    Dim newMenu As AcadPopupMenu
    Set newMenu = currMenuGroup.Menus.Add("TestMenu")
    
    ' Add a menu item to the new menu
    Dim newMenuItem As AcadPopupMenuItem
    Dim openMacro As String
    ' Assign the macro string the VB equivalent of "ESC ESC _open "
    openMacro = Chr(3) & Chr(3) & Chr(95) & "open" & Chr(32)
    
    Set newMenuItem = newMenu.AddMenuItem(newMenu.count + 1, "Open", openMacro)
    
    ' Display the menu on the menu bar
    currMenuGroup.Menus.InsertMenuInMenuBar "TestMenu", ""
        
End Sub
Sub Example_OnMenuBar()
    ' This example creates a new menu called TestMenu and inserts a menu item
    ' into it. The menu is then displayed on the menu bar, and then
    ' removed from the menu bar.
    
    Dim currMenuGroup As acadMenuGroup
    Set currMenuGroup = ThisDrawing.Application.MenuGroups.Item(0)
    
    ' Create the new menu
    Dim newMenu As AcadPopupMenu
    Set newMenu = currMenuGroup.Menus.Add("TestMenu")
    
    ' Add a menu item to the new menu
    Dim newMenuItem As AcadPopupMenuItem
    Dim openMacro As String
    ' Assign the macro string the VB equivalent of "ESC ESC _open "
    openMacro = Chr(3) & Chr(3) & Chr(95) & "open" & Chr(32)
    
    Set newMenuItem = newMenu.AddMenuItem(newMenu.count + 1, "Open", openMacro)
    
    ' Display the menu on the menu bar
    newMenu.InsertInMenuBar (ThisDrawing.Application.MenuBar.count + 1)
    GoSub QUERYMENU
    
    ' Remove the menu from the menu bar
    currMenuGroup.Menus.RemoveMenuFromMenuBar ("TestMenu")
    GoSub QUERYMENU
    Exit Sub
    
QUERYMENU:
    If newMenu.OnMenuBar Then
        MsgBox "The menu called " & newMenu.name & " is on the menu bar."
    Else
        MsgBox "The menu called " & newMenu.name & " is not on the menu bar."
    End If
    Return
        
End Sub
Sub Example_ShortcutMenu()
    ' This example iterates through the menus collection and
    ' determines if each menu is the shortcut menu.
    
    ' Note that depending on how many menus are currently loaded, the
    ' menuStatus string may not be displayed in full.
    
    Dim currMenu As AcadPopupMenu
    Dim menuStatus As String
    
    menuStatus = ""
    For Each currMenu In ThisDrawing.Application.MenuGroups.Item(0).Menus
    If currMenu.ShortcutMenu Then
        menuStatus = menuStatus & currMenu.name & " is the shortcut menu." & vbCrLf
    Else
        menuStatus = menuStatus & currMenu.name & " is not the shortcut menu." & vbCrLf
    End If
    Next currMenu
    MsgBox menuStatus
    
End Sub
Sub Example_NameNoMnemonic()
    ' This example iterates through the menus collection and
    ' displays the Name and NameNoMnemonic property for each menu.
    
    ' Note that depending on how many menus are currently loaded, the
    ' menuStatus string may not be displayed in full.
    
    Dim currMenu As AcadPopupMenu
    Dim menuStatus As String
    
    menuStatus = ""
    For Each currMenu In ThisDrawing.Application.MenuGroups.Item(0).Menus
        menuStatus = menuStatus & currMenu.name & " -- " & currMenu.NameNoMnemonic & vbCrLf
    Next currMenu
    MsgBox menuStatus
    
End Sub
Sub Example_Width()
    ' This example creates an MText object in model space.
    ' It then changes the width of the MText object.
    
    Dim MTextObj As AcadMText
    Dim corner(0 To 2) As Double
    Dim width As Double
    Dim text As String
    corner(0) = 0: corner(1) = 5: corner(2) = 0
    width = 10
    text = "This is the text String for the mtext Object"

    ' Creates the mtext Object
    Set MTextObj = ThisDrawing.ModelSpace.AddMText(corner, width, text)
    ZoomAll
    
    ' Find the current width of the mtext object
    width = MTextObj.width
    MsgBox "The current width of the mtext object is " & MTextObj.width, , "Width Example"
    
    ' Change the width of the mtext object
    MTextObj.width = width / 2
    MTextObj.Update
    MsgBox "The new width of the mtext object is " & MTextObj.width, , "Width Example"
    
End Sub

Sub Example_AddPolyfaceMesh()
    
    Dim vertexList(0 To 17) As Double

    'Data
    vertexList(0) = 4: vertexList(1) = 7: vertexList(2) = 0
    vertexList(3) = 5: vertexList(4) = 7: vertexList(5) = 0
    vertexList(6) = 6: vertexList(7) = 7: vertexList(8) = 0
    vertexList(9) = 4: vertexList(10) = 6: vertexList(11) = 0
    vertexList(12) = 5: vertexList(13) = 6: vertexList(14) = 0
    vertexList(15) = 6: vertexList(16) = 6: vertexList(17) = 1
    

    Dim FaceList(0 To 7) As Integer

    FaceList(0) = 1
    FaceList(1) = 2
    FaceList(2) = 5
    FaceList(3) = 4
    FaceList(4) = 2
    FaceList(5) = 3
    FaceList(6) = 6
    FaceList(7) = 5

    Dim obj As AcadPolyfaceMesh
    Set obj = ModelSpace.AddPolyfaceMesh(vertexList, FaceList)
    obj.Update

    ' Change the viewing direction of the viewport to
    ' better see the polyface mesh
    Dim NewDirection(0 To 2) As Double
    NewDirection(0) = -1: NewDirection(1) = -1: NewDirection(2) = 1
    ThisDrawing.ActiveViewport.direction = NewDirection
    ThisDrawing.ActiveViewport = ThisDrawing.ActiveViewport
    ZoomAll
End Sub

Sub Example_ADCInsertUnitsDefaultSource()
    ' This example reads and modifies the ADCInsertUnitsDefaultSource
    ' preference value.
    ' When finished, this example resets the preference value back to
    ' it's original value.
    
    Dim ACADPref As AcadPreferencesUser
    Dim originalValue As Integer, newValue As Integer
    
    ' Get the user preferences object

    Set ACADPref = ThisDrawing.Application.preferences.User
    
    ' Read and display the original value
    originalValue = ACADPref.ADCInsertUnitsDefaultSource
    MsgBox "The ADCInsertUnitsDefaultSource preference is set to: " & originalValue

    ' Modify the ADCInsertUnitsDefaultSource preference by toggling the value
    ACADPref.ADCInsertUnitsDefaultSource = acInsertUnitsMillimeters

    MsgBox "The ADCInsertUnitsDefaultSource preference has been set to: " & ACADPref.ADCInsertUnitsDefaultSource

    ' Reset the preference back to it's original value
    ACADPref.ADCInsertUnitsDefaultSource = originalValue
    MsgBox "The ADCInsertUnitsDefaultSource preference was reset back to: " & originalValue
End Sub
Sub Example_ADCInsertUnitsDefaultTarget()
    ' This example reads and modifies the ADCInsertUnitsDefaultTarget
    ' preference value.
    ' When finished, this example resets the preference value back to
    ' it's original value.
    
    Dim ACADPref As AcadPreferencesUser
    Dim originalValue As Integer, newValue As Integer
    
    ' Get the user preferences object

    Set ACADPref = ThisDrawing.Application.preferences.User
    
    ' Read and display the original value
    originalValue = ACADPref.ADCInsertUnitsDefaultTarget
    MsgBox "The ADCInsertUnitsDefaultTarget preference is set to: " & originalValue

    ' Modify the ADCInsertUnitsDefaultTarget preference by toggling the value
    ACADPref.ADCInsertUnitsDefaultTarget = acInsertUnitsMillimeters

    MsgBox "The ADCInsertUnitsDefaultTarget preference has been set to: " & ACADPref.ADCInsertUnitsDefaultTarget

    ' Reset the preference back to it's original value
    ACADPref.ADCInsertUnitsDefaultTarget = originalValue
    MsgBox "The ADCInsertUnitsDefaultTarget preference was reset back to: " & originalValue
End Sub
Sub Example_ActivateMethod()
    ' This example creates two new drawings and activates each drawing in turn.
    
    Dim NewDrawing1 As AcadDocument
    Dim Newdrawing2 As AcadDocument
    Set NewDrawing1 = ThisDrawing.Application.Documents.Add("")
    Set Newdrawing2 = ThisDrawing.Application.Documents.Add("")
    
    Dim drawing As AcadDocument
    For Each drawing In ThisDrawing.Application.Documents
        drawing.Activate
        MsgBox "Drawing " & drawing.name & " is active."
    Next drawing
End Sub
Sub Example_Active()
    ' This example creates two new drawings and determines
    ' which of the drawings is the active drawing.
    
    Dim NewDrawing1 As AcadDocument
    Dim Newdrawing2 As AcadDocument
    Set NewDrawing1 = ThisDrawing.Application.Documents.Add("")
    Set Newdrawing2 = ThisDrawing.Application.Documents.Add("")
    
    Dim activeStatus As String
    Dim drawing As AcadDocument
    activeStatus = ""
    For Each drawing In ThisDrawing.Application.Documents
    If drawing.Active Then
            activeStatus = activeStatus & drawing.name & " is active." & vbCrLf
    Else
            activeStatus = activeStatus & drawing.name & " is not active." & vbCrLf
    End If
    Next drawing
    MsgBox activeStatus
End Sub
Sub Example_AddToolbarButton()
    ' This example creates a new toolbar called TestToolbar and inserts a
    ' toolbar button into it. The toolbar is then displayed.
    ' To remove the toolbar after execution of this macro, use the Customize Menu
    ' option from the Tools menu.
    
    Dim currMenuGroup As acadMenuGroup
    Set currMenuGroup = ThisDrawing.Application.MenuGroups.Item(0)
    
    ' Create the new toolbar
    Dim newToolBar As AcadToolbar
    Set newToolBar = currMenuGroup.Toolbars.Add("TestToolbar")
    
    ' Add a button to the new toolbar
    Dim newButton As AcadToolbarItem
    Dim openMacro As String
    
    ' Assign the macro string the VB equivalent of "ESC ESC _open "
    openMacro = Chr(3) & Chr(3) & Chr(95) & "open" & Chr(32)
    
    Set newButton = newToolBar.AddToolbarButton("", "NewButton", "Open a file.", openMacro)
    
    
    ' Display the toolbar
    newToolBar.Visible = True
    
End Sub
Sub Example_Dock()
    ' This example creates a new toolbar called and inserts three
    ' buttons into it. The toolbar is then displayed as a floating toolbar,
    ' and then as a docked toolbar.
    ' To remove the toolbar after execution of this macro, use the Customize Menu
    ' option from the Tools menu.
    
    Dim currMenuGroup As acadMenuGroup
    Set currMenuGroup = ThisDrawing.Application.MenuGroups.Item(0)
    
    ' Create the new toolbar
    Dim newToolBar As AcadToolbar
    Set newToolBar = currMenuGroup.Toolbars.Add("TestToolbar")
    
    ' Add three buttons to the new toolbar.
    ' All three buttons will have the same macro attached.
    Dim newButton1 As AcadToolbarItem
    Dim newButton2 As AcadToolbarItem
    Dim newButton3 As AcadToolbarItem
    Dim openMacro As String
    
    ' Assign the macro string the VB equivalent of "ESC ESC _open "
    openMacro = Chr(3) & Chr(3) & Chr(95) & "open" & Chr(32)
    
    Set newButton1 = newToolBar.AddToolbarButton("", "NewButton1", "Open a file.", openMacro)
    Set newButton2 = newToolBar.AddToolbarButton("", "NewButton2", "Open a file.", openMacro)
    Set newButton3 = newToolBar.AddToolbarButton("", "NewButton3", "Open a file.", openMacro)
    
    
    ' Display the toolbar
    newToolBar.Visible = True
    
    ' Dock the toolbar to the left of the screen.
    newToolBar.Dock acToolbarDockLeft
    MsgBox "The toolbar is docked to the left."
    
    ' Dock the toolbar to the right of the screen.
    newToolBar.Dock acToolbarDockRight
    MsgBox "The toolbar is docked to the right."
    
    ' Dock the toolbar at the top of the screen.
    newToolBar.Dock acToolbarDockTop
    MsgBox "The toolbar is docked at the top."
    
    ' Dock the toolbar at the bottom of the screen.
    newToolBar.Dock acToolbarDockBottom
    MsgBox "The toolbar is docked at the bottom."
    
End Sub
Sub Example_DockStatus()
    ' This example creates a new toolbar called and inserts three
    ' buttons into it. The toolbar is then displayed as a floating toolbar,
    ' and then as a docked toolbar.
    ' To remove the toolbar after execution of this macro, use the Customize Menu
    ' option from the Tools menu.
    
    Dim currMenuGroup As acadMenuGroup
    Set currMenuGroup = ThisDrawing.Application.MenuGroups.Item(0)
    
    ' Create the new toolbar
    Dim newToolBar As AcadToolbar
    Set newToolBar = currMenuGroup.Toolbars.Add("TestToolbar")
    
    ' Add three buttons to the new toolbar.
    ' All three buttons will have the same macro attached.
    Dim newButton1 As AcadToolbarItem
    Dim newButton2 As AcadToolbarItem
    Dim newButton3 As AcadToolbarItem
    Dim openMacro As String
    
    ' Assign the macro string the VB equivalent of "ESC ESC _open "
    openMacro = Chr(3) & Chr(3) & Chr(95) & "open" & Chr(32)
    
    Set newButton1 = newToolBar.AddToolbarButton("", "NewButton1", "Open a file.", openMacro)
    Set newButton2 = newToolBar.AddToolbarButton("", "NewButton2", "Open a file.", openMacro)
    Set newButton3 = newToolBar.AddToolbarButton("", "NewButton3", "Open a file.", openMacro)
    
    
    ' Display the toolbar
    newToolBar.Visible = True
    
    ' Dock the toolbar to the left of the screen.
    newToolBar.Dock acToolbarDockLeft
    GoSub QUERYSTATUS
    
    ' Float the toolbar
    newToolBar.Float 200, 200, 1
    GoSub QUERYSTATUS
    
    Exit Sub
    
QUERYSTATUS:
    ' Query the toolbar to see if it is docked.
    If newToolBar.DockStatus = acToolbarFloating Then
        MsgBox "The toolbar is floating."
    Else
        MsgBox "The toolbar is docked."
    End If
    Return
    
End Sub
Sub Example_Float()
    ' This example creates a new toolbar called and inserts three
    ' buttons into it. The toolbar is then displayed as a floating toolbar,
    ' and then as a docked toolbar.
    ' To remove the toolbar after execution of this macro, use the Customize Menu
    ' option from the Tools menu.
    
    Dim currMenuGroup As acadMenuGroup
    Set currMenuGroup = ThisDrawing.Application.MenuGroups.Item(0)
    
    ' Create the new toolbar
    Dim newToolBar As AcadToolbar
    Set newToolBar = currMenuGroup.Toolbars.Add("TestToolbar")
    
    ' Add three buttons to the new toolbar.
    ' All three buttons will have the same macro attached.
    Dim newButton1 As AcadToolbarItem
    Dim newButton2 As AcadToolbarItem
    Dim newButton3 As AcadToolbarItem
    Dim openMacro As String
    
    ' Assign the macro string the VB equivalent of "ESC ESC _open "
    openMacro = Chr(3) & Chr(3) & Chr(95) & "open" & Chr(32)
    
    Set newButton1 = newToolBar.AddToolbarButton("", "NewButton1", "Open a file.", openMacro)
    Set newButton2 = newToolBar.AddToolbarButton("", "NewButton2", "Open a file.", openMacro)
    Set newButton3 = newToolBar.AddToolbarButton("", "NewButton3", "Open a file.", openMacro)
    
    
    ' Display the toolbar
    newToolBar.Visible = True
    
    ' Dock the toolbar to the left of the screen.
    newToolBar.Dock acToolbarDockLeft
    GoSub QUERYSTATUS
    
    ' Float the toolbar
    newToolBar.Float 200, 200, 1
    GoSub QUERYSTATUS
    
    Exit Sub
    
QUERYSTATUS:
    ' Query the toolbar to see if it is docked.
    If newToolBar.DockStatus = acToolbarFloating Then
        MsgBox "The toolbar is floating."
    Else
        MsgBox "The toolbar is docked."
    End If
    Return
    
End Sub
Sub Example_FloatingRows()
    ' This example creates a new toolbar called and inserts three
    ' buttons into it. The toolbar is then displayed as a floating
    ' toolbar with 1 and then 3 rows.
    ' To remove the toolbar after execution of this macro, use the Customize Menu
    ' option from the Tools menu.
    
    Dim currMenuGroup As acadMenuGroup
    Set currMenuGroup = ThisDrawing.Application.MenuGroups.Item(0)
    
    ' Create the new toolbar
    Dim newToolBar As AcadToolbar
    Set newToolBar = currMenuGroup.Toolbars.Add("TestToolbar")
    
    ' Add three buttons to the new toolbar.
    ' All three buttons will have the same macro attached.
    Dim newButton1 As AcadToolbarItem
    Dim newButton2 As AcadToolbarItem
    Dim newButton3 As AcadToolbarItem
    Dim openMacro As String
    
    ' Assign the macro string the VB equivalent of "ESC ESC _open "
    openMacro = Chr(3) & Chr(3) & Chr(95) & "open" & Chr(32)
    
    Set newButton1 = newToolBar.AddToolbarButton("", "NewButton1", "Open a file.", openMacro)
    Set newButton2 = newToolBar.AddToolbarButton("", "NewButton2", "Open a file.", openMacro)
    Set newButton3 = newToolBar.AddToolbarButton("", "NewButton3", "Open a file.", openMacro)
    
    
    ' Display the toolbar
    newToolBar.Visible = True
    newToolBar.Float 200, 200, 1
    
    MsgBox "The toolbar has " & newToolBar.FloatingRows & " row."
    
    newToolBar.FloatingRows = 2
    MsgBox "The toolbar has " & newToolBar.FloatingRows & " rows."
    
    newToolBar.FloatingRows = 3
    MsgBox "The toolbar has " & newToolBar.FloatingRows & " rows."
    
End Sub
Sub Example_HelpString()
    ' This example creates a new toolbar called and inserts a
    ' button into it. The HelpString property of the toolbar is then
    ' read and changed.
    ' To remove the toolbar after execution of this macro, use the Customize Menu
    ' option from the Tools menu.
    
    Dim currMenuGroup As acadMenuGroup
    Set currMenuGroup = ThisDrawing.Application.MenuGroups.Item(0)
    
    ' Create the new toolbar
    Dim newToolBar As AcadToolbar
    Set newToolBar = currMenuGroup.Toolbars.Add("TestToolbar")
    
    ' Add a button to the new toolbar.
    Dim newButton1 As AcadToolbarItem
    Dim openMacro As String
    
    ' Assign the macro string the VB equivalent of "ESC ESC _open "
    openMacro = Chr(3) & Chr(3) & Chr(95) & "open" & Chr(32)
    
    Set newButton1 = newToolBar.AddToolbarButton("", "NewButton1", "Open a file.", openMacro)
    
    ' Display the toolbar
    newToolBar.Visible = True
    
    ' Read the current value of the help string
    MsgBox "The current HelpString for the toolbar button is: " & newButton1.HelpString
    
    ' Change the value of the help string
    newButton1.HelpString = "Use this toolbar button to Open a file."
    
    ' Read the new value of the help string
    MsgBox "The new HelpString for the toolbar button is: " & newButton1.HelpString
End Sub
Sub Example_SCMCommandMode()
    ' This example reads and modifies the SCMCommandMode
    ' preference value.
    ' When finished, this example resets the preference value back to
    ' it's original value.
    
    Dim ACADPref As AcadPreferencesUser
    Dim originalValue As Integer, newValue As Integer
    
    ' Get the user preferences object

    Set ACADPref = ThisDrawing.Application.preferences.User
    
    ' Read and display the original value
    originalValue = ACADPref.SCMCommandMode
    MsgBox "The SCMCommandMode preference is set to: " & originalValue

    ' Modify the SCMCommandMode preference by toggling the value
    ACADPref.SCMCommandMode = acEnter

    MsgBox "The SCMCommandMode preference has been set to: " & ACADPref.SCMCommandMode

    ' Reset the preference back to it's original value
    ACADPref.SCMCommandMode = originalValue
    MsgBox "The SCMCommandMode preference was reset back to: " & originalValue
End Sub
Sub Example_SCMDefaultMode()
    ' This example reads and modifies the SCMDefaultMode
    ' preference value.
    ' When finished, this example resets the preference value back to
    ' it's original value.
    
    Dim ACADPref As AcadPreferencesUser
    Dim originalValue As Integer, newValue As Integer
    
    ' Get the user preferences object

    Set ACADPref = ThisDrawing.Application.preferences.User
    
    ' Read and display the original value
    originalValue = ACADPref.SCMDefaultMode
    MsgBox "The SCMDefaultMode preference is set to: " & originalValue

    ' Modify the SCMDefaultMode preference by toggling the value
    ACADPref.SCMDefaultMode = acRepeatLastCommand

    MsgBox "The SCMDefaultMode preference has been set to: " & ACADPref.SCMDefaultMode

    ' Reset the preference back to it's original value
    ACADPref.SCMDefaultMode = originalValue
    MsgBox "The SCMDefaultMode preference was reset back to: " & originalValue
End Sub
Sub Example_SCMEditMode()
    ' This example reads and modifies the SCMEditMode
    ' preference value.
    ' When finished, this example resets the preference value back to
    ' it's original value.
    
    Dim ACADPref As AcadPreferencesUser
    Dim originalValue As Integer, newValue As Integer
    
    ' Get the user preferences object

    Set ACADPref = ThisDrawing.Application.preferences.User
    
    ' Read and display the original value
    originalValue = ACADPref.SCMEditMode
    MsgBox "The SCMEditMode preference is set to: " & originalValue

    ' Modify the SCMEditMode preference by toggling the value
    ACADPref.SCMEditMode = acEdRepeatLastCommand

    MsgBox "The SCMEditMode preference has been set to: " & ACADPref.SCMEditMode

    ' Reset the preference back to it's original value
    ACADPref.SCMEditMode = originalValue
    MsgBox "The SCMEditMode preference was reset back to: " & originalValue
End Sub
Sub Example_ScaleLineweights()
    ' This example reads and modifies the ScaleLineweights
    ' Layout value.
    ' When finished, this example resets the  value back to
    ' it's original value.
    
    Dim ACADLayout As ACADLayout
    Dim originalValue As Boolean
    
    ' Get the layout object
    Set ACADLayout = ThisDrawing.ActiveLayout
    
    ' Read and display the original value
    originalValue = ACADLayout.ScaleLineweights
    MsgBox "The ScaleLineweights value is set to: " & originalValue

    ' Modify the ScaleLineweights preference by toggling the value
    ACADLayout.ScaleLineweights = Not ACADLayout.ScaleLineweights
    MsgBox "The ScaleLineweights preference has been set to: " & ACADLayout.ScaleLineweights

    ' Reset the preference back to it's original value
    ACADLayout.ScaleLineweights = originalValue
    MsgBox "The ScaleLineweights preference was reset back to: " & originalValue
End Sub

Sub Example_PlotWithLineweights()
    ' This example reads and modifies the PlotWithLineweights
    ' Layout value.
    ' When finished, this example resets the  value back to
    ' it's original value.
    
    Dim ACADLayout As ACADLayout
    Dim originalValue As Boolean
    
    ' Get the layout object
    Set ACADLayout = ThisDrawing.ActiveLayout
    
    ' Read and display the original value
    originalValue = ACADLayout.PlotWithLineweights
    MsgBox "The PlotWithLineweights value is set to: " & originalValue

    ' Modify the PlotWithLineweights preference by toggling the value
    ACADLayout.PlotWithLineweights = Not ACADLayout.PlotWithLineweights
    MsgBox "The PlotWithLineweights preference has been set to: " & ACADLayout.PlotWithLineweights

    ' Reset the preference back to it's original value
    ACADLayout.PlotWithLineweights = originalValue
    MsgBox "The PlotWithLineweights preference was reset back to: " & originalValue
End Sub
Sub Example_PlotWithPlotStyles()
    ' This example reads and modifies the PlotWithPlotStyles
    ' Layout value.
    ' When finished, this example resets the  value back to
    ' it's original value.
    
    Dim ACADLayout As ACADLayout
    Dim originalValue As Boolean
    
    ' Get the layout object
    Set ACADLayout = ThisDrawing.ActiveLayout
    
    ' Read and display the original value
    originalValue = ACADLayout.PlotWithPlotStyles
    MsgBox "The PlotWithPlotStyles value is set to: " & originalValue

    ' Modify the PlotWithPlotStyles preference by toggling the value
    ACADLayout.PlotWithPlotStyles = Not ACADLayout.PlotWithPlotStyles
    MsgBox "The PlotWithPlotStyles preference has been set to: " & ACADLayout.PlotWithPlotStyles

    ' Reset the preference back to it's original value
    ACADLayout.PlotWithPlotStyles = originalValue
    MsgBox "The PlotWithPlotStyles preference was reset back to: " & originalValue
End Sub
Sub Example_PlotLegacy()
    ' This example reads and modifies the PlotLegacy
    ' preference value.
    ' When finished, this example resets the preference value back to
    ' it's original value.
    
    Dim ACADPref As AcadPreferencesOutput
    Dim originalValue As Boolean
    
    ' Get the user preferences object

    Set ACADPref = ThisDrawing.Application.preferences.Output
    
    ' Read and display the original value
    originalValue = ACADPref.PlotLegacy
    MsgBox "The PlotLegacy preference is set to: " & originalValue

    ' Modify the PlotLegacy preference by toggling the value
    ACADPref.PlotLegacy = Not ACADPref.PlotLegacy

    MsgBox "The PlotLegacy preference has been set to: " & ACADPref.PlotLegacy

    ' Reset the preference back to it's original value
    ACADPref.PlotLegacy = originalValue
    MsgBox "The PlotLegacy preference was reset back to: " & originalValue
End Sub
Sub Example_PrinterPaperSizeAlert()
    ' This example reads and modifies the PrinterPaperSizeAlert
    ' preference value.
    ' When finished, this example resets the preference value back to
    ' it's original value.
    
    Dim ACADPref As AcadPreferencesOutput
    Dim originalValue As Boolean
    
    ' Get the user preferences object

    Set ACADPref = ThisDrawing.Application.preferences.Output
    
    ' Read and display the original value
    originalValue = ACADPref.PrinterPaperSizeAlert
    MsgBox "The PrinterPaperSizeAlert preference is set to: " & originalValue

    ' Modify the PrinterPaperSizeAlert preference by toggling the value
    ACADPref.PrinterPaperSizeAlert = Not ACADPref.PrinterPaperSizeAlert

    MsgBox "The PrinterPaperSizeAlert preference has been set to: " & ACADPref.PrinterPaperSizeAlert

    ' Reset the preference back to it's original value
    ACADPref.PrinterPaperSizeAlert = originalValue
    MsgBox "The PrinterPaperSizeAlert preference was reset back to: " & originalValue
End Sub
Sub Example_PrinterSpoolAlert()
    ' This example reads and modifies the PrinterSpoolAlert
    ' preference value.
    ' When finished, this example resets the preference value back to
    ' it's original value.
    
    Dim ACADPref As AcadPreferencesOutput
    Dim originalValue As Integer
    
    ' Get the user preferences object

    Set ACADPref = ThisDrawing.Application.preferences.Output
    
    ' Read and display the original value
    originalValue = ACADPref.PrinterSpoolAlert
    MsgBox "The PrinterSpoolAlert preference is set to: " & originalValue

    ' Modify the PrinterSpoolAlert preference by toggling the value
    ACADPref.PrinterSpoolAlert = acPrinterNeverAlert
    MsgBox "The PrinterSpoolAlert preference has been set to: " & ACADPref.PrinterSpoolAlert

    ' Reset the preference back to it's original value
    ACADPref.PrinterSpoolAlert = originalValue
    MsgBox "The PrinterSpoolAlert preference was reset back to: " & originalValue
End Sub
Sub Example_PlotPolicy()
    ' This example reads and modifies the PlotPolicy
    ' preference value.
    ' When finished, this example resets the preference value back to
    ' it's original value.
    
    Dim ACADPref As AcadPreferencesOutput
    Dim originalValue As Integer
    
    ' Get the user preferences object

    Set ACADPref = ThisDrawing.Application.preferences.Output
    
    ' Read and display the original value
    originalValue = ACADPref.PlotPolicy
    MsgBox "The PlotPolicy preference is set to: " & originalValue

    ' Modify the PlotPolicy preference by toggling the value
    ACADPref.PlotPolicy = acPolicyNamed
    MsgBox "The PlotPolicy preference has been set to: " & ACADPref.PlotPolicy

    ' Reset the preference back to it's original value
    ACADPref.PlotPolicy = originalValue
    MsgBox "The PlotPolicy preference was reset back to: " & originalValue
End Sub
Sub Example_UseLastPlotSettings()
    ' This example reads and modifies the UseLastPlotSettings
    ' preference value.
    ' When finished, this example resets the preference value back to
    ' it's original value.
    
    Dim ACADPref As AcadPreferencesOutput
    Dim originalValue As Boolean
    
    ' Get the user preferences object

    Set ACADPref = ThisDrawing.Application.preferences.Output
    
    ' Read and display the original value
    originalValue = ACADPref.UseLastPlotSettings
    MsgBox "The UseLastPlotSettings preference is set to: " & originalValue

    ' Modify the UseLastPlotSettings preference by toggling the value
    ACADPref.UseLastPlotSettings = Not ACADPref.UseLastPlotSettings

    MsgBox "The UseLastPlotSettings preference has been set to: " & ACADPref.UseLastPlotSettings

    ' Reset the preference back to it's original value
    ACADPref.UseLastPlotSettings = originalValue
    MsgBox "The UseLastPlotSettings preference was reset back to: " & originalValue
End Sub
Sub Example_PlotViewportBorders()
    ' This example reads and modifies the PlotViewportBorders
    ' Layout value.
    ' When finished, this example resets the  value back to
    ' it's original value.
    
    Dim ACADLayout As ACADLayout
    Dim originalValue As Boolean
    
    ' Get the layout object
    Set ACADLayout = ThisDrawing.ActiveLayout
    
    ' Read and display the original value
    originalValue = ACADLayout.PlotViewportBorders
    MsgBox "The PlotViewportBorders value is set to: " & originalValue

    ' Modify the PlotViewportBorders preference by toggling the value
    ACADLayout.PlotViewportBorders = Not ACADLayout.PlotViewportBorders
    MsgBox "The PlotViewportBorders preference has been set to: " & ACADLayout.PlotViewportBorders

    ' Reset the preference back to it's original value
    ACADLayout.PlotViewportBorders = originalValue
    MsgBox "The PlotViewportBorders preference was reset back to: " & originalValue
End Sub
Sub Example_PlotViewportsFirst()
    ' This example reads and modifies the PlotViewportsFirst
    ' Layout value.
    ' When finished, this example resets the  value back to
    ' it's original value.
    
    Dim ACADLayout As ACADLayout
    Dim originalValue As Boolean
    
    ' Get the layout object
    Set ACADLayout = ThisDrawing.ActiveLayout
    
    ' Read and display the original value
    originalValue = ACADLayout.PlotViewportsFirst
    MsgBox "The PlotViewportsFirst value is set to: " & originalValue

    ' Modify the PlotViewportsFirst preference by toggling the value
    ACADLayout.PlotViewportsFirst = Not ACADLayout.PlotViewportsFirst
    MsgBox "The PlotViewportsFirst preference has been set to: " & ACADLayout.PlotViewportsFirst

    ' Reset the preference back to it's original value
    ACADLayout.PlotViewportsFirst = originalValue
    MsgBox "The PlotViewportsFirst preference was reset back to: " & originalValue
End Sub
Sub Example_Backward()
   ' This example creates a text object in model space and
   ' uses the Backward property to flip the text horizontally
   
    Dim textObj As AcadText
    Dim textString As String
    Dim insertionPoint(0 To 2) As Double
    Dim height As Double
    
    ' Define the new Text object
    textString = "Hello, World."
    insertionPoint(0) = 3: insertionPoint(1) = 3: insertionPoint(2) = 0
    height = 0.5
    
    ' Create the Text object in model space
    Set textObj = ThisDrawing.ModelSpace.AddText(textString, insertionPoint, height)
    
    ThisDrawing.Application.ZoomAll
    
    MsgBox "The Text oject is now forward"
    
    textObj.Backward = True
    ThisDrawing.Regen acActiveViewport
    
    MsgBox "The Text object is now backward"
End Sub
Sub Example_PlotOrigin()
    ' This example reads and modifies the PlotOrigin
    ' Layout value.
    ' When finished, this example resets the  value back to
    ' it's original value.
    
    Dim ACADLayout As ACADLayout
    Dim originalValue As Variant
    Dim newValue(0 To 1) As Double
    
    ' Get the layout object
    Set ACADLayout = ThisDrawing.ActiveLayout
    
    ' Read and display the original value
    originalValue = ACADLayout.PlotOrigin
    MsgBox "The PlotOrigin value is set to: " & originalValue(0) & " ," & originalValue(1)

    ' Modify the PlotOrigin preference by toggling the value
    newValue(0) = originalValue(0) + 20
    newValue(1) = originalValue(1) - 20
    ACADLayout.PlotOrigin = newValue
    MsgBox "The PlotOrigin value is set to: " & newValue(0) & " ," & newValue(1)

    ' Reset the preference back to it's original value
    ACADLayout.PlotOrigin = originalValue
    MsgBox "The PlotOrigin value is set to: " & originalValue(0) & " ," & originalValue(1)
End Sub
Sub Example_PlotRotation()
    ' This example reads and modifies the PlotRotation
    ' Layout value.
    ' When finished, this example resets the  value back to
    ' it's original value.
    
    Dim ACADLayout As ACADLayout
    Dim originalValue As Integer
    
    ' Get the layout object
    Set ACADLayout = ThisDrawing.ActiveLayout
    
    ' Read and display the original value
    originalValue = ACADLayout.PlotRotation
    MsgBox "The PlotRotation value is set to: " & originalValue

    ' Modify the PlotRotation preference by toggling the value
    ACADLayout.PlotRotation = ac180degrees
    MsgBox "The PlotRotation preference has been set to: " & ACADLayout.PlotRotation

    ' Reset the preference back to it's original value
    ACADLayout.PlotRotation = originalValue
    MsgBox "The PlotRotation preference was reset back to: " & originalValue
End Sub
Sub Example_ShowPlotStyles()
    ' This example reads and modifies the ShowPlotStyles
    ' Layout value.
    ' When finished, this example resets the  value back to
    ' it's original value.
    
    Dim ACADLayout As ACADLayout
    Dim originalValue As Boolean
    
    ' Get the layout object
    Set ACADLayout = ThisDrawing.ActiveLayout
    
    ' Read and display the original value
    originalValue = ACADLayout.ShowPlotStyles
    MsgBox "The ShowPlotStyles value is set to: " & originalValue

    ' Modify the ShowPlotStyles preference by toggling the value
    ACADLayout.ShowPlotStyles = Not ACADLayout.ShowPlotStyles
    MsgBox "The ShowPlotStyles value has been set to: " & ACADLayout.ShowPlotStyles

    ' Reset the preference back to it's original value
    ACADLayout.ShowPlotStyles = originalValue
    MsgBox "The ShowPlotStyles value was reset back to: " & originalValue
End Sub
Sub Example_PlotType()
    ' This example reads and modifies the PlotType
    ' Layout value.
    ' When finished, this example resets the  value back to
    ' it's original value.
    
    Dim ACADLayout As ACADLayout
    Dim originalValue As Integer
    
    ' Get the layout object
    Set ACADLayout = ThisDrawing.ActiveLayout
    
    ' Read and display the original value
    originalValue = ACADLayout.PlotType
    MsgBox "The PlotType value is set to: " & originalValue

    ' Modify the PlotType preference by toggling the value
    ACADLayout.PlotType = acExtents
    MsgBox "The PlotType preference has been set to: " & ACADLayout.PlotType

    ' Reset the preference back to it's original value
    ACADLayout.PlotType = originalValue
    MsgBox "The PlotType preference was reset back to: " & originalValue
End Sub
Sub Example_OwnerID()
    ' This example creates an MText object in model space
    ' and then finds the OwnerID for the object.
    
    Dim MTextObj As AcadMText
    Dim corner(0 To 2) As Double
    Dim width As Double
    Dim text As String
    corner(0) = 0#: corner(1) = 10#: corner(2) = 0#
    width = 10
    text = "This is the text String for the mtext Object"

    ' Creates the mtext Object
    Set MTextObj = ThisDrawing.ModelSpace.AddMText(corner, width, text)
    ZoomAll
    
    MsgBox "The OwnerID for the MText object is: " & MTextObj.OwnerID
    
End Sub
Sub Example_LineSpacingFactor()
    ' This example creates an MText object in model space
    ' and then finds the LineSpacingFactor for the object.
    
    Dim MTextObj As AcadMText
    Dim corner(0 To 2) As Double
    Dim width As Double
    Dim text As String
    corner(0) = 0#: corner(1) = 10#: corner(2) = 0#
    width = 10
    text = "This is the text String for the mtext Object"

    ' Creates the mtext Object
    Set MTextObj = ThisDrawing.ModelSpace.AddMText(corner, width, text)
    ZoomAll
    
    ' Find the current LineSpacingFactor
    Dim currFactor As Double
    currFactor = MTextObj.LineSpacingFactor
    MsgBox "The LineSpacingFactor for the MText object is: " & currFactor
    
    ' Change the LineSpacingFactor
    MTextObj.LineSpacingFactor = 4
    MsgBox "The LineSpacingFactor for the MText object is: " & MTextObj.LineSpacingFactor
    
    ' Reset the LineSpacingFactor
    MTextObj.LineSpacingFactor = currFactor
    MsgBox "The LineSpacingFactor for the MText object is: " & MTextObj.LineSpacingFactor
    
End Sub
Sub Example_LineSpacingStyle()
    ' This example creates an MText object in model space
    ' and then finds the LineSpacingStyle for the object.
    
    Dim MTextObj As AcadMText
    Dim corner(0 To 2) As Double
    Dim width As Double
    Dim text As String
    corner(0) = 0#: corner(1) = 10#: corner(2) = 0#
    width = 10
    text = "This is the text String for the mtext Object"

    ' Creates the mtext Object
    Set MTextObj = ThisDrawing.ModelSpace.AddMText(corner, width, text)
    ZoomAll
    
    ' Find the current LineSpacingStyle
    Dim currStyle As Integer
    currStyle = MTextObj.LineSpacingStyle
    MsgBox "The LineSpacingStyle for the MText object is: " & currStyle
    
    ' Change the LineSpacingStyle
    MTextObj.LineSpacingStyle = acLineSpacingStyleExactly
    MsgBox "The LineSpacingStyle for the MText object is: " & MTextObj.LineSpacingStyle
    
    ' Reset the LineSpacingStyle
    MTextObj.LineSpacingStyle = currStyle
    MsgBox "The LineSpacingStyle for the MText object is: " & MTextObj.LineSpacingStyle
    
End Sub
Sub Example_LineWeight()
    ' This example creates a circle in model space and then
    ' finds the current lineweight for the circle. The lineweight
    ' is then changed to a new value.
   
    Dim circleObj As AcadCircle
    Dim centerPoint(0 To 2) As Double
    Dim radius As Double
    
    ' Define the circle
    centerPoint(0) = 0#: centerPoint(1) = 0#: centerPoint(2) = 0#
    radius = 5#
    
    ' Create the Circle object in model space
    Set circleObj = ThisDrawing.ModelSpace.AddCircle(centerPoint, radius)
    ZoomAll
    
    ' Find the lineweight for the circle
    MsgBox "The current lineweight for the circle is " & circleObj.Lineweight
    
    ' Change the lineweight for the circle
    circleObj.Lineweight = acLnWt211
    circleObj.Update
    MsgBox "The current lineweight for the circle is " & circleObj.Lineweight
End Sub
Sub Example_LineweightDisplay()
    ' This example reads and modifies the preference value which controls
    ' whether symbol names may include extended character sets, or more
    ' than 31 characters.
    '
    ' When finished, this example resets the preference value back to
    ' it's original value.
    
    Dim ACADPref As AcadDatabasePreferences
    Dim originalValue As Variant, newValue As Variant
    
    ' Get the user preferences object
    Set ACADPref = ThisDrawing.preferences
    
    ' Read and display the original value
    originalValue = ACADPref.LineWeightDisplay
    MsgBox "The LineweightDisplay preference is set to: " & originalValue

    ' Modify the LineweightDisplay preference by toggling the value
    ACADPref.LineWeightDisplay = Not (ACADPref.LineWeightDisplay)
    newValue = ACADPref.LineWeightDisplay
    MsgBox "The LineweightDisplay preference has been set to: " & newValue

    ' Reset the preference back to it's original value
    '
    ' * Note: Comment out this last section to leave the change to
    '         this preference in effect
    ACADPref.LineWeightDisplay = originalValue
    MsgBox "The LineweightDisplay preference was reset back to: " & originalValue
End Sub
Sub Example_ModelType()
    ' This example creates a plotconfiguration object
    ' and then finds the ModelType for the object.
    
    Dim PlotConfigObj As AcadPlotConfiguration

    ' Creates the mtext Object
    Set PlotConfigObj = ThisDrawing.PlotConfigurations.Add("NewPlotConfiguration")
    
    ' Find the current ModelType
    Dim currModelType As Boolean
    currModelType = PlotConfigObj.ModelType
    MsgBox "The ModelType for the object is: " & currModelType
    
End Sub
Sub Example_LoadAcadLspInAllDocuments()
    ' This example returns the current setting of
    ' LoadAcadLspInAllDocuments. It then changes the value, and finally
    ' it resets the value back to the original setting.
    
    Dim preferences As AcadPreferences
    Dim currLoadAcadLspInAllDocuments As Boolean
    
    Set preferences = ThisDrawing.Application.preferences
    
    ' Retrieve the current LoadAcadLspInAllDocuments value
    currLoadAcadLspInAllDocuments = preferences.System.LoadAcadLspInAllDocuments
    MsgBox "The current value for LoadAcadLspInAllDocuments is " & preferences.System.LoadAcadLspInAllDocuments, vbInformation, "LoadAcadLspInAllDocuments Example"
    
    ' Change the value for LoadAcadLspInAllDocuments
    preferences.System.LoadAcadLspInAllDocuments = Not (currLoadAcadLspInAllDocuments)
    MsgBox "The new value for LoadAcadLspInAllDocuments is " & preferences.System.LoadAcadLspInAllDocuments, vbInformation, "LoadAcadLspInAllDocuments Example"
    
    ' Reset LoadAcadLspInAllDocuments to its original value
    preferences.System.LoadAcadLspInAllDocuments = currLoadAcadLspInAllDocuments
    MsgBox "The LoadAcadLspInAllDocuments value is reset to " & preferences.System.LoadAcadLspInAllDocuments, vbInformation, "LoadAcadLspInAllDocuments Example"
End Sub
Sub Example_PlotStyleName()
    ' This example creates a circle in model space and then
    ' finds the current PlotStyleName for the circle.
   
    Dim circleObj As AcadCircle
    Dim centerPoint(0 To 2) As Double
    Dim radius As Double
    
    ' Define the circle
    centerPoint(0) = 0#: centerPoint(1) = 0#: centerPoint(2) = 0#
    radius = 5#
    
    ' Create the Circle object in model space
    Set circleObj = ThisDrawing.ModelSpace.AddCircle(centerPoint, radius)
    ZoomAll
    
    ' Find the PlotStyleName for the circle
    MsgBox "The current PlotStyleName for the circle is " & circleObj.PlotStyleName
        
End Sub
Sub Example_Document()
    ' This example creates a circle in model space and then
    ' finds the name of the document that the circle resides in.
   
    Dim circleObj As AcadCircle
    Dim centerPoint(0 To 2) As Double
    Dim radius As Double
    
    ' Define the circle
    centerPoint(0) = 0#: centerPoint(1) = 0#: centerPoint(2) = 0#
    radius = 5#
    
    ' Create the Circle object in model space
    Set circleObj = ThisDrawing.ModelSpace.AddCircle(centerPoint, radius)
    ZoomAll
    
    ' Find the document name for the circle
    Dim currDoc As AcadDocument
    Set currDoc = circleObj.Document
    
    MsgBox "The circle resides in: " & currDoc.name
        
End Sub
Sub Example_Index()
    ' This example iterates through the first menu in the menu bar
    ' and displays the index for each menu item.
    
    Dim menuItem As AcadPopupMenuItem
    Dim menuIndex As String
    menuIndex = ""
    
    For Each menuItem In ThisDrawing.Application.MenuBar.Item(0)
        menuIndex = menuIndex & menuItem.TagString & " has the index: " & menuItem.index & vbCrLf
    Next menuItem
    MsgBox menuIndex
    
End Sub
Sub Example_Label()
    ' This example iterates through the first menu in the menu bar
    ' and displays the label for each menu item.
    
    Dim menuItem As AcadPopupMenuItem
    Dim menuLabel As String
    menuLabel = ""
    
    For Each menuItem In ThisDrawing.Application.MenuBar.Item(0)
        menuLabel = menuLabel & menuItem.Label & vbCrLf
    Next menuItem
    MsgBox menuLabel
    
End Sub
Sub Example_Invisible()
    ' This example creates an attribute definition in model space.
    ' It then queries the visibility of the attribute, changes
    ' the visibility, and queries the visibility again.
    
    Dim attributeObj As AcadAttribute
    Dim height As Double
    Dim mode As Long
    Dim prompt As String
    Dim insertionPoint(0 To 2) As Double
    Dim tag As String
    Dim value As String
    
    ' Define the attribute definition
    height = 1#
    mode = acAttributeModeVerify
    prompt = "New Prompt"
    insertionPoint(0) = 5#: insertionPoint(1) = 5#: insertionPoint(2) = 0
    tag = "New Tag"
    value = "New Value"
    
    ' Create the attribute definition object in model space
    Set attributeObj = ThisDrawing.ModelSpace.AddAttribute(height, mode, prompt, insertionPoint, tag, value)
    ZoomAll
    
    ' Find the current visibility for the attribute
    GoSub QUERYSTATUS
        
    ' Change the visibility of the attribute
    attributeObj.Invisible = Not attributeObj.Invisible
    ZoomAll
    
    GoSub QUERYSTATUS
    
    Exit Sub
    
QUERYSTATUS:
    If attributeObj.Invisible Then
        MsgBox "The attribute is invisible."
    Else
        MsgBox "The attribute is visible."
    End If
    Return
End Sub
Sub Example_Block()
    ' This example finds the name of the block associated with a layout.
    
    Dim xBlock As AcadBlock
    Set xBlock = ThisDrawing.ActiveLayout.Block
    
    MsgBox "The active layout corresponds to block: " & xBlock.name
End Sub
Sub Example_Parent()
    ' This example creates a new toolbar and then finds the parent toolbar.
    ' To remove the toolbar after execution of this macro, use the Customize Menu
    ' option from the Tools menu.
    
    Dim currMenuGroup As acadMenuGroup
    Set currMenuGroup = ThisDrawing.Application.MenuGroups.Item(0)
    
    ' Create the new toolbar
    Dim newToolBar As AcadToolbar
    Set newToolBar = currMenuGroup.Toolbars.Add("MyTools")
    
    ' Add a button to the new toolbar.
    ' All three buttons will have the same macro attached.
    Dim newButton1 As AcadToolbarItem
    Dim openMacro As String
    
    ' Assign the macro string the VB equivalent of "ESC ESC _open "
    openMacro = Chr(3) & Chr(3) & Chr(95) & "open" & Chr(32)
    
    Set newButton1 = newToolBar.AddToolbarButton("", "OpenFile", "Open a file.", openMacro)
    
    ' Display the toolbar
    newToolBar.Visible = True
    
    ' Find the parent toolbar for the toolbar button
    MsgBox "The " & newButton1.name & " button is on the " & newButton1.Parent.name & " toolbar."
End Sub
Sub Example_GetFont()
    ' This example find the font information for the active text style.
    
    Dim typeFace As String
    Dim Bold As Boolean
    Dim Italic As Boolean
    Dim charSet As Long
    Dim PitchandFamily As Long
    
    ThisDrawing.ActiveTextStyle.GetFont typeFace, Bold, Italic, charSet, PitchandFamily
    
    MsgBox "The current text style has the following font properties:" & vbCrLf _
            & "Typeface: " & typeFace & vbCrLf _
            & "Bold: " & Bold & vbCrLf _
            & "Italic: " & Italic & vbCrLf _
            & "Character set: " & charSet & vbCrLf _
            & "Pitch and Family: " & PitchandFamily
    
End Sub
Sub Example_SetFont()
    ' This example find the font information for the active text style.
    ' It then changes the font to bold.
    
    Dim typeFace As String
    Dim Bold As Boolean
    Dim Italic As Boolean
    Dim charSet As Long
    Dim PitchandFamily As Long
    
    ThisDrawing.ActiveTextStyle.GetFont typeFace, Bold, Italic, charSet, PitchandFamily
    
    MsgBox "The current text style has the following font properties:" & vbCrLf _
            & "Typeface: " & typeFace & vbCrLf _
            & "Bold: " & Bold & vbCrLf _
            & "Italic: " & Italic & vbCrLf _
            & "Character set: " & charSet & vbCrLf _
            & "Pitch and Family: " & PitchandFamily
            
    ' Change the bold property
    Bold = Not Bold
    
    ThisDrawing.ActiveTextStyle.SetFont typeFace, Bold, Italic, charSet, PitchandFamily
    MsgBox "The current text style has the following font properties:" & vbCrLf _
            & "Typeface: " & typeFace & vbCrLf _
            & "Bold: " & Bold & vbCrLf _
            & "Italic: " & Italic & vbCrLf _
            & "Character set: " & charSet & vbCrLf _
            & "Pitch and Family: " & PitchandFamily
            
    ' Reset the font
    Bold = Not Bold
    ThisDrawing.ActiveTextStyle.SetFont typeFace, Bold, Italic, charSet, PitchandFamily

End Sub
Sub Example_Constant()
    ' This example creates an attribute definition in model space.
    ' It then queries the attribute to see if it is a constant attribute.
    
    Dim attributeObj As AcadAttribute
    Dim height As Double
    Dim mode As Long
    Dim prompt As String
    Dim insertionPoint(0 To 2) As Double
    Dim tag As String
    Dim value As String
    
    ' Define the attribute definition
    height = 1#
    mode = acAttributeModeVerify
    prompt = "New Prompt"
    insertionPoint(0) = 5#: insertionPoint(1) = 5#: insertionPoint(2) = 0
    tag = "New Tag"
    value = "New Value"
    
    ' Create the attribute definition object in model space
    Set attributeObj = ThisDrawing.ModelSpace.AddAttribute(height, mode, prompt, insertionPoint, tag, value)
    ZoomAll
            
    ' Query the attribute
    GoSub QUERYSTATUS
    
    ' Change the attribute
    attributeObj.constant = Not attributeObj.constant
    GoSub QUERYSTATUS
    
    Exit Sub
    
QUERYSTATUS:
    If attributeObj.constant Then
        MsgBox "The attribute is a constant attribute."
    Else
        MsgBox "The attribute is not a constant attribute."
    End If
    Return
End Sub
Sub Example_LinetypeGeneration()
    ' This example creates a polyline in model space and
    ' queries and changes the linetype generation for
    ' the polyline.
    
    ' To see the effect of changing the linetype generation, set
    ' the linetype of the polyline to something other than continuous,
    ' ByBlock, or ByLayer.
    
    Dim plineObj As AcadPolyline
    Dim points(0 To 14) As Double
    
    ' Define the 2D polyline points
    points(0) = 1: points(1) = 1: points(2) = 0
    points(3) = 1: points(4) = 2: points(5) = 0
    points(6) = 2: points(7) = 2: points(8) = 0
    points(9) = 3: points(10) = 2: points(11) = 0
    points(12) = 4: points(13) = 4: points(14) = 0
        
    ' Create a light weight Polyline object in model space
    Set plineObj = ThisDrawing.ModelSpace.AddPolyline(points)
    ZoomAll
    
    ' Find the current linetype generation for the polyline
    MsgBox "The linetype generation for the polyline is: " & plineObj.LinetypeGeneration
    
    ' Change the linetype generation
    plineObj.LinetypeGeneration = Not plineObj.LinetypeGeneration
    plineObj.Update
    MsgBox "The linetype generation for the polyline is now: " & plineObj.LinetypeGeneration
    
End Sub
Sub Example_Coordinate()
    ' This example creates a polyline in model space and
    ' queries and changes the coordinate in the first index position.
        
    Dim plineObj As AcadPolyline
    Dim points(0 To 14) As Double
    
    ' Define the 2D polyline points
    points(0) = 1: points(1) = 1: points(2) = 0
    points(3) = 1: points(4) = 2: points(5) = 0
    points(6) = 2: points(7) = 2: points(8) = 0
    points(9) = 3: points(10) = 2: points(11) = 0
    points(12) = 4: points(13) = 4: points(14) = 0
        
    ' Create a light weight Polyline object in model space
    Set plineObj = ThisDrawing.ModelSpace.AddPolyline(points)
    ZoomAll
    
    ' Find the coordinate in the first index position
    Dim coord As Variant
    coord = plineObj.Coordinate(0)
    MsgBox "The coordinate in the first index position of the polyline is: " & coord(0) & ", " _
        & coord(1) & ", " & coord(2)
    
    ' Change the coordinate
    coord(0) = coord(0) + 1
    plineObj.Coordinate(0) = coord
    plineObj.Update
    
    ' Query the new coordinate
    coord = plineObj.Coordinate(0)
    MsgBox "The coordinate in the first index position of the polyline is now: " & coord(0) & ", " _
        & coord(1) & ", " & coord(2)
    
End Sub
Sub Example_CenterType()
    ' This example creates a diametric dimension in model space.
    ' It then changes the type of center for the dimension.
    
    Dim dimObj As AcadDimDiametric
    Dim chordPoint(0 To 2) As Double
    Dim farChordPoint(0 To 2) As Double
    Dim leaderLength As Double
    
    ' Define the dimension
    chordPoint(0) = 5#: chordPoint(1) = 3#: chordPoint(2) = 0#
    farChordPoint(0) = 5#: farChordPoint(1) = 5#: farChordPoint(2) = 0#
    leaderLength = 1#
    
    ' Create the diametric dimension in model space
    Set dimObj = ThisDrawing.ModelSpace.AddDimDiametric(chordPoint, farChordPoint, leaderLength)
    ZoomAll
    
    ' Set the center to be none
    dimObj.CenterType = acCenterNone
    dimObj.Update
    MsgBox "The dimension center type is set to none."
    
    ' Change the center type to center mark
    dimObj.CenterType = acCenterMark
    dimObj.Update
    MsgBox "The dimension center type is set to center mark."
    
    ' Change the center type to center line
    dimObj.CenterType = acCenterLine
    dimObj.Update
    MsgBox "The dimension center type is set to center line."
End Sub
Sub Example_CenterMarkSize()
    ' This example creates a diametric dimension in model space.
    ' It then changes the type of center for the dimension to
    ' center mark, and adjust the size of the center mark.
    
    Dim dimObj As AcadDimDiametric
    Dim chordPoint(0 To 2) As Double
    Dim farChordPoint(0 To 2) As Double
    Dim leaderLength As Double
    
    ' Define the dimension
    chordPoint(0) = 5#: chordPoint(1) = 3#: chordPoint(2) = 0#
    farChordPoint(0) = 5#: farChordPoint(1) = 5#: farChordPoint(2) = 0#
    leaderLength = 1#
    
    ' Create the diametric dimension in model space
    Set dimObj = ThisDrawing.ModelSpace.AddDimDiametric(chordPoint, farChordPoint, leaderLength)
    ZoomAll
        
    ' Change the center type to center mark and set the size of the center mark
    dimObj.CenterType = acCenterMark
    dimObj.CenterMarkSize = 0.1
    dimObj.Update
    MsgBox "The center mark size is: " & dimObj.CenterMarkSize
    
    dimObj.CenterMarkSize = dimObj.CenterMarkSize * 2
    dimObj.Update
    MsgBox "The center mark size is: " & dimObj.CenterMarkSize
End Sub
Sub Example_StyleSheet()
    ' This example finds the name of the style sheet for the active layout
    
    Dim styleSheetName As String
    styleSheetName = ThisDrawing.ActiveLayout.StyleSheet
    
    If styleSheetName = "" Then
        MsgBox "There is no style sheet set for the active layout."
    Else
        MsgBox "The style sheet for the active layout is: " & styleSheetName
    End If
End Sub
Sub Example_CanonicalMediaName()
    ' This example finds the name of the media for the active layout
    
    Dim MediaName As String
    MediaName = ThisDrawing.ActiveLayout.CanonicalMediaName
    
    If MediaName = "" Then
        MsgBox "There is no media set for the active layout."
    Else
        MsgBox "The media for the active layout is: " & MediaName
    End If
End Sub

Sub Example_Bind()
    On Error GoTo ERRORHANDLER
                          
    ' Define external reference to be inserted
    Dim xrefHome As AcadBlock
    Dim xrefInserted As AcadExternalReference
    Dim insertionPnt(0 To 2) As Double
    Dim PathName As String
    insertionPnt(0) = 1
    insertionPnt(1) = 1
    insertionPnt(2) = 0
    PathName = "c:/AutoCAD/sample/City map.dwg"
    
    ' Add the external reference
    Set xrefInserted = ThisDrawing.ModelSpace. _
            AttachExternalReference(PathName, "XREF_IMAGE", _
            insertionPnt, 1, 1, 1, 0, False)
    ZoomAll
    MsgBox "The external reference is attached."
    
    ' Bind the external reference definition
    ThisDrawing.Blocks.Item(xrefInserted.name).Bind False
    MsgBox "The external reference is bound."
    Exit Sub
ERRORHANDLER:
    MsgBox Err.Description
End Sub

Sub Example_Detach()
    On Error GoTo ERRORHANDLER
                          
    ' Define external reference to be inserted
    Dim xrefHome As AcadBlock
    Dim xrefInserted As AcadExternalReference
    Dim insertionPnt(0 To 2) As Double
    Dim PathName As String
    insertionPnt(0) = 1
    insertionPnt(1) = 1
    insertionPnt(2) = 0
    PathName = "c:/AutoCAD/sample/City map.dwg"
    
    ' Add the external reference
    Set xrefInserted = ThisDrawing.ModelSpace. _
            AttachExternalReference(PathName, "XREF_IMAGE", _
            insertionPnt, 1, 1, 1, 0, False)
    ZoomAll
    MsgBox "The external reference is attached."
    
    ' Detach the external reference definition
    Dim name As String
    name = xrefInserted.name
    ThisDrawing.Blocks.Item(name).Detach
    MsgBox "The external reference is detached."
    Exit Sub
ERRORHANDLER:
    MsgBox Err.Description
End Sub
Sub Example_Reload()
    On Error GoTo ERRORHANDLER
                          
    ' Define external reference to be inserted
    Dim xrefHome As AcadBlock
    Dim xrefInserted As AcadExternalReference
    Dim insertionPnt(0 To 2) As Double
    Dim PathName As String
    insertionPnt(0) = 1
    insertionPnt(1) = 1
    insertionPnt(2) = 0
    PathName = "c:/AutoCAD/sample/City map.dwg"
    
    ' Add the external reference to the block
    Set xrefInserted = ThisDrawing.ModelSpace. _
            AttachExternalReference(PathName, "XREF_IMAGE", _
            insertionPnt, 1, 1, 1, 0, False)
    ZoomAll
    MsgBox "The external reference is attached."
    
    ' Reload the external reference definition
    ThisDrawing.Blocks.Item(xrefInserted.name).Reload
    MsgBox "The external reference is reloaded."
    Exit Sub
ERRORHANDLER:
    MsgBox Err.Description
End Sub
Sub Example_Unload()
    On Error GoTo ERRORHANDLER
                          
    ' Define external reference to be inserted
    Dim xrefHome As AcadBlock
    Dim xrefInserted As AcadExternalReference
    Dim insertionPnt(0 To 2) As Double
    Dim PathName As String
    insertionPnt(0) = 1
    insertionPnt(1) = 1
    insertionPnt(2) = 0
    PathName = "c:/AutoCAD/sample/City map.dwg"
    
    ' Add the external reference
    Set xrefInserted = ThisDrawing.ModelSpace. _
            AttachExternalReference(PathName, "XREF_IMAGE", _
            insertionPnt, 1, 1, 1, 0, False)
    ZoomAll
    MsgBox "The external reference is attached."
    
    ' Unload the external reference definition
    ThisDrawing.Blocks.Item(xrefInserted.name).Unload
    MsgBox "The external reference is unloaded."
    Exit Sub
ERRORHANDLER:
    MsgBox Err.Description
End Sub
Sub Example_SetLayoutsToPlot()
    ' This example creates a Circle in model space and allows the user
    ' to select which layouts for the drawing to plot.  It then uses
    ' a batch operation to send the selected layouts to the current
    ' plot device and allows the user to cancel the batch plot at certain
    ' intervals.

    Dim Plot As AcadPlot
    Dim AddedLayouts() As String
    Dim LayoutList As Variant
    Dim circleObj As AcadCircle
    Dim centerPoint(0 To 2) As Double
    Dim radius As Double
    Dim Layout As ACADLayout
    Dim ArraySize As Integer, BatchCount As Integer
    
    ' Define the Circle object
    centerPoint(0) = 0: centerPoint(1) = 0: centerPoint(2) = 0
    radius = 5#
    
    ' Create the Circle object in model space
    Set circleObj = ThisDrawing.ModelSpace.AddCircle(centerPoint, radius)

    ThisDrawing.Application.ZoomAll
    
    ' Prompt user for Layouts to plot
    For Each Layout In ThisDrawing.Layouts
        If MsgBox("Do you wish to plot the layout: " & Layout.name, vbYesNo & vbQuestion) = vbYes Then
            ArraySize = ArraySize + 1
            ReDim AddedLayouts(1 To ArraySize)
            AddedLayouts(ArraySize) = Layout.name
        End If
    Next
    
    ' If the user did not select any Layouts to plot then exit
    If ArraySize = 0 Then Exit Sub
    
    ' Send the array list containing the layout names to a variant
    ' which is compatible with SetLayoutsToPlot
    LayoutList = AddedLayouts
    
    ' Get the plot object from the drawing
    Set Plot = ThisDrawing.Plot
    
    ' Set plot options
    Plot.QuietErrorMode = False     ' We do want to be notified of errors
                                    ' * Note: Normally, in a batch situation, you do
                                    ' not want to be notified of errors, since this
                                    ' will halt the batch process.
                                    
    Plot.NumberOfCopies = 1         ' We only need one copy
    
    ' Start the batch plot the selected layouts
    
    Plot.StartBatchMode ArraySize   ' Number of items in this batch
    
    For BatchCount = 1 To ArraySize
        ' This must be called every time we call PlotToDevice
        Plot.SetLayoutsToPlot LayoutList
        
        ' Plot to default device
        Plot.PlotToDevice
        
        ' Display the results of the batch plot.  This property should really be
        ' displayed to and set from a VBA Form, but for this example, we will
        ' use a message box
        If Plot.BatchPlotProgress Then
            If MsgBox("Would you like to cancel the batch plot?", vbYesNo & vbQuestion) = vbYes Then
                Plot.BatchPlotProgress = False
            End If
        Else
            MsgBox "The batch plot has stopped!"
        End If
    Next
    
    MsgBox "Finished plotting the selected Layouts!"
End Sub
Sub Example_StartBatchMode()
    ' This example creates a Circle in model space and allows the user
    ' to select which layouts for the drawing to plot.  It then uses
    ' a batch operation to send the selected layouts to the current
    ' plot device and allows the user to cancel the batch plot at certain
    ' intervals.

    Dim Plot As AcadPlot
    Dim AddedLayouts() As String
    Dim LayoutList As Variant
    Dim circleObj As AcadCircle
    Dim centerPoint(0 To 2) As Double
    Dim radius As Double
    Dim Layout As ACADLayout
    Dim ArraySize As Integer, BatchCount As Integer
    
    ' Define the Circle object
    centerPoint(0) = 0: centerPoint(1) = 0: centerPoint(2) = 0
    radius = 5#
    
    ' Create the Circle object in model space
    Set circleObj = ThisDrawing.ModelSpace.AddCircle(centerPoint, radius)

    ThisDrawing.Application.ZoomAll
    
    ' Prompt user for Layouts to plot
    For Each Layout In ThisDrawing.Layouts
        If MsgBox("Do you wish to plot the layout: " & Layout.name, vbYesNo & vbQuestion) = vbYes Then
            ArraySize = ArraySize + 1
            ReDim AddedLayouts(1 To ArraySize)
            AddedLayouts(ArraySize) = Layout.name
        End If
    Next
    
    ' If the user did not select any Layouts to plot then exit
    If ArraySize = 0 Then Exit Sub
    
    ' Send the array list containing the layout names to a variant
    ' which is compatible with SetLayoutsToPlot
    LayoutList = AddedLayouts
    
    ' Get the plot object from the drawing
    Set Plot = ThisDrawing.Plot
    
    ' Set plot options
    Plot.QuietErrorMode = False     ' We do want to be notified of errors
                                    ' * Note: Normally, in a batch situation, you do
                                    ' not want to be notified of errors, since this
                                    ' will halt the batch process.
                                    
    Plot.NumberOfCopies = 1         ' We only need one copy
    
    ' Start the batch plot the selected layouts
    
    Plot.StartBatchMode ArraySize   ' Number of items in this batch
    
    For BatchCount = 1 To ArraySize
        ' This must be called every time we call PlotToDevice
        Plot.SetLayoutsToPlot LayoutList
        
        ' Plot to default device
        Plot.PlotToDevice
        
        ' Display the results of the batch plot.  This property should really be
        ' displayed to and set from a VBA Form, but for this example, we will
        ' use a message box
        If Plot.BatchPlotProgress Then
            If MsgBox("Would you like to cancel the batch plot?", vbYesNo & vbQuestion) = vbYes Then
                Plot.BatchPlotProgress = False
            End If
        Else
            MsgBox "The batch plot has stopped!"
        End If
    Next
    
    MsgBox "Finished plotting the selected Layouts!"
End Sub
Sub Example_QuietErrorMode()
    ' This example creates a Circle in model space and allows the user
    ' to select which layouts for the drawing to plot.  It then uses
    ' a batch operation to send the selected layouts to the current
    ' plot device and allows the user to cancel the batch plot at certain
    ' intervals.

    Dim Plot As AcadPlot
    Dim AddedLayouts() As String
    Dim LayoutList As Variant
    Dim circleObj As AcadCircle
    Dim centerPoint(0 To 2) As Double
    Dim radius As Double
    Dim Layout As ACADLayout
    Dim ArraySize As Integer, BatchCount As Integer
    
    ' Define the Circle object
    centerPoint(0) = 0: centerPoint(1) = 0: centerPoint(2) = 0
    radius = 5#
    
    ' Create the Circle object in model space
    Set circleObj = ThisDrawing.ModelSpace.AddCircle(centerPoint, radius)

    ThisDrawing.Application.ZoomAll
    
    ' Prompt user for Layouts to plot
    For Each Layout In ThisDrawing.Layouts
        If MsgBox("Do you wish to plot the layout: " & Layout.name, vbYesNo & vbQuestion) = vbYes Then
            ArraySize = ArraySize + 1
            ReDim AddedLayouts(1 To ArraySize)
            AddedLayouts(ArraySize) = Layout.name
        End If
    Next
    
    ' If the user did not select any Layouts to plot then exit
    If ArraySize = 0 Then Exit Sub
    
    ' Send the array list containing the layout names to a variant
    ' which is compatible with SetLayoutsToPlot
    LayoutList = AddedLayouts
    
    ' Get the plot object from the drawing
    Set Plot = ThisDrawing.Plot
    
    ' Set plot options
    Plot.QuietErrorMode = False     ' We do want to be notified of errors
                                    ' * Note: Normally, in a batch situation, you do
                                    ' not want to be notified of errors, since this
                                    ' will halt the batch process.
                                    
    Plot.NumberOfCopies = 1         ' We only need one copy
    
    ' Start the batch plot the selected layouts
    
    Plot.StartBatchMode ArraySize   ' Number of items in this batch
    
    For BatchCount = 1 To ArraySize
        ' This must be called every time we call PlotToDevice
        Plot.SetLayoutsToPlot LayoutList
        
        ' Plot to default device
        Plot.PlotToDevice
        
        ' Display the results of the batch plot.  This property should really be
        ' displayed to and set from a VBA Form, but for this example, we will
        ' use a message box
        If Plot.BatchPlotProgress Then
            If MsgBox("Would you like to cancel the batch plot?", vbYesNo & vbQuestion) = vbYes Then
                Plot.BatchPlotProgress = False
            End If
        Else
            MsgBox "The batch plot has stopped!"
        End If
    Next
    
    MsgBox "Finished plotting the selected Layouts!"
End Sub
Sub Example_NumberOfCopies()
    ' This example creates a Circle in model space and allows the user
    ' to select which layouts for the drawing to plot.  It then uses
    ' a batch operation to send the selected layouts to the current
    ' plot device and allows the user to cancel the batch plot at certain
    ' intervals.

    Dim Plot As AcadPlot
    Dim AddedLayouts() As String
    Dim LayoutList As Variant
    Dim circleObj As AcadCircle
    Dim centerPoint(0 To 2) As Double
    Dim radius As Double
    Dim Layout As ACADLayout
    Dim ArraySize As Integer, BatchCount As Integer
    
    ' Define the Circle object
    centerPoint(0) = 0: centerPoint(1) = 0: centerPoint(2) = 0
    radius = 5#
    
    ' Create the Circle object in model space
    Set circleObj = ThisDrawing.ModelSpace.AddCircle(centerPoint, radius)

    ThisDrawing.Application.ZoomAll
    
    ' Prompt user for Layouts to plot
    For Each Layout In ThisDrawing.Layouts
        If MsgBox("Do you wish to plot the layout: " & Layout.name, vbYesNo & vbQuestion) = vbYes Then
            ArraySize = ArraySize + 1
            ReDim AddedLayouts(1 To ArraySize)
            AddedLayouts(ArraySize) = Layout.name
        End If
    Next
    
    ' If the user did not select any Layouts to plot then exit
    If ArraySize = 0 Then Exit Sub
    
    ' Send the array list containing the layout names to a variant
    ' which is compatible with SetLayoutsToPlot
    LayoutList = AddedLayouts
    
    ' Get the plot object from the drawing
    Set Plot = ThisDrawing.Plot
    
    ' Set plot options
    Plot.QuietErrorMode = False     ' We do want to be notified of errors
                                    ' * Note: Normally, in a batch situation, you do
                                    ' not want to be notified of errors, since this
                                    ' will halt the batch process.
                                    
    Plot.NumberOfCopies = 1         ' We only need one copy
    
    ' Start the batch plot the selected layouts
    
    Plot.StartBatchMode ArraySize   ' Number of items in this batch
    
    For BatchCount = 1 To ArraySize
        ' This must be called every time we call PlotToDevice
        Plot.SetLayoutsToPlot LayoutList
        
        ' Plot to default device
        Plot.PlotToDevice
        
        ' Display the results of the batch plot.  This property should really be
        ' displayed to and set from a VBA Form, but for this example, we will
        ' use a message box
        If Plot.BatchPlotProgress Then
            If MsgBox("Would you like to cancel the batch plot?", vbYesNo & vbQuestion) = vbYes Then
                Plot.BatchPlotProgress = False
            End If
        Else
            MsgBox "The batch plot has stopped!"
        End If
    Next
    
    MsgBox "Finished plotting the selected Layouts!"
End Sub
Sub Example_BatchPlotProgress()
    ' This example creates a Circle in model space and allows the user
    ' to select which layouts for the drawing to plot.  It then uses
    ' a batch operation to send the selected layouts to the current
    ' plot device and allows the user to cancel the batch plot at certain
    ' intervals.

    Dim Plot As AcadPlot
    Dim AddedLayouts() As String
    Dim LayoutList As Variant
    Dim circleObj As AcadCircle
    Dim centerPoint(0 To 2) As Double
    Dim radius As Double
    Dim Layout As ACADLayout
    Dim ArraySize As Integer, BatchCount As Integer
    
    ' Define the Circle object
    centerPoint(0) = 0: centerPoint(1) = 0: centerPoint(2) = 0
    radius = 5#
    
    ' Create the Circle object in model space
    Set circleObj = ThisDrawing.ModelSpace.AddCircle(centerPoint, radius)

    ThisDrawing.Application.ZoomAll
    
    ' Prompt user for Layouts to plot
    For Each Layout In ThisDrawing.Layouts
        If MsgBox("Do you wish to plot the layout: " & Layout.name, vbYesNo & vbQuestion) = vbYes Then
            ArraySize = ArraySize + 1
            ReDim AddedLayouts(1 To ArraySize)
            AddedLayouts(ArraySize) = Layout.name
        End If
    Next
    
    ' If the user did not select any Layouts to plot then exit
    If ArraySize = 0 Then Exit Sub
    
    ' Send the array list containing the layout names to a variant
    ' which is compatible with SetLayoutsToPlot
    LayoutList = AddedLayouts
    
    ' Get the plot object from the drawing
    Set Plot = ThisDrawing.Plot
    
    ' Set plot options
    Plot.QuietErrorMode = False     ' We do want to be notified of errors
                                    ' * Note: Normally, in a batch situation, you do
                                    ' not want to be notified of errors, since this
                                    ' will halt the batch process.
                                    
    Plot.NumberOfCopies = 1         ' We only need one copy
    
    ' Start the batch plot the selected layouts
    
    Plot.StartBatchMode ArraySize   ' Number of items in this batch
    
    For BatchCount = 1 To ArraySize
        ' This must be called every time we call PlotToDevice
        Plot.SetLayoutsToPlot LayoutList
        
        ' Plot to default device
        Plot.PlotToDevice
        
        ' Display the results of the batch plot.  This property should really be
        ' displayed to and set from a VBA Form, but for this example, we will
        ' use a message box
        If Plot.BatchPlotProgress Then
            If MsgBox("Would you like to cancel the batch plot?", vbYesNo & vbQuestion) = vbYes Then
                Plot.BatchPlotProgress = False
            End If
        Else
            MsgBox "The batch plot has stopped!"
        End If
    Next
    
    MsgBox "Finished plotting the selected Layouts!"
End Sub
Sub Example_CopyObjects()
    ' This example creates a Circle object and uses the CopyObjects
    ' method to make a copy of the new Circle.

    Dim DOC1 As AcadDocument
    Dim circleObj1 As AcadCircle, circleObj2 As AcadCircle
    Dim circleObj1Copy As AcadCircle, circleObj2Copy As AcadCircle
    Dim centerPoint(0 To 2) As Double
    Dim radius1 As Double, radius2 As Double
    Dim radius1Copy As Double, radius2Copy As Double
    Dim objCollection(0 To 1) As Object
    Dim retObjects As Variant
    
    ' Define the Circle object
    centerPoint(0) = 0: centerPoint(1) = 0: centerPoint(2) = 0
    radius1 = 5#: radius2 = 7#
    radius1Copy = 1#: radius2Copy = 2#
    
    ' Create a new drawing
    Set DOC1 = Documents.Add
    
    ' Add two circles to the drawing
    Set circleObj1 = DOC1.ModelSpace.AddCircle(centerPoint, radius1)
    Set circleObj2 = DOC1.ModelSpace.AddCircle(centerPoint, radius2)
    ThisDrawing.Application.ZoomAll
    
    ' Copy objects
    '
    ' First put the objects to be copied into a form compatible with CopyObjects
    Set objCollection(0) = circleObj1
    Set objCollection(1) = circleObj2
    
    ' Copy object and get back a collection of the new objects (copies)
    retObjects = DOC1.CopyObjects(objCollection)
    
    ' Get newly created object and apply new properties to the copies
    Set circleObj1Copy = retObjects(0)
    Set circleObj2Copy = retObjects(1)
    
    circleObj1Copy.radius = radius1Copy
    circleObj1Copy.Color = acRed
    circleObj2Copy.radius = radius2Copy
    circleObj2Copy.Color = acRed
        
    ThisDrawing.Application.ZoomAll
    
    MsgBox "Circles copied."
End Sub
Sub Example_ToleranceUpperLimit()
   ' This example creates an aligned dimension in model space and
   ' sets the tolerance limits using the ToleranceLowerLimit and
   ' ToleranceUpperLimit properties

    Dim dimObj As AcadDimAligned
    Dim newText As AcadTextStyle
    Dim point1(0 To 2) As Double, point2(0 To 2) As Double
    Dim location(0 To 2) As Double
    
    ' Define the dimension
    point1(0) = 5: point1(1) = 5: point1(2) = 0
    point2(0) = 5.5: point2(1) = 5: point2(2) = 0
    location(0) = 5: location(1) = 7: location(2) = 0
    
    ' Create an aligned dimension object in model space
    Set dimObj = ThisDrawing.ModelSpace.AddDimAligned(point1, point2, location)
    
    ' Turn on tolerance display
    dimObj.ToleranceDisplay = acTolSymmetrical
    
    ThisDrawing.Application.ZoomAll
    
    ' Read and display the tolerance limits for the dimension
    MsgBox "The tolerance lower limit is set to: " & dimObj.ToleranceLowerLimit & vbCrLf & _
           "The tolerance upper limit is set to: " & dimObj.ToleranceUpperLimit
    
    ' Adjust the tolerance limits for this dimension
    dimObj.ToleranceLowerLimit = 0.0001
    dimObj.ToleranceUpperLimit = 0.005
    
    ThisDrawing.Regen acAllViewports
    
    ' Read and display the tolerance limits for the dimension
    MsgBox "The tolerance lower limit is now set to: " & dimObj.ToleranceLowerLimit & vbCrLf & _
           "The tolerance upper limit is now set to: " & dimObj.ToleranceUpperLimit

End Sub
Sub Example_ToleranceLowerLimit()
   ' This example creates an aligned dimension in model space and
   ' sets the tolerance limits using the ToleranceLowerLimit and
   ' ToleranceUpperLimit properties

    Dim dimObj As AcadDimAligned
    Dim newText As AcadTextStyle
    Dim point1(0 To 2) As Double, point2(0 To 2) As Double
    Dim location(0 To 2) As Double
    
    ' Define the dimension
    point1(0) = 5: point1(1) = 5: point1(2) = 0
    point2(0) = 5.5: point2(1) = 5: point2(2) = 0
    location(0) = 5: location(1) = 7: location(2) = 0
    
    ' Create an aligned dimension object in model space
    Set dimObj = ThisDrawing.ModelSpace.AddDimAligned(point1, point2, location)
    
    ' Turn on tolerance display
    dimObj.ToleranceDisplay = acTolSymmetrical
    
    ThisDrawing.Application.ZoomAll
    
    ' Read and display the tolerance limits for the dimension
    MsgBox "The tolerance lower limit is set to: " & dimObj.ToleranceLowerLimit & vbCrLf & _
           "The tolerance upper limit is set to: " & dimObj.ToleranceUpperLimit
    
    ' Adjust the tolerance limits for this dimension
    dimObj.ToleranceLowerLimit = 0.0001
    dimObj.ToleranceUpperLimit = 0.005
    
    ThisDrawing.Regen acAllViewports
    
    ' Read and display the tolerance limits for the dimension
    MsgBox "The tolerance lower limit is now set to: " & dimObj.ToleranceLowerLimit & vbCrLf & _
           "The tolerance upper limit is now set to: " & dimObj.ToleranceUpperLimit

End Sub
Sub Example_PickGroup()
    ' This example reads and modifies the preference value which
    ' determines if picking a single object in a group selects the entire group.
    ' When finished, this example resets the preference value back to
    ' it's original value.
    
    Dim ACADPref As AcadPreferencesSelection
    Dim originalValue As Variant, newValue As Variant
    
    ' Get the user preferences object
    Set ACADPref = ThisDrawing.Application.preferences.Selection
    
    ' Read and display the original value
    originalValue = ACADPref.PickGroup
    MsgBox "The PickGroup preference is set to: " & originalValue

    ' Modify the PickGroup preference by toggling the value
    ACADPref.PickGroup = Not (ACADPref.PickGroup)
    newValue = ACADPref.PickGroup
    MsgBox "The PickGroup preference has been set to: " & newValue

    ' Reset the preference back to it's original value
    '
    ' * Note: Comment out this last section to leave the change to
    '         this preference in effect
    ACADPref.PickGroup = originalValue
    MsgBox "The PickGroup preference was reset back to: " & originalValue
End Sub
Sub Example_XRefFadeIntensity()
    ' This example reads and modifies the preference value which controls
    ' the dimming intensity for XRefs. When finished, this example resets
    ' the preference value back to it's original value.
    '
    ' * Note: Changes can only be observed when in-place editing of an Xref
    ' object is in progress and other entities are visible.
    
    Dim ACADPref As AcadPreferencesDisplay
    Dim originalValue As Variant, newValue As Variant
    
    ' Get the display preferences object
    Set ACADPref = ThisDrawing.Application.preferences.DISPLAY
    
    ' Read and display the original value
    originalValue = ACADPref.XRefFadeIntensity
    MsgBox "The XRefFadeIntensity preference is: " & originalValue

    ' Modify the XRefFadeIntensity preference by setting it to 75
    ACADPref.XRefFadeIntensity = 75
    newValue = ACADPref.XRefFadeIntensity
    ThisDrawing.Regen acAllViewports
    
    MsgBox "The XRefFadeIntensity preference has been set to: " & newValue

    ' Reset the preference back to it's original value
    '
    ' * Note: Comment out this last section to leave the change to
    '         this preference in effect
    ACADPref.XRefFadeIntensity = originalValue
    ThisDrawing.Regen acAllViewports
    
    MsgBox "The XRefFadeIntensity preference was reset back to: " & originalValue
End Sub

Sub Example_GetPlotDeviceNames()
    ' This example gets the current plot device information
    ' and then displays the list of plot device names,
    ' media names, localized media names, and plot style
    ' table entries.
    Dim Layout As ACADLayout
    Set Layout = ThisDrawing.ModelSpace.Layout
    
    ' Refresh the current plot information for
    ' this session.
    Layout.RefreshPlotDeviceInfo
    
    ' List all the valid device names for the system
    Dim plotDevices As Variant
    plotDevices = Layout.GetPlotDeviceNames()
    
    Dim x As Integer
    For x = LBound(plotDevices) To UBound(plotDevices)
        MsgBox plotDevices(x)
    Next
    
    ' List all the media names, and their localized version
    Dim mediaNames As Variant
    mediaNames = Layout.GetCanonicalMediaNames()
    
    For x = LBound(mediaNames) To UBound(mediaNames)
        MsgBox mediaNames(x)
        MsgBox Layout.GetLocaleMediaName(mediaNames(x))
    Next
    
    ' List all the entries in the plot style table
    Dim styleNames As Variant
    styleNames = Layout.GetPlotStyleTableNames()
    
    For x = LBound(styleNames) To UBound(styleNames)
        MsgBox styleNames(x)
    Next
    
End Sub
Sub Example_GetAllProfileNames()
    ' This example gets all the profiles available for the system.
    
    Dim systemProfiles As Variant
    Call AcadApplication.preferences.Profiles.GetAllProfileNames(systemProfiles)
       
    ' List all the profiles for the system
    Dim x As Integer
    Dim msg As String
    msg = ""
    For x = LBound(systemProfiles) To UBound(systemProfiles)
        msg = msg & systemProfiles(x) & vbCrLf
    Next
    MsgBox msg, vbInformation, "Available Profiles"
End Sub
Sub Example_RefreshPlotDeviceInfo()
    ' This example gets the current plot device information
    ' and then displays the list of plot device names,
    ' media names, localized media names, and plot style
    ' table entries.
    Dim Layout As ACADLayout
    Set Layout = ThisDrawing.ModelSpace.Layout
    
    ' Refresh the current plot information for
    ' this session.
    Layout.RefreshPlotDeviceInfo
    
    ' List all the valid device names for the system
    Dim plotDevices As Variant
    plotDevices = Layout.GetPlotDeviceNames()
    
    Dim x As Integer
    For x = LBound(plotDevices) To UBound(plotDevices)
        MsgBox plotDevices(x)
    Next
    
    ' List all the media names, and their localized version
    Dim mediaNames As Variant
    mediaNames = Layout.GetCanonicalMediaNames()
    
    For x = LBound(mediaNames) To UBound(mediaNames)
        MsgBox mediaNames(x)
        MsgBox Layout.GetLocaleMediaName(mediaNames(x))
    Next
    
    ' List all the entries in the plot style table
    Dim styleNames As Variant
    styleNames = Layout.GetPlotStyleTableNames()
    
    For x = LBound(styleNames) To UBound(styleNames)
        MsgBox styleNames(x)
    Next
    
End Sub
Sub Example_GetCanonicalMediaNames()
    ' This example gets the current plot device information
    ' and then displays the list of plot device names,
    ' media names, localized media names, and plot style
    ' table entries.
    Dim Layout As ACADLayout
    Set Layout = ThisDrawing.ModelSpace.Layout
    
    ' Refresh the current plot information for
    ' this session.
    Layout.RefreshPlotDeviceInfo
    
    ' List all the valid device names for the system
    Dim plotDevices As Variant
    plotDevices = Layout.GetPlotDeviceNames()
    
    Dim x As Integer
    For x = LBound(plotDevices) To UBound(plotDevices)
        MsgBox plotDevices(x)
    Next
    
    ' List all the media names, and their localized version
    Dim mediaNames As Variant
    mediaNames = Layout.GetCanonicalMediaNames()
    
    For x = LBound(mediaNames) To UBound(mediaNames)
        MsgBox mediaNames(x)
        MsgBox Layout.GetLocaleMediaName(mediaNames(x))
    Next
    
    ' List all the entries in the plot style table
    Dim styleNames As Variant
    styleNames = Layout.GetPlotStyleTableNames()
    
    For x = LBound(styleNames) To UBound(styleNames)
        MsgBox styleNames(x)
    Next
    
End Sub
Sub Example_GetLocaleMediaName()
    ' This example gets the current plot device information
    ' and then displays the list of plot device names,
    ' media names, localized media names, and plot style
    ' table entries.
    Dim Layout As ACADLayout
    Set Layout = ThisDrawing.ModelSpace.Layout
    
    ' Refresh the current plot information for
    ' this session.
    Layout.RefreshPlotDeviceInfo
    
    ' List all the valid device names for the system
    Dim plotDevices As Variant
    plotDevices = Layout.GetPlotDeviceNames()
    
    Dim x As Integer
    For x = LBound(plotDevices) To UBound(plotDevices)
        MsgBox plotDevices(x)
    Next
    
    ' List all the media names, and their localized version
    Dim mediaNames As Variant
    mediaNames = Layout.GetCanonicalMediaNames()
    
    For x = LBound(mediaNames) To UBound(mediaNames)
        MsgBox mediaNames(x)
        MsgBox Layout.GetLocaleMediaName(mediaNames(x))
    Next
    
    ' List all the entries in the plot style table
    Dim styleNames As Variant
    styleNames = Layout.GetPlotStyleTableNames()
    
    For x = LBound(styleNames) To UBound(styleNames)
        MsgBox styleNames(x)
    Next
    
End Sub
Sub Example_GetPlotStyleTableNames()
    ' This example gets the current plot device information
    ' and then displays the list of plot device names,
    ' media names, localized media names, and plot style
    ' table entries.
    Dim Layout As ACADLayout
    Set Layout = ThisDrawing.ModelSpace.Layout
    
    ' Refresh the current plot information for
    ' this session.
    Layout.RefreshPlotDeviceInfo
    
    ' List all the valid device names for the system
    Dim plotDevices As Variant
    plotDevices = Layout.GetPlotDeviceNames()
    
    Dim x As Integer
    For x = LBound(plotDevices) To UBound(plotDevices)
        MsgBox plotDevices(x)
    Next
    
    ' List all the media names, and their localized version
    Dim mediaNames As Variant
    mediaNames = Layout.GetCanonicalMediaNames()
    
    For x = LBound(mediaNames) To UBound(mediaNames)
        MsgBox mediaNames(x)
        MsgBox Layout.GetLocaleMediaName(mediaNames(x))
    Next
    
    ' List all the entries in the plot style table
    Dim styleNames As Variant
    styleNames = Layout.GetPlotStyleTableNames()
    
    For x = LBound(styleNames) To UBound(styleNames)
        MsgBox styleNames(x)
    Next
    
End Sub
Sub Example_LargeButtons()
    ' This example uses MenuGroups to obtain a reference to the ACAD main menu.
    ' It then creates a new Toolbar (TestMenu) and inserts a ToolBarButton
    ' into it.  We then set the LargeButtons property to change the visible style
    ' of all the system Toolbars
    
    Dim CurrSize As Boolean, ButtonSize As String
    Dim Toolbars As AcadToolbars

    ' Make the system Toolbar buttons bigger
    Set Toolbars = ThisDrawing.Application.MenuGroups("ACAD").Toolbars
   
    ' Get current size
    CurrSize = Toolbars.LargeButtons
    
    ' Display current Toolbar size
    GoSub DISPLAY
   
    ' Toggle Toolbar size
    Toolbars.LargeButtons = Not (Toolbars.LargeButtons)
    
    ' Display current Toolbar size
    GoSub DISPLAY
    
    ' Reset to original value
    Toolbars.LargeButtons = CurrSize
    
    ' Display current Toolbar size
    GoSub DISPLAY

    Exit Sub
    
DISPLAY:
    ' Display button style
    ButtonSize = IIf(Toolbars.LargeButtons, "Large", "Normal size")
    MsgBox "We are displaying " & ButtonSize & " buttons.", vbInformation

    Return
End Sub
Sub Example_AttachToolbarToFlyout()
    ' This example uses MenuGroups to obtain a reference to the ACAD main menu.
    ' It then creates a new Toolbar(TestMenu) with a Toolbar button that will act
    ' as a flyout.  We will then set the Flyout menu to an existing Toolbar menu.
    ' The Toolbar will automatically be displayed and will display the UCS menu
    ' as a flyout.
        
    Dim currMenuGroup As acadMenuGroup
    Dim newToolBar As AcadToolbar, newToolBarFlyoutButton As AcadToolbarItem
    
    On Error GoTo ERRORTRAP
    
    ' Use MenuGroups property to obtain reference to main ACAD menu
    Set currMenuGroup = ThisDrawing.Application.MenuGroups.Item("ACAD")
    
    ' Create a new Toolbar in this group
    Set newToolBar = currMenuGroup.Toolbars.Add("TestMenu")
    
    ' Add new button to TestMenu that will link to the Flyout menu
    '
    ' * NOTE: We set the macro name to the name of the flyout toolbar.
    ' We do this since setting it to an empty string causes an error.  The paremeter
    ' is actually ignored when the style is flyout, but must have any value other than "".
    Set newToolBarFlyoutButton = newToolBar.AddToolbarButton(newToolBar.count + 1, "Flyout", "Flyout", "UCS", True)
    
    ' Link the existing toolbar "UCS" as the flyout for our new toolbar button
    '
    ' * NOTE: To change the flyout, simply change the MenuGroup and Toolbar name below
    newToolBarFlyoutButton.AttachToolbarToFlyout "ACAD", "UCS"
   
    MsgBox "A new Toolbar with a flyout has been added to the ACAD menu system!"
    
    Exit Sub

ERRORTRAP:
    MsgBox "The following error has occurred: " & Err.Description
End Sub
Sub Example_Flyout()
    ' This example uses MenuGroups to obtain a reference to the ACAD main menu.
    ' It then creates a new Toolbar(TestMenu) with a Toolbar button that will act
    ' as a flyout.  We will then set the Flyout menu to an existing Toolbar menu.
    ' The Toolbar will automatically be displayed and will display the UCS menu
    ' as a flyout.
        
    Dim currMenuGroup As acadMenuGroup
    Dim newToolBar As AcadToolbar, newToolBarFlyoutButton As AcadToolbarItem
    
    On Error GoTo ERRORTRAP
    
    ' Use MenuGroups property to obtain reference to main ACAD menu
    Set currMenuGroup = ThisDrawing.Application.MenuGroups.Item("ACAD")
    
    ' Create a new Toolbar in this group
    Set newToolBar = currMenuGroup.Toolbars.Add("TestMenu")
    
    ' Add new button to TestMenu that will link to the Flyout menu
    '
    ' * NOTE: We set the macro name to the name of the flyout toolbar.
    ' We do this since setting it to an empty string causes an error.  The paremeter
    ' is actually ignored when the style is flyout, but must have any value other than "".
    Set newToolBarFlyoutButton = newToolBar.AddToolbarButton(newToolBar.count + 1, "Flyout", "Flyout", "UCS", True)
    
    ' Link the existing toolbar "UCS" as the flyout for our new toolbar button
    '
    ' * NOTE: To change the flyout, simply change the MenuGroup and Toolbar name below
    newToolBarFlyoutButton.AttachToolbarToFlyout "ACAD", "UCS"
   
    MsgBox "The flyout attached to the Test menu is " & newToolBarFlyoutButton.Flyout.name
    
    Exit Sub

ERRORTRAP:
    MsgBox "The following error has occurred: " & Err.Description
End Sub
Sub Example_ControlPoints()
   ' This example creates a Spline object in model space, reads the control points
   ' of the Spline and then modifies the control points of the Spline.

    Dim splineObj As AcadSpline
    Dim startTan(0 To 2) As Double, endTan(0 To 2) As Double
    Dim fitPoints(0 To 8) As Double
    Dim UserMessage As String
    Dim ControlPoints As Variant
    Dim iCount As Long, iPoint As Integer
    
    ' Define the Spline object
    startTan(0) = 0.5: startTan(1) = 0.5: startTan(2) = 0
    endTan(0) = 0.5: endTan(1) = 0.5: endTan(2) = 0
    fitPoints(0) = 0: fitPoints(1) = 0: fitPoints(2) = 0
    fitPoints(3) = 5:   fitPoints(4) = 5: fitPoints(5) = 0
    fitPoints(6) = 10: fitPoints(7) = 0: fitPoints(8) = 0
    
    ' Create new Spline object
    Set splineObj = ThisDrawing.ModelSpace.AddSpline(fitPoints, startTan, endTan)
    ThisDrawing.Application.ZoomAll
    
    ' Display control points for this Spline
    GoSub DISPLAYPOINTS
    
    ' Modify control points for this Spline
    ControlPoints(0) = 3
    splineObj.ControlPoints = ControlPoints
    ThisDrawing.Application.ZoomAll
        
    ' Display new control points for this Spline
    GoSub DISPLAYPOINTS
        
    Exit Sub
    
DISPLAYPOINTS:
    ControlPoints = splineObj.ControlPoints
    
    ' Display in groups of three
    UserMessage = ""
    iPoint = 0
    For iCount = 0 To UBound(ControlPoints) Step 3
        iPoint = iPoint + 1
        UserMessage = UserMessage & iPoint & ")" & vbTab
        UserMessage = UserMessage & ControlPoints(iCount)
        UserMessage = UserMessage & ", " & ControlPoints(iCount + 1)
        UserMessage = UserMessage & ", " & ControlPoints(iCount + 2)
        UserMessage = UserMessage & vbCrLf
    Next
    
    MsgBox "The " & splineObj.NumberOfControlPoints & " Spline control points are: " & vbCrLf & vbCrLf & UserMessage
    
    Return
End Sub
Sub Example_FitPoints()
   ' This example creates a Spline object in model space, reads the fit points
   ' of the Spline and then modifies the fit points of the Spline.

    Dim splineObj As AcadSpline
    Dim startTan(0 To 2) As Double, endTan(0 To 2) As Double
    Dim FPoints(0 To 8) As Double
    Dim UserMessage As String
    Dim fitPoints As Variant
    Dim iCount As Long, iPoint As Integer
    Dim NewFP(0 To 2) As Double
    
    ' Define the Spline object
    startTan(0) = 0.5: startTan(1) = 0.5: startTan(2) = 0
    endTan(0) = 0.5: endTan(1) = 0.5: endTan(2) = 0
    FPoints(0) = 0: FPoints(1) = 0: FPoints(2) = 0
    FPoints(3) = 5:   FPoints(4) = 5: FPoints(5) = 0
    FPoints(6) = 10: FPoints(7) = 0: FPoints(8) = 0
    
    ' Create new Spline object
    Set splineObj = ThisDrawing.ModelSpace.AddSpline(FPoints, startTan, endTan)
    ThisDrawing.Application.ZoomAll
    
    ' Display fit points for this Spline
    GoSub DISPLAYPOINTS
    
    ' Modify an existing fit point for this Spline
    fitPoints(0) = 3
    splineObj.fitPoints = fitPoints
    
    ' Now add a new fit point
    NewFP(0) = 15: NewFP(1) = 4: NewFP(2) = 0
    splineObj.AddFitPoint splineObj.NumberOfFitPoints + 1, NewFP
        
    ThisDrawing.Application.ZoomAll
            
    ' Display new fit points for this Spline
    GoSub DISPLAYPOINTS
        
    Exit Sub
    
DISPLAYPOINTS:
    fitPoints = splineObj.fitPoints
    
    ' Display in groups of three
    UserMessage = ""
    iPoint = 0
    For iCount = 0 To UBound(fitPoints) Step 3
        iPoint = iPoint + 1
        UserMessage = UserMessage & iPoint & ")" & vbTab
        UserMessage = UserMessage & fitPoints(iCount)
        UserMessage = UserMessage & ", " & fitPoints(iCount + 1)
        UserMessage = UserMessage & ", " & fitPoints(iCount + 2)
        UserMessage = UserMessage & vbCrLf
    Next
    
    MsgBox "The " & splineObj.NumberOfFitPoints & " Spline fit points are: " & vbCrLf & vbCrLf & UserMessage
    
    Return
End Sub
Sub Example_DefaultPlotStyleTable()
    ' This example reads and modifies the preference value which
    ' specifies the default plot style table to attach to new drawings.
    '
    ' * Note: You may want to change the path of the new style table below.
    
    Dim ACADPref As AcadPreferencesOutput
    Dim CurrentFile As String
    
    Const NewFile = "c:\program files\Acad2000\Plot Styles\monochrome.ctb"
    
    ' Get the drafting preferences object
    Set ACADPref = ThisDrawing.Application.preferences.Output
    
    ' Read and display the current plot style table path
    CurrentFile = ACADPref.DefaultPlotStyleTable
    If CurrentFile = "" Then
        MsgBox "There is no current plot style table being used", vbInformation
    Else
        MsgBox "The current plot style table is: " & CurrentFile
    End If

    ' Use a new plot style table
    ACADPref.DefaultPlotStyleTable = NewFile
    
    ' Read and display the new plot style table path
    CurrentFile = ACADPref.DefaultPlotStyleTable
    MsgBox "The new plot style table is: " & CurrentFile, vbInformation

End Sub
Sub Example_DimensionLineExtend()
   ' This example creates an aligned dimension in model space and
   ' uses DimensionLineExtend to specify the distance the dimension
   ' line extends beyond the extension line when oblique strokes are
   ' drawn instead of arrowheads

    Dim dimObj As AcadDimAligned
    Dim point1(0 To 2) As Double, point2(0 To 2) As Double
    Dim location(0 To 2) As Double
    
    ' Define the dimension
    point1(0) = 5: point1(1) = 5: point1(2) = 0
    point2(0) = 10.123: point2(1) = 5: point2(2) = 0
    location(0) = 5: location(1) = 7: location(2) = 0
    
    ' Create an aligned dimension object in model space
    Set dimObj = ThisDrawing.ModelSpace.AddDimAligned(point1, point2, location)
    dimObj.Arrowhead1Type = acArrowOblique
    dimObj.Arrowhead2Type = acArrowOblique
    
    ThisDrawing.Application.ZoomAll
    
    MsgBox "A new Dimension has been created.  Press any key to extend the dimension lines."
    
    ' Round the distance of the alternate dimension to 0.50 of a unit
    dimObj.DimensionLineExtend = 2
    ThisDrawing.Regen acAllViewports
    
    MsgBox "The dimension lines have been extended to: " & dimObj.DimensionLineExtend
End Sub
Sub Example_DimLineSuppress()
   ' This example creates a Radial Dimension in model space and
   ' uses the DimLineSuppress property to toggle the display
   ' of the dimension lines

    Dim dimObj As AcadDimRadial
    Dim center(0 To 2) As Double
    Dim chordPoint(0 To 2) As Double
    Dim leaderLen As Integer
    
    ' Define the dimension
    center(0) = 0: center(1) = 0: center(2) = 0
    chordPoint(0) = 5: chordPoint(1) = 5: chordPoint(2) = 0
    leaderLen = 5
    
    ' Create the radial dimension in model space
    Set dimObj = ThisDrawing.ModelSpace.AddDimRadial(center, chordPoint, leaderLen)
    ThisDrawing.Application.ZoomAll
    
    MsgBox "The radial dimension has been created.", vbInformation
    
    dimObj.DimLineSuppress = Not (dimObj.DimLineSuppress)
    ThisDrawing.Application.ZoomAll
    
    MsgBox "The radial dimension appearance has been modified.", vbInformation
End Sub
Sub Example_GetBitmaps()
    ' This example uses MenuGroups to obtain a reference to the ACAD main menu.
    ' It then creates a new Toolbar (TestMenu) and inserts a ToolBarButton
    ' with a custom icon into it. The menu is automatically shown.
    '
    ' * NOTE: The paths of the icons for the new tollbar should be updated
    ' before running this example.
        
    Dim currMenuGroup As acadMenuGroup
    Dim newToolBar As AcadToolbar, newToolBarButton As AcadToolbarItem
    Dim openMacro As String
    Dim SmallBitmapName  As String, LargeBitmapName  As String
    
    On Error GoTo ERRORTRAP
    
    ' Use MenuGroups property to obtain reference to main ACAD menu
    Set currMenuGroup = ThisDrawing.Application.MenuGroups.Item("ACAD")
    
    ' Create the new Toolbar in this group
    Set newToolBar = currMenuGroup.Toolbars.Add("TestMenu")
    
    ' Add an item the new Toolbar and assign an Open macro
    ' (VBA equivalent of: "ESC ESC _open ")
    openMacro = Chr(3) & Chr(3) & Chr(95) & "open" & Chr(32)
    Set newToolBarButton = newToolBar.AddToolbarButton(newToolBar.count + 1, "Open", "Open Macro", openMacro, False)
   
    ' Read icon paths for this Toolbar button
    GoSub READPATHS
    
    ' Change the default icon (smile face) for the new toolbar button
    SmallBitmapName = "c:\images\16x16.bmp"     ' Use a 16x16 pixel .BMP image
    LargeBitmapName = "c:\images\32x32.bmp"     ' Use a 32x32 pixel .BMP image
    newToolBarButton.SetBitmaps SmallBitmapName, LargeBitmapName
    
    ' Read icon paths for this Toolbar button
    GoSub READPATHS
    
    Exit Sub
    
READPATHS:
    ' Read icon paths for this Toolbar button
    newToolBarButton.GetBitmaps SmallBitmapName, LargeBitmapName
    MsgBox "The new Toolbar uses the following icon files: " & _
           vbCrLf & vbCrLf & "Small Bitmap: " & SmallBitmapName & vbCrLf & _
           "Large Bitmap: " & LargeBitmapName

    Return

ERRORTRAP:
    MsgBox "The following error has occurred: " & Err.Description
End Sub
Sub Example_SetBitmaps()
    ' This example uses MenuGroups to obtain a reference to the ACAD main menu.
    ' It then creates a new Toolbar (TestMenu) and inserts a ToolBarButton
    ' with a custom icon into it. The menu is automatically shown.
    '
    ' * NOTE: The paths of the icons for the new tollbar should be updated
    ' before running this example.
        
    Dim currMenuGroup As acadMenuGroup
    Dim newToolBar As AcadToolbar, newToolBarButton As AcadToolbarItem
    Dim openMacro As String
    Dim SmallBitmapName  As String, LargeBitmapName  As String
    
    On Error GoTo ERRORTRAP
    
    ' Use MenuGroups property to obtain reference to main ACAD menu
    Set currMenuGroup = ThisDrawing.Application.MenuGroups.Item("ACAD")
    
    ' Create the new Toolbar in this group
    Set newToolBar = currMenuGroup.Toolbars.Add("TestMenu")
    
    ' Add an item the new Toolbar and assign an Open macro
    ' (VBA equivalent of: "ESC ESC _open ")
    openMacro = Chr(3) & Chr(3) & Chr(95) & "open" & Chr(32)
    Set newToolBarButton = newToolBar.AddToolbarButton(newToolBar.count + 1, "Open", "Open Macro", openMacro, False)
   
    ' Read icon paths for this Toolbar button
    GoSub READPATHS
    
    ' Change the default icon (smile face) for the new toolbar button
    SmallBitmapName = "c:\images\16x16.bmp"     ' Use a 16x16 pixel .BMP image
    LargeBitmapName = "c:\images\32x32.bmp"     ' Use a 32x32 pixel .BMP image
    newToolBarButton.SetBitmaps SmallBitmapName, LargeBitmapName
    
    ' Read icon paths for this Toolbar button
    GoSub READPATHS
    
    Exit Sub
    
READPATHS:
    ' Read icon paths for this Toolbar button
    newToolBarButton.GetBitmaps SmallBitmapName, LargeBitmapName
    MsgBox "The new Toolbar uses the following icon files: " & _
           vbCrLf & vbCrLf & "Small Bitmap: " & SmallBitmapName & vbCrLf & _
           "Large Bitmap: " & LargeBitmapName
    Return

ERRORTRAP:
    MsgBox "The following error has occurred: " & Err.Description
End Sub
Sub Example_Key()
    ' This example creates two Circle objects and uses the CopyObjects
    ' method to make a copy of the new Circles.  It then returns the
    ' object ID's of the source objects using the .Key property and uses these
    ' values to remove the original (source) objects

    Dim circleObj1 As AcadCircle, circleObj2 As AcadCircle
    Dim circleObj1Copy As AcadCircle, circleObj2Copy As AcadCircle
    Dim centerPoint(0 To 2) As Double
    Dim radius1 As Double, radius2 As Double
    Dim radius1Copy As Double, radius2Copy As Double
    Dim objCollection(0 To 1) As Object
    Dim retObjects As Variant
    Dim IDPairs As Variant
    Dim SourceObject As AcadObject
    
    ' Define the Circle object
    centerPoint(0) = 0: centerPoint(1) = 0: centerPoint(2) = 0
    radius1 = 5#: radius2 = 7#
    radius1Copy = 1#: radius2Copy = 2#
    
    ' Add two circles to the drawing
    Set circleObj1 = ThisDrawing.ModelSpace.AddCircle(centerPoint, radius1)
    Set circleObj2 = ThisDrawing.ModelSpace.AddCircle(centerPoint, radius2)
    ThisDrawing.Application.ZoomAll
    
    ' Copy objects
    '
    ' First put the objects to be copied into a form compatible with CopyObjects
    Set objCollection(0) = circleObj1
    Set objCollection(1) = circleObj2
    
    ' Copy object and get back a collection of the new objects (copies)
    retObjects = ThisDrawing.CopyObjects(objCollection, , IDPairs)
    
    ' Get newly created object and apply new properties to the copies
    Set circleObj1Copy = retObjects(0)
    Set circleObj2Copy = retObjects(1)
    
    circleObj1Copy.radius = radius1Copy
    circleObj1Copy.Color = acRed
    circleObj2Copy.radius = radius2Copy
    circleObj2Copy.Color = acRed
        
    ThisDrawing.Application.ZoomAll
    ThisDrawing.Regen acAllViewports
    
    ' Display the object ID's of the source objects used for the copy
    MsgBox "The first source object ID is: " & IDPairs(0).Key & vbCrLf & _
           "The second source object ID is: " & IDPairs(1).Key

    ' This key can be used with objectIDtoObject to reference the source objects,
    ' which is handy if the user manually selected the source objects.
    '
    ' Here we delete the source objects from the ID obtained
    Set SourceObject = ThisDrawing.ObjectIdToObject(IDPairs(0).Key)
    SourceObject.Delete
    Set SourceObject = ThisDrawing.ObjectIdToObject(IDPairs(1).Key)
    SourceObject.Delete
    
    ThisDrawing.Regen acAllViewports
    
    MsgBox "We just deleted the source objects!", vbInformation
End Sub
Sub Example_Value()
    ' This example creates two Circle objects and uses the CopyObjects
    ' method to make a copy of the new Circles.  It then returns the
    ' object ID's of the new objects using the .Value property and uses these
    ' values to remove the new (target) objects

    Dim circleObj1 As AcadCircle, circleObj2 As AcadCircle
    Dim circleObj1Copy As AcadCircle, circleObj2Copy As AcadCircle
    Dim centerPoint(0 To 2) As Double
    Dim radius1 As Double, radius2 As Double
    Dim radius1Copy As Double, radius2Copy As Double
    Dim objCollection(0 To 1) As Object
    Dim retObjects As Variant
    Dim IDPairs As Variant
    Dim TargetObject As AcadObject
    
    ' Define the Circle object
    centerPoint(0) = 0: centerPoint(1) = 0: centerPoint(2) = 0
    radius1 = 5#: radius2 = 7#
    radius1Copy = 1#: radius2Copy = 2#
    
    ' Add two circles to the drawing
    Set circleObj1 = ThisDrawing.ModelSpace.AddCircle(centerPoint, radius1)
    Set circleObj2 = ThisDrawing.ModelSpace.AddCircle(centerPoint, radius2)
    ThisDrawing.Application.ZoomAll
    
    ' Copy objects
    '
    ' First put the objects to be copied into a form compatible with CopyObjects
    Set objCollection(0) = circleObj1
    Set objCollection(1) = circleObj2
    
    ' Copy object and get back a collection of the new objects (copies)
    retObjects = ThisDrawing.CopyObjects(objCollection, , IDPairs)
    
    ' Get newly created object and apply new properties to the copies
    Set circleObj1Copy = retObjects(0)
    Set circleObj2Copy = retObjects(1)
    
    circleObj1Copy.radius = radius1Copy
    circleObj1Copy.Color = acRed
    circleObj2Copy.radius = radius2Copy
    circleObj2Copy.Color = acRed
        
    ThisDrawing.Application.ZoomAll
    ThisDrawing.Regen acAllViewports
    
    ' Display the object ID's of the source objects used for the copy
    MsgBox "The first target object ID is: " & IDPairs(0).value & vbCrLf & _
           "The second target object ID is: " & IDPairs(1).value

    ' This key can be used with objectIDtoObject to reference the source objects,
    ' which is handy if the user manually selected the source objects.
    '
    ' Here we delete the source objects from the ID obtained
    Set TargetObject = ThisDrawing.ObjectIdToObject(IDPairs(0).value)
    TargetObject.Delete
    Set TargetObject = ThisDrawing.ObjectIdToObject(IDPairs(1).value)
    TargetObject.Delete
    
    ThisDrawing.Regen acAllViewports
    
    MsgBox "We just deleted the target objects!", vbInformation
End Sub
Sub Example_IsCloned()
    ' This example creates a Circle object and uses the CopyObjects
    ' method to make a copy of the new Circle.  It then displays some information
    ' about the source objects used in the CopyObjects operation.

    Dim circleObj As AcadCircle, circleObjCopy As AcadCircle
    Dim centerPoint(0 To 2) As Double
    Dim radius1 As Double, radius1Copy As Double
    Dim objCollection(0 To 0) As Object
    Dim retObjects As Variant
    Dim IDPairs As Variant
    Dim IsClonedState As String, IsPrimary As String, IsXLated As String
    
    ' Define the Circle object
    centerPoint(0) = 0: centerPoint(1) = 0: centerPoint(2) = 0
    radius1 = 5#: radius1Copy = 1#
    
    ' Add two circles to the drawing
    Set circleObj = ThisDrawing.ModelSpace.AddCircle(centerPoint, radius1)
    ThisDrawing.Application.ZoomAll
    
    ' Copy objects
    '
    ' First put the objects to be copied into a form compatible with CopyObjects
    Set objCollection(0) = circleObj
    
    ' Copy object and get back a collection of the new objects (copies)
    retObjects = ThisDrawing.CopyObjects(objCollection, , IDPairs)
    
    ' Get newly created object and apply new properties to the copies
    Set circleObjCopy = retObjects(0)
    
    circleObjCopy.radius = radius1Copy
    circleObjCopy.Color = acRed
        
    ThisDrawing.Application.ZoomAll
    ThisDrawing.Regen acAllViewports
    
    ' Display whether the first source object has a clone
    IsClonedState = IIf(IDPairs(0).IsCloned, "is cloned.", "is not cloned.")
    IsPrimary = IIf(IDPairs(0).IsPrimary, "is a primary member of the objects being copied.", "is owned by a primary member of the objects being copied.")
    IsXLated = IIf(IDPairs(0).IsOwnerXlated, "has been translated.", "has not been translated.")
    
    MsgBox "The new Circle source object: " & IsClonedState & vbCrLf & _
           "The new Circle source object: " & IsPrimary & vbCrLf & _
           "The source of the new Circle object: " & IsXLated & vbCrLf, vbInformation

End Sub
Sub Example_IsOwnerXlated()
    ' This example creates a Circle object and uses the CopyObjects
    ' method to make a copy of the new Circle.  It then displays some information
    ' about the source objects used in the CopyObjects operation.

    Dim circleObj As AcadCircle, circleObjCopy As AcadCircle
    Dim centerPoint(0 To 2) As Double
    Dim radius1 As Double, radius1Copy As Double
    Dim objCollection(0 To 0) As Object
    Dim retObjects As Variant
    Dim IDPairs As Variant
    Dim IsClonedState As String, IsPrimary As String, IsXLated As String
    
    ' Define the Circle object
    centerPoint(0) = 0: centerPoint(1) = 0: centerPoint(2) = 0
    radius1 = 5#: radius1Copy = 1#
    
    ' Add two circles to the drawing
    Set circleObj = ThisDrawing.ModelSpace.AddCircle(centerPoint, radius1)
    ThisDrawing.Application.ZoomAll
    
    ' Copy objects
    '
    ' First put the objects to be copied into a form compatible with CopyObjects
    Set objCollection(0) = circleObj
    
    ' Copy object and get back a collection of the new objects (copies)
    retObjects = ThisDrawing.CopyObjects(objCollection, , IDPairs)
    
    ' Get newly created object and apply new properties to the copies
    Set circleObjCopy = retObjects(0)
    
    circleObjCopy.radius = radius1Copy
    circleObjCopy.Color = acRed
        
    ThisDrawing.Application.ZoomAll
    ThisDrawing.Regen acAllViewports
    
    ' Display whether the first source object has a clone
    IsClonedState = IIf(IDPairs(0).IsCloned, "is cloned.", "is not cloned.")
    IsPrimary = IIf(IDPairs(0).IsPrimary, "is a primary member of the objects being copied.", "is owned by a primary member of the objects being copied.")
    IsXLated = IIf(IDPairs(0).IsOwnerXlated, "has been translated.", "has not been translated.")
    
    MsgBox "The new Circle source object: " & IsClonedState & vbCrLf & _
           "The new Circle source object: " & IsPrimary & vbCrLf & _
           "The source of the new Circle object: " & IsXLated & vbCrLf, vbInformation

End Sub
Sub Example_IsPrimary()
    ' This example creates a Circle object and uses the CopyObjects
    ' method to make a copy of the new Circle.  It then displays some information
    ' about the source objects used in the CopyObjects operation.

    Dim circleObj As AcadCircle, circleObjCopy As AcadCircle
    Dim centerPoint(0 To 2) As Double
    Dim radius1 As Double, radius1Copy As Double
    Dim objCollection(0 To 0) As Object
    Dim retObjects As Variant
    Dim IDPairs As Variant
    Dim IsClonedState As String, IsPrimary As String, IsXLated As String
    
    ' Define the Circle object
    centerPoint(0) = 0: centerPoint(1) = 0: centerPoint(2) = 0
    radius1 = 5#: radius1Copy = 1#
    
    ' Add two circles to the drawing
    Set circleObj = ThisDrawing.ModelSpace.AddCircle(centerPoint, radius1)
    ThisDrawing.Application.ZoomAll
    
    ' Copy objects
    '
    ' First put the objects to be copied into a form compatible with CopyObjects
    Set objCollection(0) = circleObj
    
    ' Copy object and get back a collection of the new objects (copies)
    retObjects = ThisDrawing.CopyObjects(objCollection, , IDPairs)
    
    ' Get newly created object and apply new properties to the copies
    Set circleObjCopy = retObjects(0)
    
    circleObjCopy.radius = radius1Copy
    circleObjCopy.Color = acRed
        
    ThisDrawing.Application.ZoomAll
    ThisDrawing.Regen acAllViewports
    
    ' Display whether the first source object has a clone
    IsClonedState = IIf(IDPairs(0).IsCloned, "is cloned.", "is not cloned.")
    IsPrimary = IIf(IDPairs(0).IsPrimary, "is a primary member of the objects being copied.", "is owned by a primary member of the objects being copied.")
    IsXLated = IIf(IDPairs(0).IsOwnerXlated, "has been translated.", "has not been translated.")
    
    MsgBox "The new Circle source object: " & IsClonedState & vbCrLf & _
           "The new Circle source object: " & IsPrimary & vbCrLf & _
           "The source of the new Circle object: " & IsXLated & vbCrLf, vbInformation

End Sub
Sub Example_ISOPenWidth()
    ' This example creates an associative hatch in model space.
    ' The ISOPenWidth of the hatch pattern is then returned and changed.
    
    Dim hatchObj As AcadHatch
    Dim patternName As String, PatternType As Long
    Dim bAssociativity As Boolean
    Dim outerLoop(0 To 1) As Object
    Dim center(0 To 2) As Double
    Dim radius As Double, startAngle As Double, endAngle As Double
    Dim innerLoop1(0) As Object, innerLoop2(0) As Object
    Dim PatternScale As Double

    ' Define the hatch
    patternName = "ANSI31": PatternType = 0: bAssociativity = True
    
    ' Create the associative Hatch object
    Set hatchObj = ThisDrawing.ModelSpace.AddHatch(PatternType, patternName, bAssociativity)
   
    ' Create the outer loop for the hatch.
    ' An arc and a line are used to create a closed loop.
    center(0) = 5: center(1) = 3: center(2) = 0
    radius = 3:  startAngle = 0:  endAngle = 3.141592
    
    Set outerLoop(0) = ThisDrawing.ModelSpace.AddArc(center, radius, startAngle, endAngle)
    Set outerLoop(1) = ThisDrawing.ModelSpace.AddLine(outerLoop(0).startPoint, outerLoop(0).endPoint)
        
    ' Append the outer loop to the hatch object
    hatchObj.AppendOuterLoop (outerLoop)
    
    ' Append the first circle as one inner loop
    center(0) = 5: center(1) = 4.5: center(2) = 0
    radius = 1
    
    Set innerLoop1(0) = ThisDrawing.ModelSpace.AddCircle(center, radius)
    hatchObj.AppendInnerLoop (innerLoop1)
    
    ' Append the second circle as the other inner loop
    radius = 0.5
    Set innerLoop2(0) = ThisDrawing.ModelSpace.AddCircle(center, radius)
    hatchObj.AppendInnerLoop (innerLoop2)
    
    ' Evaluate and display the hatch
    hatchObj.Evaluate
    ThisDrawing.Regen True
    
    ' Find the ISO pen width of the hatch pattern
    MsgBox "The ISO pen width of the hatch pattern is: " & hatchObj.ISOPenWidth, vbInformation

    ' Change the ISO pen width of the hatch pattern
    hatchObj.ISOPenWidth = acPenWidth050
    hatchObj.Evaluate
    ThisDrawing.Regen True
    
    ' Display new pen width for this hatch
    If hatchObj.ISOPenWidth = acPenWidthUnk Then
        ' Non-Standard pen widths
        MsgBox "The ISO pen width of the hatch pattern is now: " & hatchObj.PatternScale, vbInformation
    Else
        ' Standard pen widths
        MsgBox "The ISO pen width of the hatch pattern is now: " & hatchObj.ISOPenWidth, vbInformation
    End If

End Sub
Sub Example_LinearScaleFactor()
   ' This example creates an aligned dimension in model space and
   ' turns on the tolerance display for the new dimension.  The LinearScaleFactor
   ' of the tolerance is then read and modified.
   '
   ' * Note the change in the text of the dimension after the modification.

    Dim dimObj As AcadDimAligned
    Dim newText As AcadTextStyle
    Dim point1(0 To 2) As Double, point2(0 To 2) As Double
    Dim location(0 To 2) As Double
    Dim CurrentScale As Integer
    
    ' Define the dimension
    point1(0) = 1: point1(1) = 10: point1(2) = 0
    point2(0) = 10: point2(1) = 10: point2(2) = 0
    location(0) = 5: location(1) = 7: location(2) = 0
    
    ' Create an aligned dimension object in model space
    Set dimObj = ThisDrawing.ModelSpace.AddDimAligned(point1, point2, location)
    
    ' Turn on the tolerance display
    dimObj.ToleranceDisplay = acTolSymmetrical
    ThisDrawing.Application.ZoomAll
    
    ' Display current scale factor
    MsgBox dimObj.LinearScaleFactor

    ' Change current scale factor
    dimObj.LinearScaleFactor = 10#      ' Multiply by ten
    ThisDrawing.Regen acAllViewports

    ' Display new scale factor
    MsgBox dimObj.LinearScaleFactor
End Sub
Sub Example_PrimaryUnitsPrecision()
   ' This example creates an aligned dimension in model space and
   ' uses PrimaryUnitsPrecision to allow the user to change
   ' the number of decimal places displayed for the primary units and tolerance
   ' units of the dimension.

    Dim dimObj As AcadDimAligned
    Dim point1(0 To 2) As Double, point2(0 To 2) As Double
    Dim location(0 To 2) As Double
    Dim oldPrecision As String, newPrecision As String
    
    ' Define the dimension
    point1(0) = 0: point1(1) = 5: point1(2) = 0
    point2(0) = 5.12345678: point2(1) = 5: point2(2) = 0
    location(0) = 5: location(1) = 7: location(2) = 0
    
    ' Create an aligned dimension object in model space
    Set dimObj = ThisDrawing.ModelSpace.AddDimAligned(point1, point2, location)
    
    ' Enable and setup tolerance display
    dimObj.ToleranceDisplay = acTolSymmetrical
    dimObj.ToleranceLowerLimit = -0.0001
    dimObj.ToleranceUpperLimit = 0.005
    
    ThisDrawing.Application.ZoomAll

    ' Store old precision value as default for input box
    oldPrecision = dimObj.PrimaryUnitsPrecision
    
    ' Allow the user to change the precision for the dimension and dimension tolerance
    newPrecision = InputBox("Enter a new precision for the dimension and tolerances.  The value must range from 0 to 8.", "Change Precision", oldPrecision)
    
    Select Case newPrecision
        Case 0: newPrecision = acDimPrecisionZero
        Case 1: newPrecision = acDimPrecisionOne
        Case 2: newPrecision = acDimPrecisionTwo
        Case 3: newPrecision = acDimPrecisionThree
        Case 4: newPrecision = acDimPrecisionFour
        Case 5: newPrecision = acDimPrecisionFive
        Case 6: newPrecision = acDimPrecisionSix
        Case 7: newPrecision = acDimPrecisionSeven
        Case 8: newPrecision = acDimPrecisionEight
        Case Else
            MsgBox "The precision has not been changed."
            Exit Sub
    End Select
    
    ' Change the dimension and tolerance precision
    dimObj.TolerancePrecision = newPrecision
    dimObj.PrimaryUnitsPrecision = newPrecision
    
    ThisDrawing.Regen acAllViewports
    
    ' Read back and display the dimension and dimension tolerance precision
    newPrecision = dimObj.PrimaryUnitsPrecision
    MsgBox "The precision has been set to " & newPrecision & " decimal places"
End Sub
Sub Example_Preset()
    ' This example creates a block containing an attribute definition.
    ' Initially, the attribute has the preset flag turned on and will display a preset
    ' value for the attribute when the parent block is inserted as a reference.
    '
    ' Everytime the example is run, we attempt to find our attribute and
    ' toggle the Preset value.
    '
    ' * Note: After running this example for the first time, select the menu "Insert/Block..."
    ' and create a block reference from "Block-PRESET".  You will see
    ' the preset value appear for the attribute when the blockref appears.
    '
    ' Then run the example again and repeat the block insert.  Notice this time that the
    ' preset has been turned off and you are now prompted for the attribute value.
    
    Dim attributeObj As AcadAttribute
    Dim height As Double, mode As Long, prompt As String, tag As String, value As String
    Dim AttrInsertionPoint(0 To 2) As Double
    Dim BlockInsertionPoint(0 To 2) As Double
    Dim newBlock As AcadBlock
    Dim IsPreset As String
    
    ' See if we have already created this Block.  If so, get hold of the Block and
    ' the attribute inside, otherwise create a new block containing an
    ' attribute.
    On Error Resume Next
    
    Set newBlock = ThisDrawing.Blocks("Block-PRESET")
    
    
    If Err = 0 Then         ' We have created our example block
        Set attributeObj = newBlock.Item(0)                 ' Get only object in example block
    
        attributeObj.Preset = Not (attributeObj.Preset)     ' Toggle the attribute preset value
    
    ElseIf Err <> 0 Then    ' We have not created our example block
    
        ' Create a new block to hold the Attribute object
        BlockInsertionPoint(0) = 0: BlockInsertionPoint(1) = 0: BlockInsertionPoint(2) = 0
        Set newBlock = ThisDrawing.Blocks.Add(BlockInsertionPoint, "Block-PRESET")
    
        ' Define the attribute definition
        AttrInsertionPoint(0) = 0: AttrInsertionPoint(1) = 0: AttrInsertionPoint(2) = 0
        height = 1#:
        mode = acAttributeModePreset
        prompt = "New Prompt"
        tag = "New Tag": value = "Preset"
        
        ' Add attribute definition object to new Block
        Set attributeObj = newBlock.AddAttribute(height, mode, prompt, AttrInsertionPoint, tag, value)
    
    End If
    
    On Error GoTo 0

    ' Read the attribute back and dislay information
    IsPreset = IIf(attributeObj.Preset, "has a preset value of: " & attributeObj.textString, _
                   "does not have a preset value")
                   
    MsgBox "The block attribute " & IsPreset, vbInformation
End Sub

Sub Example_TabOrder()
    ' This example creates two new Layouts, sets the TabOrder of the Layouts to be
    ' in alphabetic order and displays a list of Layouts in the order they appear
    ' in the tabs.
    
    Dim Layout1 As ACADLayout, Layout2 As ACADLayout
    Dim SortLayoutRight As ACADLayout, SortLayoutLeft As ACADLayout
    Dim SortIt As New Collection
    Dim TabCount As Long, SortCount As Long, TabOrder As Long
    Dim TabName As String, SortText As String, msg As String
    Dim tempLayout As ACADLayout
    Dim AddedTab As Boolean
        
    ' Create new Layouts
    On Error Resume Next
    Set Layout1 = ThisDrawing.Layouts.Add("Z VIEW")
    Set Layout2 = ThisDrawing.Layouts.Add("A VIEW")
    On Error GoTo 0
    
    ' Alphabetize internally
    For TabCount = 0 To (ThisDrawing.Layouts.count - 1)
        AddedTab = False
        
        TabName = ThisDrawing.Layouts(TabCount).name
        
        If TabName = "Model" Then GoTo SKIP                 ' Skip modelspace
        
        If SortIt.count = 0 Then
            SortIt.Add TabName                              ' Add to beginning of list
        Else
            For SortCount = 1 To SortIt.count               ' Add to list by string
                SortText = SortIt(SortCount)
                If StrComp(TabName, SortText, vbTextCompare) = -1 Then
                    If SortCount = 1 Then
                        SortIt.Add TabName                  ' Add as first item
                    Else
                        SortIt.Add TabName, , SortCount     ' Add as previous item
                    End If
                    AddedTab = True
                    Exit For
                End If
            Next
            
            If Not (AddedTab) Then SortIt.Add TabName, , , SortIt.count  ' Add if we haven't yet
        End If
SKIP:
    Next
    
    ' Write new ACAD tab order
    For SortCount = 1 To SortIt.count
        Set tempLayout = ThisDrawing.Layouts(SortIt(SortCount))
        tempLayout.TabOrder = SortCount
    Next
    
    '-------------------------------
    ' Read and display New Tab Order
    '-------------------------------
    msg = "The tab order is now set to: " & vbCrLf & vbCrLf
    For TabCount = 0 To (ThisDrawing.Layouts.count - 1)
        TabName = ThisDrawing.Layouts(TabCount).name
        If TabName = "Model" Then GoTo SKIP2                ' Don't show modelspace
        TabOrder = ThisDrawing.Layouts(TabCount).TabOrder
        msg = msg & "(" & TabOrder & ")" & vbTab & TabName & vbCrLf
SKIP2:
    Next
    
    MsgBox msg, vbInformation

End Sub
Sub Example_ShortCutMenuDisplay()
    ' This example reads and toggles the preference value which controls
    ' whether right-clicking in the drawing area displays a shortcut menu
    ' or issues ENTER.
    
    Dim ACADPref As AcadPreferencesUser
    Dim originalValue As Variant, newValue As Variant
    Dim newAction As String
    
    ' Get the drafting preferences object
    Set ACADPref = ThisDrawing.Application.preferences.User
    
    ' Read and display the original value
    originalValue = ACADPref.ShortCutMenuDisplay
    newAction = IIf(originalValue, "displays the shortcut menu", "sends an ENTER keystroke to ACAD")
    MsgBox "Right-clicking the mouse CURRENTLY " & newAction, vbInformation

    ' Modify the AutoSnapMarker preference by toggling the value
    ACADPref.ShortCutMenuDisplay = Not (originalValue)
    newValue = ACADPref.ShortCutMenuDisplay
    newAction = IIf(newValue, "display the shortcut menu", "send an ENTER keystroke to ACAD")
    MsgBox "Right-clicking the mouse over the drawing WILL NOW " & newAction, vbInformation
End Sub
Sub Example_ViewToPlot()
    ' This example reads a list of available Named Views and displays a plot preview
    ' of the view selected by the user.  The current view to plot,
    ' if set, if preceded by an '*'
    '
    ' * Note: After previewing the plot, you will have to exit the
    ' plot preview before the VBA example will stop and control will be returned
    
    Dim ViewList As New Collection
    Dim View As AcadView
    Dim iCount As Long
    Dim msg As String
    Dim ViewName As String, ViewNum As String
    
    ' Get list of views available to plot
    For Each View In ThisDrawing.Views
        ViewList.Add View
    Next
    
    ' Are there any named views to plot
    If ViewList.count = 0 Then
        MsgBox "There are no named views to plot.", vbInformation
        Exit Sub
    End If
    
    ' Read and display the current plot style table path
    For iCount = 1 To ViewList.count
        ViewName = ViewList(iCount).name
        
        If ViewName = ThisDrawing.ActiveLayout.ViewToPlot Then  ' Is this the current view to plot
            ViewNum = iCount
            ViewName = "*" & ViewName
        End If
        
        msg = msg & "(" & iCount & ") " & vbTab & ViewName & vbCrLf
    Next
    
    ' Prompt user for the view to plot
RETRY:
    ViewNum = InputBox("Which view would you like to plot?" & vbCrLf & vbCrLf & msg, "View To Plot", ViewNum)
    
    If Trim(ViewNum) = "" Then
        Exit Sub
    End If
    
    If Not (IsNumeric(ViewNum)) Then
        MsgBox "You must supply a numeric value corresponding to one of the views listed above.", vbExclamation
        GoTo RETRY
    End If
    
    ' Tell the drawing which view to plot
    ThisDrawing.ActiveLayout.ViewToPlot = ViewList(CLng(ViewNum)).name
    
    ' Make sure we tell the drawing to plot a view, not some other plot style
    ThisDrawing.ActiveLayout.PlotType = acView
    
    ' Send Plot To Window
    ThisDrawing.Plot.DisplayPlotPreview acFullPreview
End Sub
Sub Example_SetWindowToPlot()
    ' This example allows the user to define an area in the current layout
    ' and displays a plot preview of the defined area.
    '
    ' * Note: After previewing the plot, you will have to exit the
    ' plot preview before the VBA example will stop and control will be returned
    
    Dim point1 As Variant, point2 As Variant
    
    ' Get first point in window
    point1 = ThisDrawing.Utility.GetPoint(, "Click the lower-left of the window to plot.")
    ReDim Preserve point1(0 To 1)   ' Change this to a 2D array by removing the Z position
    
    ' Get second point in window
    point2 = ThisDrawing.Utility.GetPoint(, "Click the upper-right of the window to plot.")
    ReDim Preserve point2(0 To 1)   ' Change this to a 2D array by removing the Z position
    
    ' Send information about window to current layout
    ThisDrawing.ActiveLayout.SetWindowToPlot point1, point2
    
    ' Read back window information
    ThisDrawing.ActiveLayout.GetWindowToPlot point1, point2
    
    MsgBox "Press any key to plot the following window:" & vbCrLf & vbCrLf & _
           "Lower Left: " & point1(0) & ", " & point1(1) & vbCrLf & _
           "Upper Right: " & point2(0) & ", " & point2(1)
    
    ' Make sure we tell the drawing to plot a view, not some other plot style
    ThisDrawing.ActiveLayout.PlotType = acWindow
    
    ' Send Plot To Window
    ThisDrawing.Plot.DisplayPlotPreview acFullPreview
End Sub
Sub Example_GetWindowToPlot()
    ' This example allows the user to define an area in the current layout
    ' and displays a plot preview of the defined area.
    '
    ' * Note: After previewing the plot, you will have to exit the
    ' plot preview before the VBA example will stop and control will be returned
    
    Dim point1 As Variant, point2 As Variant
    
    ' Get first point in window
    point1 = ThisDrawing.Utility.GetPoint(, "Click the lower-left of the window to plot.")
    ReDim Preserve point1(0 To 1)   ' Change this to a 2D array by removing the Z position
    
    ' Get second point in window
    point2 = ThisDrawing.Utility.GetPoint(, "Click the upper-right of the window to plot.")
    ReDim Preserve point2(0 To 1)   ' Change this to a 2D array by removing the Z position
    
    ' Send information about window to current layout
    ThisDrawing.ActiveLayout.SetWindowToPlot point1, point2
    
    ' Read back window information
    ThisDrawing.ActiveLayout.GetWindowToPlot point1, point2
    
    MsgBox "Press any key to plot the following window:" & vbCrLf & vbCrLf & _
           "Lower Left: " & point1(0) & ", " & point1(1) & vbCrLf & _
           "Upper Right: " & point2(0) & ", " & point2(1)
    
    ' Make sure we tell the drawing to plot a view, not some other plot style
    ThisDrawing.ActiveLayout.PlotType = acWindow
    
    ' Send Plot To Window
    ThisDrawing.Plot.DisplayPlotPreview acFullPreview
End Sub
Sub Example_SetXRecordData()
    ' This example creates a new XRecord if one doesn't exist,
    ' appends data to the XRecord and reads it back.  To see data being added
    ' run the example more than once.
    
    Dim TrackingDictionary As AcadDictionary, TrackingXRecord As AcadXRecord
    Dim XRecordDataType As Variant, XRecordData As Variant
    Dim ArraySize As Long, iCount As Long
    Dim DataType As Integer, Data As String, msg As String
    
    ' Unique identifiers to distinguish our XRecordData from other XRecordData
    Const TYPE_STRING = 1
    Const TAG_DICTIONARY_NAME = "ObjectTrackerDictionary"
    Const TAG_XRECORD_NAME = "ObjectTrackerXRecord"

    ' Connect to the dictionary we store the XRecord in
    On Error GoTo CREATE
    Set TrackingDictionary = ThisDrawing.Dictionaries(TAG_DICTIONARY_NAME)
    Set TrackingXRecord = TrackingDictionary.GetObject(TAG_XRECORD_NAME)
    On Error GoTo 0
    
    ' Get current XRecordData
    TrackingXRecord.GetXRecordData XRecordDataType, XRecordData
    
    ' If we don't have an array already then create one
    If VarType(XRecordDataType) And vbArray = vbArray Then
        ArraySize = UBound(XRecordDataType) + 1       ' Get the size of the data elements returned
        ArraySize = ArraySize + 1                        ' Increase to hold new data
    
        ReDim Preserve XRecordDataType(0 To ArraySize)
        ReDim Preserve XRecordData(0 To ArraySize)
    Else
        ArraySize = 0
        ReDim XRecordDataType(0 To ArraySize) As Integer
        ReDim XRecordData(0 To ArraySize) As Variant
    End If
    
    ' Append new XRecord Data
    '
    ' For this sample we only append the current time to the XRecord
    XRecordDataType(ArraySize) = TYPE_STRING: XRecordData(ArraySize) = CStr(Now)
    TrackingXRecord.SetXRecordData XRecordDataType, XRecordData
    
    ' Read back all XRecordData entries
    TrackingXRecord.GetXRecordData XRecordDataType, XRecordData
    ArraySize = UBound(XRecordDataType)
    
    ' Retrieve and display stored XRecordData
    For iCount = 0 To ArraySize
        ' Get information for this element
        DataType = XRecordDataType(iCount)
        Data = XRecordData(iCount)
        
        If DataType = TYPE_STRING Then
            msg = msg & Data & vbCrLf
        End If
    Next
    
    MsgBox "The data in the XRecord is: " & vbCrLf & vbCrLf & msg, vbInformation
    
    Exit Sub

CREATE:
    ' Create the entities that hold our XRecordData
    If TrackingDictionary Is Nothing Then  ' Make sure we have our tracking object
        Set TrackingDictionary = ThisDrawing.Dictionaries.Add(TAG_DICTIONARY_NAME)
        Set TrackingXRecord = TrackingDictionary.AddXRecord(TAG_XRECORD_NAME)
    End If
    
    Resume
End Sub
Sub Example_GetXRecordData()
    ' This example creates a new XRecord if one doesn't exist,
    ' appends data to the XRecord and reads it back.  To see data being added
    ' run the example more than once.
    
    Dim TrackingDictionary As AcadDictionary, TrackingXRecord As AcadXRecord
    Dim XRecordDataType As Variant, XRecordData As Variant
    Dim ArraySize As Long, iCount As Long
    Dim DataType As Integer, Data As String, msg As String
    
    ' Unique identifiers to distinguish our XRecordData from other XRecordData
    Const TYPE_STRING = 1
    Const TAG_DICTIONARY_NAME = "ObjectTrackerDictionary"
    Const TAG_XRECORD_NAME = "ObjectTrackerXRecord"

    ' Connect to the dictionary we store the XRecord in
    On Error GoTo CREATE
    Set TrackingDictionary = ThisDrawing.Dictionaries(TAG_DICTIONARY_NAME)
    Set TrackingXRecord = TrackingDictionary.GetObject(TAG_XRECORD_NAME)
    On Error GoTo 0
    
    ' Get current XRecordData
    TrackingXRecord.GetXRecordData XRecordDataType, XRecordData
    
    ' If we don't have an array already then create one
    If VarType(XRecordDataType) And vbArray = vbArray Then
        ArraySize = UBound(XRecordDataType) + 1       ' Get the size of the data elements returned
        ArraySize = ArraySize + 1                        ' Increase to hold new data
    
        ReDim Preserve XRecordDataType(0 To ArraySize)
        ReDim Preserve XRecordData(0 To ArraySize)
    Else
        ArraySize = 0
        ReDim XRecordDataType(0 To ArraySize) As Integer
        ReDim XRecordData(0 To ArraySize) As Variant
    End If
    
    ' Append new XRecord Data
    '
    ' For this sample we only append the current time to the XRecord
    XRecordDataType(ArraySize) = TYPE_STRING: XRecordData(ArraySize) = CStr(Now)
    TrackingXRecord.SetXRecordData XRecordDataType, XRecordData
    
    ' Read back all XRecordData entries
    TrackingXRecord.GetXRecordData XRecordDataType, XRecordData
    ArraySize = UBound(XRecordDataType)
    
    ' Retrieve and display stored XRecordData
    For iCount = 0 To ArraySize
        ' Get information for this element
        DataType = XRecordDataType(iCount)
        Data = XRecordData(iCount)
        
        If DataType = TYPE_STRING Then
            msg = msg & Data & vbCrLf
        End If
    Next
    
    MsgBox "The data in the XRecord is: " & vbCrLf & vbCrLf & msg, vbInformation
    
    Exit Sub

CREATE:
    ' Create the entities that hold our XRecordData
    If TrackingDictionary Is Nothing Then  ' Make sure we have our tracking object
        Set TrackingDictionary = ThisDrawing.Dictionaries.Add(TAG_DICTIONARY_NAME)
        Set TrackingXRecord = TrackingDictionary.AddXRecord(TAG_XRECORD_NAME)
    End If
    
    Resume
End Sub
Sub Example_GetPaperSize()
    ' This example gets the width and hight of the default
    ' paper size for your system.
    
    Dim PaperWidth As Double
    Dim PaperHeight As Double
    
    ThisDrawing.ActiveLayout.GetPaperSize PaperWidth, PaperHeight
    
    MsgBox "The default paper size is " & vbCrLf & _
            "Width: " & PaperWidth & vbCrLf & _
            "Height: " & PaperHeight

End Sub
Sub Example_ArrowHeadBlock()
    ' This example creates a radial dimension object in model space
    ' and then alters the visible appearance (shape) of the arrow head
    ' using the ArrowHeadBlock property.
    ' We'll use the ArrowHeadBlock property to set the arrow head to an existing
    ' block object containing a custom Circle object

    Dim dimObj As AcadDimRadial
    Dim center(0 To 2) As Double
    Dim chordPoint(0 To 2) As Double
    Dim leaderLen As Integer
    Dim BlockName As String
    
    ' Define the dimension
    center(0) = 0#: center(1) = 0#: center(2) = 0#
    chordPoint(0) = 5#: chordPoint(1) = 5#: chordPoint(2) = 0#
    leaderLen = 5
    
    ' Create the radial dimension in model space
    Set dimObj = ThisDrawing.ModelSpace.AddDimRadial(center, chordPoint, leaderLen)
    ZoomAll
    
    ' Set arrow head type to user-defined to allow
    ' the use of a block as the new arrow head
    'dimObj.ArrowheadType = acArrowUserDefined
    dimObj.ArrowheadBlock = "CBlock"
    ZoomAll
    
    ' Read and display current arrow head block name
    BlockName = dimObj.ArrowheadBlock
    
    MsgBox "The arrow head block name for this object is: " & BlockName
    
End Sub
Sub Example_GetCustomScale()
    ' This example will access the Layouts collection for the current drawing
    ' and list basic information about the custom scale for each Layout.
    ' It will then change the custom scale information for model space and re-display
    ' the scale information.

    Dim Layouts As AcadLayouts, Layout As ACADLayout
    Dim msg As String
    Dim Numerator As Double, Denominator As Double
    Dim Measurement As String
    
    ' Display current scale information
    GoSub DISPLAY_SCALE_INFO
    
    ' Modify scale
    Numerator = 1
    Denominator = 1
    
    ThisDrawing.Layouts("Model").SetCustomScale Numerator, Denominator
    ThisDrawing.Regen acAllViewports
            
    ' Display new scale information
    GoSub DISPLAY_SCALE_INFO
        
    Exit Sub
    
DISPLAY_SCALE_INFO:
    ' Get layouts collection from document object
    Set Layouts = ThisDrawing.Layouts
    
    msg = vbCrLf & vbCrLf   ' Start with a space
    
    ' Get the scale information of every layout in this drawing
    For Each Layout In Layouts
        msg = msg & Layout.name & vbCrLf
        
        ' Get scale information
        Layout.GetCustomScale Numerator, Denominator
        
        ' Are we using inches or millimeters
        Measurement = IIf(Layout.PaperUnits = acInches, " inch(es)", " millimeter(s)")
        
        ' Format for display
        msg = msg & vbTab & "Contains " & Numerator & Measurement & vbCrLf
        msg = msg & vbTab & "Contains " & Denominator & " drawing units" & vbCrLf
        msg = msg & "_____________________" & vbCrLf
        
    Next
    
    ' Display custom scale information
    MsgBox "Custom scale information for the current drawing is: " & msg
    
    Return
End Sub
Sub Example_SetCustomScale()
    ' This example will access the Layouts collection for the current drawing
    ' and list basic information about the custom scale for each Layout.
    ' It will then change the custom scale information for model space and re-display
    ' the scale information.

    Dim Layouts As AcadLayouts, Layout As ACADLayout
    Dim msg As String
    Dim Numerator As Double, Denominator As Double
    Dim Measurement As String
    
    ' Display current scale information
    GoSub DISPLAY_SCALE_INFO
    
    ' Modify scale
    Numerator = 1
    Denominator = 1
    
    ThisDrawing.Layouts("Model").SetCustomScale Numerator, Denominator
    ThisDrawing.Regen acAllViewports
            
    ' Display new scale information
    GoSub DISPLAY_SCALE_INFO
        
    Exit Sub
    
DISPLAY_SCALE_INFO:
    ' Get layouts collection from document object
    Set Layouts = ThisDrawing.Layouts
    
    msg = vbCrLf & vbCrLf   ' Start with a space
    
    ' Get the scale information of every layout in this drawing
    For Each Layout In Layouts
        msg = msg & Layout.name & vbCrLf
        
        ' Get scale information
        Layout.GetCustomScale Numerator, Denominator
        
        ' Are we using inches or millimeters
        Measurement = IIf(Layout.PaperUnits = acInches, " inch(es)", " millimeter(s)")
        
        ' Format for display
        msg = msg & vbTab & "Contains " & Numerator & Measurement & vbCrLf
        msg = msg & vbTab & "Contains " & Denominator & " drawing units" & vbCrLf
        msg = msg & "_____________________" & vbCrLf
        
    Next
    
    ' Display custom scale information
    MsgBox "Custom scale information for the current drawing is: " & msg
    
    Return
End Sub
Sub Example_AddXRecord()
    ' This example creates a new XRecord if one doesn't exist,
    ' appends data to the XRecord and reads it back.  To see data being added
    ' run the example more than once.
    
    Dim TrackingDictionary As AcadDictionary, TrackingXRecord As AcadXRecord
    Dim XRecordDataType As Variant, XRecordData As Variant
    Dim ArraySize As Long, iCount As Long
    Dim DataType As Integer, Data As String, msg As String
    
    ' Unique identifiers to distinguish our XRecordData from other XRecordData
    Const TYPE_STRING = 1
    Const TAG_DICTIONARY_NAME = "ObjectTrackerDictionary"
    Const TAG_XRECORD_NAME = "ObjectTrackerXRecord"

    ' Connect to the dictionary we store the XRecord in
    On Error GoTo CREATE
    Set TrackingDictionary = ThisDrawing.Dictionaries(TAG_DICTIONARY_NAME)
    Set TrackingXRecord = TrackingDictionary.GetObject(TAG_XRECORD_NAME)
    On Error GoTo 0
    
    ' Get current XRecordData
    TrackingXRecord.GetXRecordData XRecordDataType, XRecordData
    
    ' If we don't have an array already then create one
    If VarType(XRecordDataType) And vbArray = vbArray Then
        ArraySize = UBound(XRecordDataType) + 1       ' Get the size of the data elements returned
        ArraySize = ArraySize + 1                        ' Increase to hold new data
    
        ReDim Preserve XRecordDataType(0 To ArraySize)
        ReDim Preserve XRecordData(0 To ArraySize)
    Else
        ArraySize = 0
        ReDim XRecordDataType(0 To ArraySize) As Integer
        ReDim XRecordData(0 To ArraySize) As Variant
    End If
    
    ' Append new XRecord Data
    '
    ' For this sample we only append the current time to the XRecord
    XRecordDataType(ArraySize) = TYPE_STRING: XRecordData(ArraySize) = CStr(Now)
    TrackingXRecord.SetXRecordData XRecordDataType, XRecordData
    
    ' Read back all XRecordData entries
    TrackingXRecord.GetXRecordData XRecordDataType, XRecordData
    ArraySize = UBound(XRecordDataType)
    
    ' Retrieve and display stored XRecordData
    For iCount = 0 To ArraySize
        ' Get information for this element
        DataType = XRecordDataType(iCount)
        Data = XRecordData(iCount)
        
        If DataType = TYPE_STRING Then
            msg = msg & Data & vbCrLf
        End If
    Next
    
    MsgBox "The data in the XRecord is: " & vbCrLf & vbCrLf & msg, vbInformation
    
    Exit Sub

CREATE:
    ' Create the entities that hold our XRecordData
    If TrackingDictionary Is Nothing Then  ' Make sure we have our tracking object
        Set TrackingDictionary = ThisDrawing.Dictionaries.Add(TAG_DICTIONARY_NAME)
        Set TrackingXRecord = TrackingDictionary.AddXRecord(TAG_XRECORD_NAME)
    End If
    
    Resume
End Sub
Sub Example_TranslateIDs()
    ' This example creates a new XRecord if one doesn't exist,
    ' and toggles the setting for TranslateIDs
    
    Dim TrackingDictionary As AcadDictionary, TrackingXRecord As AcadXRecord
    Dim XRecordDataType As Variant, XRecordData As Variant
    Dim ArraySize As Long, iCount As Long
    Dim DataType As Integer, Data As String, msg As String
    
    ' Unique identifiers to distinguish our XRecordData from other XRecordData
    Const TYPE_STRING = 1
    Const TAG_DICTIONARY_NAME = "ObjectTrackerDictionary"
    Const TAG_XRECORD_NAME = "ObjectTrackerXRecord"

    ' Connect to the dictionary we store the XRecord in
    On Error GoTo CREATE
    Set TrackingDictionary = ThisDrawing.Dictionaries(TAG_DICTIONARY_NAME)
    Set TrackingXRecord = TrackingDictionary.GetObject(TAG_XRECORD_NAME)
    On Error GoTo 0
    
    ' Get current XRecordData
    TrackingXRecord.GetXRecordData XRecordDataType, XRecordData
    
    ' If we don't have an array already then create one
    If VarType(XRecordDataType) And vbArray = vbArray Then
        ArraySize = UBound(XRecordDataType) + 1       ' Get the size of the data elements returned
        ArraySize = ArraySize + 1                        ' Increase to hold new data
    
        ReDim Preserve XRecordDataType(0 To ArraySize)
        ReDim Preserve XRecordData(0 To ArraySize)
    Else
        ArraySize = 0
        ReDim XRecordDataType(0 To ArraySize) As Integer
        ReDim XRecordData(0 To ArraySize) As Variant
    End If
    
    ' Find the current value of TranslateIDs
    Dim currXlate As Boolean
    currXlate = TrackingXRecord.TranslateIDs
    MsgBox "The current setting of the TranslateIDs is " & currXlate
    
    ' Toggle the setting
    TrackingXRecord.TranslateIDs = Not currXlate
    MsgBox "The new setting for the TranslateIDs is " & TrackingXRecord.TranslateIDs
    
    ' Reset the value
    TrackingXRecord.TranslateIDs = currXlate
    MsgBox "TranslateIDs has been reset to " & TrackingXRecord.TranslateIDs
    
    Exit Sub

CREATE:
    ' Create the entities that hold our XRecordData
    If TrackingDictionary Is Nothing Then  ' Make sure we have our tracking object
        Set TrackingDictionary = ThisDrawing.Dictionaries.Add(TAG_DICTIONARY_NAME)
        Set TrackingXRecord = TrackingDictionary.AddXRecord(TAG_XRECORD_NAME)
    End If
    
    Resume
End Sub
Sub Example_ArrowHead1Block()
    ' This example creates an aligned dimension object in model space
    ' and then alters the visible appearance (shape) of the arrow head
    ' using the ArrowHeadBlock property.
    ' We'll use the ArrowHeadBlock property to set the arrow head to an existing
    ' block object containing a custom Circle object

    Dim DimPointAngularObj As AcadDim3PointAngular
    Dim AngleVertex(0 To 2) As Double
    Dim FirstPoint(0 To 2) As Double, SecondPoint(0 To 2) As Double
    Dim TextPoint(0 To 2) As Double
    Dim BlockName As String
   
    ' Define the new Dim3PointAngular object
    AngleVertex(0) = 0: AngleVertex(1) = 0: AngleVertex(2) = 0
    FirstPoint(0) = 2: FirstPoint(1) = 2: FirstPoint(2) = 0
    SecondPoint(0) = 1: SecondPoint(1) = 4: SecondPoint(2) = 0
    TextPoint(0) = 6: TextPoint(1) = 6: TextPoint(2) = 0

    ' Create the new Dim3PointAngular object in model space
    Set DimPointAngularObj = ThisDrawing.ModelSpace.AddDim3PointAngular(AngleVertex, FirstPoint, SecondPoint, TextPoint)
    ZoomAll
    
    ' Set arrow head type to user-defined to allow
    ' the use of a block as the new arrow head
    'dimObj.ArrowheadType = acArrowUserDefined
    DimPointAngularObj.Arrowhead1Block = "CBlock"
    DimPointAngularObj.Arrowhead2Block = "CBlock"
    ZoomAll
    
    ' Read and display current arrow head block name
    BlockName = DimPointAngularObj.Arrowhead1Block
    
    MsgBox "The arrow head block name for this object is: " & BlockName
    
End Sub
Sub Example_ArrowHead2Block()
    ' This example creates an aligned dimension object in model space
    ' and then alters the visible appearance (shape) of the arrow head
    ' using the ArrowHeadBlock property.
    ' We'll use the ArrowHeadBlock property to set the arrow head to an existing
    ' block object containing a custom Circle object

    Dim DimPointAngularObj As AcadDim3PointAngular
    Dim AngleVertex(0 To 2) As Double
    Dim FirstPoint(0 To 2) As Double, SecondPoint(0 To 2) As Double
    Dim TextPoint(0 To 2) As Double
    Dim BlockName As String
   
    ' Define the new Dim3PointAngular object
    AngleVertex(0) = 0: AngleVertex(1) = 0: AngleVertex(2) = 0
    FirstPoint(0) = 2: FirstPoint(1) = 2: FirstPoint(2) = 0
    SecondPoint(0) = 1: SecondPoint(1) = 4: SecondPoint(2) = 0
    TextPoint(0) = 6: TextPoint(1) = 6: TextPoint(2) = 0

    ' Create the new Dim3PointAngular object in model space
    Set DimPointAngularObj = ThisDrawing.ModelSpace.AddDim3PointAngular(AngleVertex, FirstPoint, SecondPoint, TextPoint)
    ZoomAll
    
    ' Set arrow head type to user-defined to allow
    ' the use of a block as the new arrow head
    'dimObj.ArrowheadType = acArrowUserDefined
    DimPointAngularObj.Arrowhead1Block = "CBlock"
    DimPointAngularObj.Arrowhead2Block = "CBlock"
    ZoomAll
    
    ' Read and display current arrow head block name
    BlockName = DimPointAngularObj.Arrowhead2Block
    
    MsgBox "The arrow head block name for this object is: " & BlockName
    
End Sub
Sub Example_CenterPlot()
    ' This example will access the Layouts collection for the current drawing
    ' and display whether the plot for this layout is to be centered on the media.
    ' It will then toggle the state of CenterPlot for "Layout1" and re-display the
    ' CenterPlot state for each Layout.

    Dim Layouts As AcadLayouts, Layout As ACADLayout
    Dim msg As String
    Dim IsCentered As String
    
    ' Get layouts collection from document object
    Set Layouts = ThisDrawing.Layouts
    
    ' Display current layout information
    GoSub DISPLAY
    
    ' Toggle centered state for Layout1
    Layouts("Layout1").PlotType = acDisplay
    Layouts("Layout1").CenterPlot = Not (Layouts("Layout1").CenterPlot)
    ThisDrawing.Regen acAllViewports
    
    ' Display new layout information
    GoSub DISPLAY
    
    Exit Sub
    
DISPLAY:
    msg = ""    ' Clear message
    
    ' Determine whether this layout is centered on the media during a plot
    For Each Layout In Layouts
        IsCentered = IIf(Layout.CenterPlot, " are centered ", " are not centered ")
        
        ' Format for display
        msg = msg & "Objects for " & Layout.name & IsCentered & "on the media during a plot." & vbCrLf
    Next
    
    ' Display layout information
    MsgBox msg
    
    Return
End Sub
Sub Example_CustomScale()
   ' This example adds a line in paper space, creates a new PViewport in
   ' paper space, and cycles through some common paper space custom scale sizes
   ' for the new PViewport
   
    Dim lineObj As AcadLine
    Dim PViewPort As AcadPViewport
    Dim startPoint(0 To 2) As Double, endPoint(0 To 2)  As Double
    Dim center(0 To 2) As Double
    Dim width As Double, height As Double
    
    ' Define the start and end points for the line
    startPoint(0) = 1: startPoint(1) = 1: startPoint(2) = 0
    endPoint(0) = 5: endPoint(1) = 5: endPoint(2) = 0
    
    ' Define the PViewport
    center(0) = 3: center(1) = 3: center(2) = 0
    width = 40: height = 40
    
    ' Create the line in paper space
    Set lineObj = ThisDrawing.PaperSpace.AddLine(startPoint, endPoint)
       
    ' Create the PViewport
    Set PViewPort = ThisDrawing.PaperSpace.AddPViewport(center, width, height)
   
    ' Set PViewport scale to custom so we can modify the scale
    PViewPort.StandardScale = acVpCustomScale
    
    ' Change from model space to paperspace
    ThisDrawing.ActiveSpace = acPaperSpace
    
    ' Read and display the existing PViewport scale setting
    MsgBox "The scale of the new PViewport is: " & PViewPort.CustomScale
    
    ' Change the custom scale setting to 1:10 scale
    PViewPort.CustomScale = 0.1
   
    ' Read and display the new PViewport scale setting
    MsgBox "The scale of the new PViewport has been changed to: " & PViewPort.CustomScale

End Sub
Sub Example_Fit()
    ' This example creates an aligned dimension in model space
    ' and cycles the text fit of the dimension to a couple of common values
    
    Dim dimObj As AcadDimAligned
    Dim point1(0 To 2) As Double, point2(0 To 2) As Double
    Dim location(0 To 2) As Double
    Dim CurrentFit As String
    
    ' Define the dimension
    point1(0) = 5: point1(1) = 5: point1(2) = 0
    point2(0) = 6: point2(1) = 5: point2(2) = 0
    location(0) = 5: location(1) = 7: location(2) = 0
    
    ' Create an aligned dimension object in model space
    Set dimObj = ThisDrawing.ModelSpace.AddDimAligned(point1, point2, location)
    ThisDrawing.Application.ZoomAll
    
    ' Read and display current dimension line fit information
    Select Case dimObj.Fit
        Case acTextAndArrows:   CurrentFit = "Text and Arrows"
        Case acArrowsOnly:      CurrentFit = "Arrows Only"
        Case acTextOnly:        CurrentFit = "Text Only"
        Case acBestFit:         CurrentFit = "Best Fit"
    End Select
    
    MsgBox "The current dimension fit is set to: " & CurrentFit

    ' Change the fit to arrows only
    dimObj.Fit = acArrowsOnly
    ThisDrawing.Regen acAllViewports
    MsgBox "The dimension fit has been changed to arrows only"
    
    ' Change the fit to text only
    dimObj.Fit = acTextOnly
    ThisDrawing.Regen acAllViewports
    MsgBox "The dimension fit has been changed to text only"
    
End Sub
Sub Example_GetPaperMargins()
    ' This example will access the Layouts collection for the current drawing
    ' and list the plot size based on the margins returned from the GetPaperMargins
    ' property for each Layout except model space.
    Dim Layouts As AcadLayouts, Layout As ACADLayout
    Dim msg As String
    Dim Measurement As String
    Dim MarginLowerLeft As Variant, MarginUpperRight As Variant

    Dim PaperHeight As Double, PaperWidth As Double
    Dim PlotHeight As Double, PlotWidth As Double
    
    ' Get layouts collection from document object
    Set Layouts = ThisDrawing.Layouts
    
    msg = vbCrLf & vbCrLf   ' Start with a space
    
    ' Get the margin information of every layout in this drawing

    For Each Layout In Layouts
        ' Skip model space
        If Layout.name = "Model" Then GoTo NEXT_LAYOUT
        ThisDrawing.ActiveLayout = Layout
        
        msg = msg & Layout.name & vbCrLf
        
        ' Get paper size and margin information
        Layout.GetPaperMargins MarginLowerLeft, MarginUpperRight
        Layout.GetPaperSize PaperWidth, PaperHeight
        
        ' Do plot area calculations

        PlotWidth = PaperWidth - (MarginUpperRight(0) & MarginLowerLeft(0))
        PlotHeight = PaperHeight - (MarginUpperRight(1) - MarginLowerLeft(1))
        
        ' Are we using inches or millimeters
        Measurement = " millimeter(s)"
        
        ' Format for display
        msg = msg & vbTab & "The paper size for this layout is: " & PaperWidth & " X " & PaperHeight & Measurement & vbCrLf & vbCrLf

        msg = msg & vbTab & "The paper margins are: " & vbCrLf & _
                            vbTab & vbTab & "Left" & vbTab & "(" & MarginLowerLeft(0) & ")" & Measurement & vbCrLf & _
                            vbTab & vbTab & "Right" & vbTab & "(" & MarginUpperRight(0) & ")" & Measurement & vbCrLf & _
                            vbTab & vbTab & "Top" & vbTab & "(" & MarginUpperRight(1) & ")" & Measurement & vbCrLf & _
                            vbTab & vbTab & "Bottom" & vbTab & "(" & MarginLowerLeft(1) & ")" & Measurement & vbCrLf & vbCrLf
        msg = msg & vbTab & "The paper plot area for this layout is: " & PlotWidth & " X " & PlotHeight & Measurement & vbCrLf

        msg = msg & "_____________________" & vbCrLf
        
NEXT_LAYOUT:
    Next
    
    ' Display paper size and margin information
    MsgBox "Paper plot information for the current drawing is: " & msg
End Sub

Sub Example_Knots()
   ' This example creates a Spline object in model space and
   ' returns the knot vector for the new Spline

    Dim splineObj As AcadSpline
    Dim startTan(0 To 2) As Double, endTan(0 To 2) As Double
    Dim fitPoints(0 To 8) As Double
    Dim knotVector As Variant

    ' Define the Spline object
    startTan(0) = 0.5: startTan(1) = 0.5: startTan(2) = 0
    endTan(0) = 0.5: endTan(1) = 0.5: endTan(2) = 0
    fitPoints(0) = 0: fitPoints(1) = 0: fitPoints(2) = 0: fitPoints(3) = 5
    fitPoints(4) = 5: fitPoints(5) = 0: fitPoints(6) = 10: fitPoints(7) = 0: fitPoints(8) = 0
    
    ' Create new Spline object
    Set splineObj = ThisDrawing.ModelSpace.AddSpline(fitPoints, startTan, endTan)
    ThisDrawing.Application.ZoomAll
    
    ' Display the knot vector of the new Spline
    knotVector = splineObj.Knots
    MsgBox "The knot vector of the new Spline is: " & vbCrLf & _
                                            knotVector(0) & vbCrLf & _
                                            knotVector(1) & vbCrLf & _
                                            knotVector(2)
End Sub
Sub Example_TextOutsideAlign()
   ' This example creates an aligned dimension in model space and
   ' allows the user to toggle the TextOutsideAlign value for the dimension

    Dim dimObj As AcadDimAligned
    Dim point1(0 To 2) As Double, point2(0 To 2) As Double
    Dim location(0 To 2) As Double
    
    ' Define the dimension
    point1(0) = 5: point1(1) = 5: point1(2) = 0
    point2(0) = 5.5: point2(1) = 5.5: point2(2) = 0
    location(0) = 5: location(1) = 7: location(2) = 0
    
    ' Create an aligned dimension object in model space
    Set dimObj = ThisDrawing.ModelSpace.AddDimAligned(point1, point2, location)
    
    ThisDrawing.Application.ZoomAll

Toggle:
    Select Case MsgBox("Press OK to toggle the TextOutsideAlign value for this dimension", vbOKCancel)
        Case vbOK
            ' Toggle the TextOutsideAlign value for this dimension
            dimObj.TextOutsideAlign = Not (dimObj.TextOutsideAlign)
            dimObj.Update
            ThisDrawing.Regen acActiveViewport
            
            ' Read and display the new dimension TextOutsideAlign value
            MsgBox "TextOutsideAlign is currently set to: " & dimObj.TextOutsideAlign
            
        Case vbCancel
            Exit Sub
    End Select
    
    GoTo Toggle
   
End Sub
Sub Example_TextInsideAlign()
   ' This example creates an aligned dimension in model space and
   ' allows the user to toggle the TextInsideAlign value for the dimension

    Dim dimObj As AcadDimAligned
    Dim point1(0 To 2) As Double, point2(0 To 2) As Double
    Dim location(0 To 2) As Double
    
    ' Define the dimension
    point1(0) = 5: point1(1) = 5: point1(2) = 0
    point2(0) = 5.5: point2(1) = 6: point2(2) = 0
    location(0) = 5: location(1) = 7: location(2) = 0
    
    ' Create an aligned dimension object in model space
    Set dimObj = ThisDrawing.ModelSpace.AddDimAligned(point1, point2, location)
    
    dimObj.TextInside = True    ' The TextInsideAlign property will only work
                                ' when this property is active
    
    ThisDrawing.Application.ZoomAll

Toggle:
    Select Case MsgBox("Press OK to toggle the TextInsideAlign value for this dimension", vbOKCancel)
        Case vbOK
            ' Toggle the TextInsideAlign value for this dimension
            dimObj.TextInsideAlign = Not (dimObj.TextInsideAlign)
            ThisDrawing.Regen acAllViewports
            
            ' Read and display the new dimension TextInsideAlign value
            MsgBox "TextInsideAlign is currently set to: " & dimObj.TextInsideAlign
        
        Case vbCancel
            Exit Sub
    End Select
    
    GoTo Toggle
   
End Sub
Sub Example_PickfirstSelectionSet()
    ' This example lists all the objects in the pickfirst selection set.
    ' Before running this example, create some objects in the active
    ' drawing and select those objects. The objects currently selected
    ' in the active drawing will be returned in the pickfirst selection set.
            
    Dim pfSS As AcadSelectionSet
    Dim ssobject As AcadEntity
    Dim msg As String
    msg = vbCrLf
    
    Set pfSS = ThisDrawing.PickfirstSelectionSet
    For Each ssobject In pfSS
        msg = msg & vbCrLf & ssobject.ObjectName
    Next ssobject
    MsgBox "The Pickfirst selection set contains: " & msg
    
End Sub
Sub Example_Verify()
    ' This example creates an attribute definition in model space.
    ' It then sets the definition to be verify, and queries the mode.
    
    Dim attributeObj As AcadAttribute
    Dim height As Double
    Dim mode As Long
    Dim prompt As String
    Dim insertionPoint(0 To 2) As Double
    Dim tag As String
    Dim value As String
    
    ' Define the attribute definition
    height = 1#
    mode = acAttributeModeVerify
    prompt = "New Prompt"
    insertionPoint(0) = 5#: insertionPoint(1) = 5#: insertionPoint(2) = 0
    tag = "New Tag"
    value = "New Value"
    
    ' Create the attribute definition object in model space
    Set attributeObj = ThisDrawing.ModelSpace.AddAttribute(height, mode, prompt, insertionPoint, tag, value)
    ZoomAll
    
    ' Change the mode to be verify
    attributeObj.mode = acAttributeModeVerify
    attributeObj.Update
    
    ' Check to see if the attribute is set to verify
    MsgBox (IIf(attributeObj.Verify, "The attribute is set to verify", "The attribute is not set to verify"))
End Sub
Sub Example_ViewportOn()
    ' This example creates two new paperspace viewports.
    ' It then checks the status of the viewports.
    
    Dim pviewportObj1 As AcadPViewport
    Dim pviewportObj2 As AcadPViewport
    Dim center(0 To 2) As Double
    Dim width As Double
    Dim height As Double
    
    ' Define the pviewport
    center(0) = 3: center(1) = 3: center(2) = 0
    width = 10
    height = 10
    
    ' Change from model space to paperspace
    ThisDrawing.ActiveSpace = acPaperSpace
    
    ' Create the pviewports
    Set pviewportObj1 = ThisDrawing.PaperSpace.AddPViewport(center, width, height)
    center(0) = 8: center(1) = 8: center(2) = 0
    width = 10
    height = 10
    Set pviewportObj2 = ThisDrawing.PaperSpace.AddPViewport(center, width, height)
    
    ' Before making a pViewport active,
    ' the mspace property needs to be True
    pviewportObj1.DISPLAY (True)
    ThisDrawing.mspace = True
    ThisDrawing.ActivePViewport = pviewportObj1
    ThisDrawing.Regen acAllViewports
    
    MsgBox "pviewportObj1 is " & (IIf(pviewportObj1.ViewportOn, "on.", "not on.")) & vbCrLf & _
           "pviewportObj2 is " & (IIf(pviewportObj2.ViewportOn, "on.", "not on."))
    
    ' Now turn on pviewportObj2 as well
    pviewportObj2.DISPLAY (True)
    MsgBox "pviewportObj1 is " & (IIf(pviewportObj1.ViewportOn, "on.", "not on.")) & vbCrLf & _
           "pviewportObj2 is " & (IIf(pviewportObj2.ViewportOn, "on.", "not on."))
    
End Sub
Sub Example_DeleteConfiguration()
    ' This example creates a new viewport and splits
    ' the viewport into 4 windows.
    ' It then deletes the viewport configuration
    Dim oldViewport As AcadViewport
    Set oldViewport = ThisDrawing.ActiveViewport
       
    ' Create a new viewport and make it active
    Dim newViewport As AcadViewport
    Set newViewport = ThisDrawing.Viewports.Add("TESTVIEWPORT")
    ThisDrawing.ActiveViewport = newViewport
    
    ' Split the viewport in 4 windows
    newViewport.Split acViewport4
    
    ' Make the newly split viewport active
    ThisDrawing.ActiveViewport = newViewport
    MsgBox "The viewport configuration split into 4 windows."

    ' Delete the viewport configuration
    ThisDrawing.ActiveViewport = oldViewport
    ThisDrawing.Viewports.DeleteConfiguration ("TESTVIEWPORT")
    ThisDrawing.Regen acAllViewports
    MsgBox "The viewport configuration has been deleted."
End Sub
Sub Example_GetConstantAttributes()
    ' This example creates a constant attribute definition on a block.
    ' It then queries the block to return the attribute.
    
    ' Create the block to hold the attribute
    Dim blockObj As AcadBlock
    Dim insertionPnt(0 To 2) As Double
    insertionPnt(0) = 0#: insertionPnt(1) = 0#: insertionPnt(2) = 0#
    Set blockObj = ThisDrawing.Blocks.Add(insertionPnt, "New_Block")
    
    ' Define the attribute definition
    Dim attributeObj As AcadAttribute
    Dim height As Double
    Dim mode As Long
    Dim prompt As String
    Dim tag As String
    Dim value As String
    height = 1#
    mode = acAttributeModeConstant
    prompt = "Constant Prompt"
    insertionPnt(0) = 5#: insertionPnt(1) = 5#: insertionPnt(2) = 0#
    tag = "Constant Tag"
    value = "Constant Value"
    
    ' Create the attribute definition object on the block
    Set attributeObj = blockObj.AddAttribute(height, mode, prompt, insertionPnt, tag, value)
    ZoomAll
    
    ' Insert the block into the drawing
    Dim blockRefObj As AcadBlockReference
    insertionPnt(0) = 2#: insertionPnt(1) = 2#: insertionPnt(2) = 0
    Set blockRefObj = ThisDrawing.ModelSpace.InsertBlock(insertionPnt, "New_Block", 1#, 1#, 1#, 0)
    
    ' Get the constant attribute definition from the block
    Dim queryAttribute As Variant
    queryAttribute = blockRefObj.GetConstantAttributes
    
    Dim count As Integer
    count = UBound(queryAttribute) - LBound(queryAttribute)
    MsgBox "The block reference has " & count & " constant attributes."
End Sub
Sub Example_UCSPerViewport()
    ' This example creates a new paperspace viewport.
    ' It then finds the UCSPerViewport setting
    ' for that viewport.
    
    Dim pviewportObj As AcadPViewport
    Dim center(0 To 2) As Double
    Dim width As Double
    Dim height As Double
    
    ' Define the pviewport
    center(0) = 3: center(1) = 3: center(2) = 0
    width = 40
    height = 40
    
    ' Change from model space to paperspace
    ThisDrawing.ActiveSpace = acPaperSpace
    
    ' Create the pviewport
    Set pviewportObj = ThisDrawing.PaperSpace.AddPViewport(center, width, height)
    ThisDrawing.Regen acAllViewports
    
    ' Find the current setting of the UCSPerViewport property
    MsgBox "UCSPerViewport: " & pviewportObj.UCSPerViewport
End Sub
Sub Example_SubMenu()
    ' This example finds the menu used as the sub menu for the
    ' "Autodesk on the web" menu item in the Help menu.
    
    Dim acadMenuGroup As acadMenuGroup
    Set acadMenuGroup = ThisDrawing.Application.MenuGroups.Item("ACAD")
    
    Dim helpMenu As AcadPopupMenu
    Set helpMenu = acadMenuGroup.Menus.Item("&Help")
    
    Dim WebMenuItem As AcadPopupMenuItem
    Set WebMenuItem = helpMenu.Item(5)
        
    Dim subWebMenu As AcadPopupMenu
    Set subWebMenu = WebMenuItem.SubMenu
    
    MsgBox "The name of the submenu is " & subWebMenu.TagString
End Sub

Sub Example_ZoomPrevious()
    ' This example creates several objects in model space and
    ' then performs a variety of zooms on the drawing.
    
    ' Create a Ray object in model space
    Dim rayObj As AcadRay
    Dim basePoint(0 To 2) As Double
    Dim SecondPoint(0 To 2) As Double
    basePoint(0) = 3#: basePoint(1) = 3#: basePoint(2) = 0#
    SecondPoint(0) = 1#: SecondPoint(1) = 3#: SecondPoint(2) = 0#
    Set rayObj = ThisDrawing.ModelSpace.AddRay(basePoint, SecondPoint)
    
    ' Create a polyline object in model space
    Dim plineObj As AcadLWPolyline
    Dim points(0 To 5) As Double
    points(0) = 3: points(1) = 7
    points(2) = 9: points(3) = 2
    points(4) = 3: points(5) = 5
    Set plineObj = ThisDrawing.ModelSpace.AddLightWeightPolyline(points)
    plineObj.Closed = True

    ' Create a line object in model space
    Dim lineObj As AcadLine
    Dim startPoint(0 To 2) As Double
    Dim endPoint(0 To 2) As Double
    startPoint(0) = 0: startPoint(1) = 0: startPoint(2) = 0
    endPoint(0) = 2: endPoint(1) = 2: endPoint(2) = 0
    Set lineObj = ThisDrawing.ModelSpace.AddLine(startPoint, endPoint)
    
    ' Create a circle object in model space
    Dim circObj As AcadCircle
    Dim centerPt(0 To 2) As Double
    Dim radius As Double
    centerPt(0) = 20: centerPt(1) = 30: centerPt(2) = 0
    radius = 3
    Set circObj = ThisDrawing.ModelSpace.AddCircle(centerPt, radius)

    ' Create an ellipse object in model space
    Dim ellObj As AcadEllipse
    Dim majAxis(0 To 2) As Double
    Dim center(0 To 2) As Double
    Dim radRatio As Double
    center(0) = 5#: center(1) = 5#: center(2) = 0#
    majAxis(0) = 10: majAxis(1) = 20#: majAxis(2) = 0#
    radRatio = 0.3
    Set ellObj = ThisDrawing.ModelSpace.AddEllipse(center, majAxis, radRatio)

' ZoomAll
    MsgBox "Perform a ZoomAll"
    ZoomAll
        
' ZoomExtents
    MsgBox "Perform a ZoomExtents"
    ZoomExtents
    
' ZoomPickWindow
    MsgBox "Perform a ZoomPickWindow"
    ZoomPickWindow
    
' ZoomPrevious
    MsgBox "Perform a ZoomPrevious"
    ZoomPrevious
End Sub
Sub Example_GetAcadState()
    ' This example gets the acadState object and checks to see if
    ' AutoCAD is in a quiescent state.
    Dim State As AcadState
    Set State = GetAcadState
    If State.IsQuiescent Then
        MsgBox "AutoCAD is quiescent."
    Else
        MsgBox "AutoCAD is not quiescent."
    End If
End Sub
Sub Example_IsQuiescent()
    ' This example gets the acadState object and checks to see if
    ' AutoCAD is in a quiescent state.
    Dim State As AcadState
    Set State = GetAcadState
    If State.IsQuiescent Then
        MsgBox "AutoCAD is quiescent."
    Else
        MsgBox "AutoCAD is not quiescent."
    End If
End Sub
