Attribute VB_Name = "ErrorTest"
Attribute VB_Base = "0{8C870A19-75E6-11D2-99C9-00609761BD90}{8C8709F1-75E6-11D2-99C9-00609761BD90}"
Attribute VB_Creatable = False
Attribute VB_PredeclaredId = True
Attribute VB_Exposed = False
Attribute VB_TemplateDerived = False
Attribute VB_Customizable = False
Private Sub btnErrorTest_Click()
    ErrorTest1
End Sub

Private Sub btnOK_Click()
    Unload Me
End Sub

Attribute VB_Name = "Module1"
Public Sub ErrorTest1()
    Stop
    Dim FileName As String
    FileName = "c:\"
    
    On Error GoTo HandleErr         ' trigger the error handler
' the work goes here
    FileLen (FileName)              ' force an error
    
ExitHere:
    Exit Sub
    
HandleErr:
    Select Case Err.Number          ' check the error number returned
        Case 53
            MsgBox "File " & FileName & " not found.", _
             vbOKOnly + vbExclamation
             
        Case Else
            ' Call a generic last-ditch error handler
            Call HandleErrors
    End Select
    Resume ExitHere
End Sub

Private Sub HandleErrors()
    ' You could, of course, substitute your own text,
    ' rather than using Err.Description.
    MsgBox "Error " & Err.Number & ":" & _
            vbCrLf & Err.Description, _
            vbOKOnly + vbInformation
End Sub
