Attribute VB_Name = "Main"
'References:
'------------------------------------------
'Visual Basic for Applications
'AutoCAD 2000 Type Library
'OLE Automation
'Microsoft Forms (2.0) Object Library
'Microsoft Visual Basic (6.0) Extensibility
'------------------------------------------

Option Explicit

Public Sub AcadStartup()
On Error Resume Next

        Call funcLoadProject("C:\Program Files\AutoCAD 2000i\Tblocks.dvb", False)

End Sub

Public Function funcLoadProject(strProjNme As String, bUnLoad As Boolean, Optional strModNme As String = "")
On Error Resume Next
Dim ACADApp As AcadApplication
Set ACADApp = GetObject(, "AutoCAD.Application")


    If funcIsLoaded(strProjNme) = False Then
        ACADApp.LoadDVB strProjNme
        
        If strModNme <> "" Then
            ACADApp.RunMacro strModNme
        End If
        
        If bUnLoad = True Then
            ACADApp.UnloadDVB strProjNme
        End If
    End If

        Set ACADApp = Nothing
    
    'ACADApp.LoadDVB "D:\vba book\Bill's chapters\my documents\vba1\CoolStuf.DVB"
    'ACADApp.RunMacro "Module1.VeryNeat"
    'ACADApp.UnloadDVB "D:\vba book\Bill's chapters\my documents\vba1\CoolStuf.DVB"

End Function

Public Function funcIsLoaded(strProjPath As String) As Boolean
Dim objIDE As VBIDE.VBE
Dim strName As String
Dim intCnt As Integer
Dim blnLoaded As Boolean
Set objIDE = Application.VBE
  
  For intCnt = 1 To objIDE.VBProjects.Count
    strName = objIDE.VBProjects(intCnt).BuildFileName
    If StrComp(strProjPath, strName, vbTextCompare) = 0 Then
      funcIsLoaded = True
      Exit For
    End If
  Next intCnt
  
  funcIsLoaded = blnLoaded
  
End Function
