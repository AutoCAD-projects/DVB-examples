Attribute VB_Name = "Module1"


Sub Set1()

    Dim S1 As AcadSelectionSet
    Set S1 = ThisDrawing.SelectionSets.Add("S1")

End Sub

Sub Set2()

    Dim S2 As AcadSelectionSet
    Set S2 = ThisDrawing.SelectionSets.Item("S2")
    S2.Clear
    AppActivate ThisDrawing.Application.Caption
    S2.SelectOnScreen
    Dim Apoint As AcadPoint
    Dim Pnt(0 To 2) As Double
    Pnt(0) = 0#: Pnt(1) = 0#: Pnt(2) = 0#
    Set Apoint = ThisDrawing.ModelSpace.AddPoint(Pnt)
    Dim varApoint(0) As AcadPoint
    Set varApoint(0) = Apoint
    'S2.AddItems (varApoint)

    Dim MatchIt As Object
    Dim Ent As Object
    Set MatchIt = S2.Item(0)
    For Each Ent In S2
        If MatchIt.EntityType = Ent.EntityType And MatchIt.Layer <> Ent.Layer Then
            Ent.Layer = MatchIt.Layer
            Ent.Update
        End If
        My_Filter2 S2, Ent
    Next Ent

End Sub

' Version 1 of a selection set filter.
Sub My_Filter1(SS As AcadSelectionSet, ET As Object)
   Dim Ents() As Object
   Dim Ent As Object
   Dim I As Long
   I = 0
   For Each Ent In SS
      If Ent.EntityType <> ET.EntityType Then
         ReDim Preserve Ents(0 To I)
         Set Ents(I) = Ent
         I = I + 1
      End If
   Next Ent
   If I > 0 Then
      SS.RemoveItems (Ents)
   End If
End Sub


' Version 2 of a selection set filter
Sub My_Filter2(SS As AcadSelectionSet, ET As Object)
   Dim Ents(0) As Object
   Dim I As Long
   I = SS.Count
   While (I > 0)
      I = I - 1
      Set Ents(0) = SS.Item(I)
      If Ents(0).EntityType <> ET.EntityType Then
         SS.RemoveItems (Ents)
      End If
   Wend
End Sub

Sub first_last()

    Dim EntFirst, EntLast, MdlSpc As Object
    Set MdlSpc = ThisDrawing.ModelSpace
    Set EntFirst = MdlSpc.Item(0)
    I = MdlSpc.Count - 1
    Set EntLast = MdlSpc.Item(I)

End Sub

Sub Creat_Text()

    Dim MyObj As AcadText
    Dim IP(0 To 2) As Double
    IP(0) = 5#: IP(1) = 10#: IP(2) = 0#
    Set MyObj = ThisDrawing.ModelSpace.AddText("This is a test", IP, 0.2)
    ' Text object is created, and can now be updated to what we need
    MyObj.Rotation = D2R(90#) 'D2R defined below..
    MyObj.ObliqueAngle = D2R(22.5)   'Angles must be in radians
    ' The text object now exists in the drawing as desired.

End Sub
' The function D2R does not exist in the VBA library,
' you must create it as follows.
Function D2R(D As Double) As Double
   D2R = D * 3.14159265359 / 180#
End Function

Sub Circle_Fileter()

    Dim Ftyp(1) As Integer
    Dim Fval(1) As Variant
    Dim Filter1, Filter2 As Variant
    Ftyp(0) = 0: Fval(0) = "CIRCLE"
    Ftyp(1) = 40: Fval(1) = 5#
    Dim S1 As AcadSelectionSet
    Set S1 = ThisDrawing.SelectionSets.Item("S1")
    S1.Clear
    Filter1 = Ftyp: Filter2 = Fval
    S1.Select acSelectionSetAll, , , Filter1, Filter2


End Sub

Sub Circle_Filter1()

    Dim Ftyp1(2) As Integer: Dim Fvar1(2) As Variant
    Dim Filter1, Filter2 As Variant
    Ftyp1(0) = 0: Fvar1(0) = "CIRCLE"
    Ftyp1(1) = -4: Fvar1(1) = "<="
    Ftyp1(2) = 40: Fvar1(2) = 5#
    Filter1 = Ftyp1: Filter2 = Fvar1
    Dim S1 As AcadSelectionSet
    Set S1 = ThisDrawing.SelectionSets.Item("S1")
    S1.Clear
    S1.Select acSelectionSetAll, , , Filter1, Filter2

End Sub

Sub Filters()

    Dim Pnt(0 To 2) As Double
    Dim Ftyp(1) As Integer: Dim Fval(1) As Variant
    Dim Filter1, Filter2 As Variant
    Pnt(0) = 0#: Pnt(1) = 0#: Pnt(2) = 0#
    Ftyp(0) = -4: Fval(0) = ">=,>=,*"
    Ftyp(1) = 10: Fval(1) = Pnt
    Filter1 = Ftyp: Filter2 = Fval
    Dim S1 As AcadSelectionSet
    Set S1 = ThisDrawing.SelectionSets.Item("S1")
    S1.Clear
    S1.Select acSelectionSetAll, , , Filter1, Filter2

End Sub

Sub Arc_Filter()

    Dim Pnt1(0 To 2) As Double
    Dim Pnt2(0 To 2) As Double
    Dim Ftyp1(2) As Integer: Dim Fvar1(2) As Variant
    Dim Filter1, Filter2 As Variant
    Pnt1(0) = 0#: Pnt1(1) = 0#: Pnt1(2) = 0#
    Pnt2(0) = 15#: Pnt2(1) = 15#: Pnt2(2) = 0#
    Ftyp1(0) = 0: Fvar1(0) = "ARC"
    Ftyp1(1) = -4: Fvar1(1) = "<"
    Ftyp1(2) = 40: Fvar1(2) = 1#
    Filter1 = Ftyp1: Filter2 = Fvar1
    
    Dim S1 As AcadSelectionSet
    Set S1 = ThisDrawing.SelectionSets.Item("S1")
    S1.Clear
    
    S1.Select acSelectionSetWindow, Pnt1, Pnt2, Filter1, Filter2

End Sub

Sub More_Filters()


    Dim Ft(0) As Integer: Dim Fv(0) As Variant
    Ft(0) = 8: Fv(0) = "AA*,AB*"
    Filter1 = Ft: Filter2 = Fv
    
    Dim S1 As AcadSelectionSet
    Set S1 = ThisDrawing.SelectionSets.Item("S1")
    S1.Clear
    
    S1.Select acSelectionSetAll, , , Filter1, Filter2

End Sub

Sub cir_or_arc_filter()

    Dim Ftyp4(4) As Integer: Dim Fvar4(4) As Variant
    Ftyp4(0) = -4: Fvar4(0) = "<OR"
    Ftyp4(1) = 0: Fvar4(1) = "CIRCLE"
    Ftyp4(2) = 0: Fvar4(2) = "ARC"
    Ftyp4(3) = 0: Fvar4(3) = "ELLIPSE"
    Ftyp4(4) = -4: Fvar4(4) = "OR>"
    
    Filter1 = Ftyp4: Filter2 = Fvar4
    Dim S1 As AcadSelectionSet
    Set S1 = ThisDrawing.SelectionSets.Item("S1")
    S1.Clear
    S1.Select acSelectionSetAll, , , Filter1, Filter2


End Sub

Sub mor_filters1()

    Dim Ftyp14(14) As Integer
    Dim Fvar14(14) As Variant
    Ftyp14(0) = -4: Fvar14(0) = "<OR" 'Start the overall OR test
    Ftyp14(1) = -4: Fvar14(1) = "<AND" 'Start the AND test for ARC
    Ftyp14(2) = 0: Fvar14(2) = "ARC"
    Ftyp14(3) = 8: Fvar14(3) = "PART"
    Ftyp14(4) = -4: Fvar14(4) = "<="
    Ftyp14(5) = 40: Fvar14(5) = 1#
    Ftyp14(6) = -4: Fvar14(6) = "AND>"  'End the AND test for ARC
    Ftyp14(7) = -4: Fvar14(7) = "<AND"  'Start the AND test for CIRCLE
    Ftyp14(8) = 0: Fvar14(8) = "CIRCLE"
    Ftyp14(9) = -4: Fvar14(9) = ">="
    Ftyp14(10) = 40: Fvar14(10) = 0.25
    Ftyp14(11) = -4: Fvar14(11) = "<="
    Ftyp14(12) = 40: Fvar14(12) = 0.75
    Ftyp14(13) = -4: Fvar14(13) = "AND>" 'End the AND test for CIRCLE
    Ftyp14(14) = -4: Fvar14(14) = "OR>" 'End the overall OR test

    Filter1 = Ftyp14: Filter2 = Fvar14
    Dim S1 As AcadSelectionSet
    Set S1 = ThisDrawing.SelectionSets.Item("S1")
    S1.Clear
    S1.Select acSelectionSetAll, , , Filter1, Filter2

End Sub

Function SS_Create() As AcadSelectionSet
  Dim SS1 As Double
  Do
    SS1 = ThisDrawing.GetVariable("DATE")
    S$ = "SS" & Str$(Fix(1000000# * (SS1 - Fix(SS1))))
    Err.Clear
    On Error Resume Next
    Set SS_Create = ThisDrawing.SelectionSets.Item(S$)
  Loop Until (Err.Number <> 0)
  Set SS_Create = ThisDrawing.SelectionSets.Add(S$)
End Function

Sub last_selection()

    Set S1 = ThisDrawing.SelectionSets.Item("NewOne")
    S1.Clear
    Dim Filter1, Filter2 As Variant
    Dim Gcodes(1) As Integer: Dim Dvals(1) As Variant
    Gcodes(0) = 0: Dvals(0) = "CIRCLE"
    Gcodes(1) = 8: Dvals(1) = "0"
    Filter1 = Gcodes: Filter2 = Dvals
    S1.Select acSelectionSetAll, , , Filter1, Filter2
    ' Selection set contains all the circles in the drawing
    Dvals(0) = "LINE"
    Filter2 = Dvals 'variant MUST be reassigned after change.
    S1.Select acSelectionSetAll, , , Filter1, Filter2
    ' Now S1 has all the lines added after the circles.

End Sub
