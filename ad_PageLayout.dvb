Attribute VB_Name = "Module1"
'
'  ad_PageLayout
'
'  This routine assigns a particular Layout as the Active Layout.
'    It was developed in AutoCAD 2000.
'  Demand load:  -vbarun;ad_PageLayout.dvb!ad_PageLayout;
'
'  version 1.00
'  7/22/2000
'
'  Copyright©2000-2003 ActiveDwg.com
'
'  This routine is provided for demonstration purposes only and must
'    not be used for critical applications without your verification
'    that this routine will perform as you intended.
'  This routine may be freely utilized for your own personal use so long
'    as the entire contents of this header remain intact.
'  This routine is provided "as-is" and no declaration, written or implied,
'    is made as to its reliability for any particular task. Any use of this
'    routine is solely at your own risk.
'
Option Explicit
Sub ad_PageLayout()
    Dim newLayout As AcadLayout
    Dim PageLayouts As AcadLayouts
    Dim newLayoutName As String
    
    Set PageLayouts = ThisDrawing.Layouts
    newLayoutName = "Model"
    Set newLayout = ThisDrawing.Layouts(newLayoutName)
    ThisDrawing.ActiveLayout = newLayout
End Sub
