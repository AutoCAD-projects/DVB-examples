Attribute VB_Name = "ThisDrawing"
Attribute VB_Base = "0{8E75D913-3D21-11D2-85C4-080009A0C626}"
Attribute VB_GlobalNameSpace = False
Attribute VB_Creatable = False
Attribute VB_PredeclaredId = True
Attribute VB_Exposed = True
Attribute VB_TemplateDerived = False
Attribute VB_Customizable = True
'      VBA Sample
'
'      Copyright (C) 1999, 2002 by Autodesk, Inc.
'
'      Permission to use, copy, modify, and distribute this software
'      for any purpose and without fee is hereby granted, provided
'      that the above copyright notice appears in all copies and
'      that both that copyright notice and the limited warranty and
'      restricted rights notice below appear in all supporting
'      documentation.
'
'      AUTODESK PROVIDES THIS PROGRAM "AS IS" AND WITH ALL FAULTS.
'      AUTODESK SPECIFICALLY DISCLAIMS ANY IMPLIED WARRANTY OF
'      MERCHANTABILITY OR FITNESS FOR A PARTICULAR USE.  AUTODESK, INC.
'      DOES NOT WARRANT THAT THE OPERATION OF THE PROGRAM WILL BE
'      UNINTERRUPTED OR ERROR FREE.
'
'      Use, duplication, or disclosure by the U.S. Government is subject to
'      restrictions set forth in FAR 52.227-19 (Commercial Computer
'      Software - Restricted Rights) and DFAR 252.227-7013(c)(1)(ii)
'      (Rights in Technical Data and Computer Software), as applicable.
'
Option Explicit
Private Declare Sub vbaNew Lib "acVba.arx" ()
Private Declare Sub vbaMan Lib "acVba.arx" ()
Private Declare Sub vbaRun Lib "acVba.arx" ()
Private Declare Sub vbaPrefs Lib "acVba.arx" ()
Dim ctrl As CommandBarPopup, ctrlFile As CommandBarPopup
Dim WithEvents eve1 As CommandBarEvents
Attribute eve1.VB_VarHelpID = -1
Dim WithEvents eve2 As CommandBarEvents
Attribute eve2.VB_VarHelpID = -1
Dim WithEvents eve3 As CommandBarEvents
Attribute eve3.VB_VarHelpID = -1
Dim WithEvents eveFile1 As CommandBarEvents
Attribute eveFile1.VB_VarHelpID = -1
Dim WithEvents eveFile2 As CommandBarEvents
Attribute eveFile2.VB_VarHelpID = -1
Dim WithEvents eveFile3 As CommandBarEvents
Attribute eveFile3.VB_VarHelpID = -1
Dim vbext As VBIDE.VBE


Sub CreateVBAToolBar()
    Dim objToolBars As AcadToolbars
    
    Set objToolBars = ThisDrawing.Application.MenuGroups.Item(0).Toolbars
    
    Dim objToolBar As AcadToolbar
    On Error Resume Next
    Set objToolBar = objToolBars.Add("VBA ToolBar")
    If Err Then
        Set objToolBar = objToolBars.Item("VBA ToolBar")
'       MsgBox "'VBA ToolBar' already exists!!"
        Exit Sub
    End If
    On Error GoTo 0
    Dim objToolbarItem As AcadToolbarItem
    Set objToolbarItem = objToolBar.AddToolbarButton(0, "Run Macro", "VBA Macros", "_VBARUN ")
    Call objToolbarItem.SetBitmaps(".\Sample\VBA\VBAIDEmenu\vbarun.bmp", ".\Sample\VBA\VBAIDEmenu\vbarun.bmp")

    Set objToolbarItem = objToolBar.AddToolbarButton(0, "Load Project", "Load Project", "_VBALOAD ")
    Call objToolbarItem.SetBitmaps(".\Sample\VBA\VBAIDEmenu\vbaload.bmp", ".\Sample\VBA\VBAIDEmenu\vbaload.bmp")

    Set objToolbarItem = objToolBar.AddToolbarButton(0, "VBA Manager", "VBA Manager", "_VBAMAN ")
    Call objToolbarItem.SetBitmaps(".\Sample\VBA\VBAIDEmenu\vbaman.bmp", ".\Sample\VBA\VBAIDEmenu\vbaman.bmp")

    Set objToolbarItem = objToolBar.AddToolbarButton(0, "VBA Options", "Invokes VBA Options Dialog", "_VBAPREF ")
    Call objToolbarItem.SetBitmaps(".\Sample\VBA\VBAIDEmenu\vbaopt.bmp", ".\Sample\VBA\VBAIDEmenu\vbaopt.bmp")

    Set objToolbarItem = objToolBar.AddToolbarButton(0, "VBA IDE", "VBA IDE", "_VBAIDE ")
    Call objToolbarItem.SetBitmaps(".\Sample\VBA\VBAIDEmenu\vbaide.bmp", ".\Sample\VBA\VBAIDEmenu\vbaide.bmp")
    objToolBar.Dock acToolbarDockRight
    'Call ThisDrawing.Application.MenuGroups.Item("ACAD").SaveAs("ACADVBA", acMenuFileSource)
End Sub

Sub VBAIDE_Customization()
    Set vbext = AcadApplication.VBE
    
    Dim obj As Object
    Dim cmdbar As Office.CommandBar
    Set cmdbar = vbext.CommandBars.Item("Menu Bar")
    cmdbar.Reset
     On Error GoTo 0
     
    Set ctrlFile = cmdbar.Controls.Item("File")
    
    Dim objFile1 As CommandBarControl, objFile2 As CommandBarControl, objFile3 As CommandBarControl
    Set objFile1 = ctrlFile.Controls.Add(Type:=msoControlButton, Before:=1)
    With objFile1
        .Caption = "&New"
        .TooltipText = "Create New Global Project"
        '.ShortcutText = "Ctrl+N"
        .Visible = True
    End With
    Set eveFile1 = vbext.Events.CommandBarEvents(objFile1)

    Set objFile2 = ctrlFile.Controls.Add(Type:=msoControlButton, Before:=2)
    Set objFile3 = ctrlFile.Controls.Add(Type:=msoControlButton, Before:=3)

    With objFile2
        .Caption = "Open..."
        .TooltipText = "Open Global Project..."
        '.ShortcutText = "Ctrl+O"
        .Visible = True
    End With
    Set eveFile2 = vbext.Events.CommandBarEvents(objFile2)


    With objFile3
        .Caption = "Close"
        .TooltipText = "Close Project"
        .Visible = True
    End With
    Set eveFile3 = vbext.Events.CommandBarEvents(objFile3)
    
    
    Set ctrl = cmdbar.Controls.Add(Type:=msoControlPopup, temporary:=True)
    With ctrl
        .Caption = "AutoCAD"
        .DescriptionText = "My Button"
        .TooltipText = "AutoCAD Custom Menu"
        .Visible = True
        .Tag = "PRC"
    End With
    

    Dim obj1 As Object
    Set obj1 = ctrl.Controls.Add(Type:=msoControlButton)
    With obj1
        .Caption = "VBA Manager..."
        .TooltipText = "VBA Manager..."
        .Visible = True
    End With
    Set eve1 = vbext.Events.CommandBarEvents(obj1)
    
    Dim obj3 As Object
    Set obj3 = ctrl.Controls.Add(Type:=msoControlButton)
    With obj3
        .Caption = "VBA Macros..."
        .TooltipText = "VBA Macros..."
        .Visible = True
    End With
    Set eve3 = vbext.Events.CommandBarEvents(obj3)
    Dim obj2 As Object
    Set obj2 = ctrl.Controls.Add(Type:=msoControlButton)
    With obj2
        .Caption = "VBA Options..."
        .TooltipText = "VBA Options..."
        .Visible = True
    End With
    Set eve2 = vbext.Events.CommandBarEvents(obj2)
End Sub


Private Sub eveFile2_Click(ByVal CommandBarControl As Object, handled As Boolean, CancelDefault As Boolean)
    If TypeOf CommandBarControl Is CommandBarButton Then
        If AcadApplication.Documents.Count > 0 Then
            ThisDrawing.SendCommand "vbaload "
            DoEvents
            ThisDrawing.SendCommand "vbaide "
        Else
            MsgBox "This command will work only when AutoCAD is not in Zero Document state", vbInformation, "VBALOAD"
        End If
    End If

End Sub
Private Sub eve1_Click(ByVal CommandBarControl As Object, handled As Boolean, CancelDefault As Boolean)
    If TypeOf CommandBarControl Is CommandBarButton Then
        vbaMan
    End If
End Sub
Private Sub eve2_Click(ByVal CommandBarControl As Object, handled As Boolean, CancelDefault As Boolean)
    If TypeOf CommandBarControl Is CommandBarButton Then
        vbaPrefs
    End If
End Sub
Private Sub eve3_Click(ByVal CommandBarControl As Object, handled As Boolean, CancelDefault As Boolean)
    If TypeOf CommandBarControl Is CommandBarButton Then
        If Documents.Count <> 0 Then
            vbaRun
        Else
            MsgBox "This command will work only when AutoCAD is not in Zero Document state", vbInformation, "VBARUN"
        End If
    End If
End Sub


Private Sub eveFile1_Click(ByVal CommandBarControl As Object, handled As Boolean, CancelDefault As Boolean)
    If TypeOf CommandBarControl Is CommandBarButton Then
        vbaNew
    End If
End Sub

Private Sub eveFile3_Click(ByVal CommandBarControl As Object, handled As Boolean, CancelDefault As Boolean)
    If TypeOf CommandBarControl Is CommandBarButton Then
        unload
    End If
End Sub

Private Sub unload()
    Dim str As String
    str = VBWindows
    If str = "DWG" Then
        MsgBox "To unload embedded project, close the containing drawing!"
        Exit Sub
    End If
    AcadApplication.UnloadDVB str
End Sub

Private Function VBWindows() As String
    Set vbext = AcadApplication.VBE
    Dim win As VBIDE.Window
    Dim pos As Long
    For Each win In vbext.Windows
        If Not win.LinkedWindowFrame Is Nothing Then
            pos = InStr(1, win.LinkedWindowFrame.Caption, ".dvb")
            If pos <> 0 Then
                VBWindows = Mid(win.LinkedWindowFrame.Caption, Len("Microsoft Visual Basic - ") + 1, pos - Len("Microsoft Visual Basic - ") + 3)
                Exit Function
            End If
            pos = InStr(1, win.LinkedWindowFrame.Caption, ".dwg")
            If pos <> 0 Then
                VBWindows = "DWG"
            Else 'Unsaved Global Project
                pos = InStr(Len("Microsoft Visual Basic - ") + 1, win.LinkedWindowFrame.Caption, " ")
                VBWindows = Mid(win.LinkedWindowFrame.Caption, Len("Microsoft Visual Basic - ") + 1, pos - Len("Microsoft Visual Basic - ") - 1)
            End If
            Exit Function
        End If
    Next win
End Function
