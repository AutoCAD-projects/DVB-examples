Attribute VB_Name = "Access_VBA_mod"
Public wksObj As Object         'Workspaces
Public dbsObj As Object         'Access
Public tblObj As Object         'Table
Public fldObj As Object         'Fields
Public rstObj As Object         'Memory version of database
'a;sldfj;alskjf;alskjf
