Attribute VB_Name = "basGlobal"
Option Explicit
Public Const gintMAX_SIZE As Integer = 50
Global Const gstrNULL$ = ""                             'Empty string
Global Const gconAppname As String = "VBA Book"
Global Const gconSection As String = "General"
Global Const gconKey As String = "My File"


Public Sub RegExample()
    frmRegAccess.Show
End Sub
'
' IN: [strIniFile] - name of .INI file to read
'     [strSection] - section where key is found
'     [strKey] - name of key to get the value of
'
'-----------------------------------------------------------
'
Public Function ReadRegistry(ByVal strAppName, ByVal strSECTION As String, ByVal strKey As String) As String
'    Stop
    Dim strResult As String
    On Error Resume Next                        ' getsetting throws an error if all
                                                ' arguments are not present
    strResult = GetSetting(strAppName, strSECTION, strKey)  ' get the data
    'Debug.Print Err.Number
    If Err.Number > 0 Then                      ' Was an error thrown?
        ReadRegistry = gstrNULL                 ' return nothing
    Else
        ReadRegistry = strResult                ' return the item
    End If
End Function
Public Function WriteRegistry(ByVal strAppName, ByVal strSECTION As String, ByVal strKey As String, ByVal strItem As String)
'    Stop
    Dim strResult As String
    Dim intPos As Integer

    Call SaveSetting(strAppName, strSECTION, strKey, strItem)
    If Err.Number > 0 Then
        Debug.Print "failure"
    Else
        MsgBox frmRegAccess.txtItem & " was sucessfully written to the Registry Key " & frmRegAccess.txtKey & "."
    End If
End Function
Function StripTerminator(ByVal strString As String) As String
' returns the string with out the terminator or any characters following it
' or it returns the original string when no terminator present
    Dim intZeroPos As Integer

    intZeroPos = InStr(strString, Chr$(0))                  'get terminators position
    If intZeroPos > 0 Then
        StripTerminator = Left$(strString, intZeroPos - 1)  'get up to it
    Else
        StripTerminator = strString                         ' no, return the string
    End If
End Function

Attribute VB_Name = "frmRegAccess"
Attribute VB_Base = "0{28807C0E-2350-11D2-99EE-00609761BD90}{28807BF1-2350-11D2-99EE-00609761BD90}"
Attribute VB_Creatable = False
Attribute VB_PredeclaredId = True
Attribute VB_Exposed = False
Attribute VB_TemplateDerived = False
Attribute VB_Customizable = False
Option Explicit

Private Sub btnDone_Click()
    End
End Sub

Private Sub btnReadReg_Click()
    Dim strResult As String
    strResult = ReadRegistry(ByVal txtAppName.Text, ByVal txtSection.Text, txtKey.Text)
    txtItem.Text = strResult
    
End Sub

Private Sub btnReload_Click()
    txtAppName.Text = gconAppname
    txtSection.Text = gconSection
    txtKey.Text = gconKey
    txtItem.Text = gstrNULL$
End Sub

Private Sub btnRemove_Click()
    ' Remove items from registry.
    If Len(txtKey.Text) > 0 Then
        DeleteSetting txtAppName.Text, txtSection.Text, txtKey.Text
    ElseIf Len(txtSection.Text) > 0 Then
        DeleteSetting txtAppName.Text, txtSection.Text
    Else
        DeleteSetting txtAppName.Text
    End If

End Sub

Private Sub btnWriteReg_Click()
    Dim strResult As String
    If Len(txtAppName.Text) > 0 Then
        If Len(txtSection.Text) > 0 And _
           Len(txtKey.Text) > 0 And _
           Len(txtItem.Text) > 0 Then
           strResult = WriteRegistry(ByVal txtAppName.Text, ByVal txtSection.Text, ByVal txtKey.Text, ByVal txtItem.Text)
        Else
            MsgBox "The Section, Key and Item text boxes must be filled out to continue."
        End If
    Else
        MsgBox txtAppName.Text & " not found.", , "Error"
    End If
End Sub

Private Sub UserForm_Initialize()
    btnReload_Click

End Sub
