Attribute VB_Name = "basGlobal"
Option Explicit
Declare Function GetComputerName Lib "kernel32" Alias "GetComputerNameA" (ByVal lpBuffer As String, nSize As Long) As Long
Declare Function GetDiskFreeSpace Lib "kernel32" Alias "GetDiskFreeSpaceA" (ByVal lpRootPathName As String, lpSectorsPerCluster As Long, lpBytesPerSector As Long, lpNumberOfFreeClusters As Long, lpTotalNumberOfClusters As Long) As Long
Declare Function GetEnvironmentVariable Lib "kernel32" Alias "GetEnvironmentVariableA" (ByVal lpName As String, ByVal lpBuffer As String, ByVal nSize As Long) As Long
Declare Function GetTempPath Lib "kernel32" Alias "GetTempPathA" (ByVal nBufferLength As Long, ByVal lpBuffer As String) As Long
Declare Function GetUserName Lib "advapi32.dll" Alias "GetUserNameA" (ByVal lpBuffer As String, nSize As Long) As Long
Declare Function GetTimeFormat Lib "kernel32" Alias "GetTimeFormatA" (ByVal Locale As Long, ByVal dwFlags As Long, lpTime As SYSTEMTIME, ByVal lpFormat As String, ByVal lpTimeStr As String, ByVal cchTime As Long) As Long
Declare Sub GetLocalTime Lib "kernel32" (lpSystemTime As SYSTEMTIME)
Declare Sub GetSystemTime Lib "kernel32" (lpSystemTime As SYSTEMTIME)
Public Const glngMAX_COMPUTERNAME_LENGTH As Long = 50

Const LOCALE_SYSTEM_DEFAULT& = &H800
' user defined object type for getting local & system time
Type SYSTEMTIME
        wYear As Integer
        wMonth As Integer
        wDayOfWeek As Integer
        wDay As Integer
        wHour As Integer
        wMinute As Integer
        wSecond As Integer
        wMilliseconds As Integer
End Type
Public Sub MyComputer()
    Dim strMessage As String
    Dim MAX_STRING_LENGTH As Long
    
    ' Get the computer's name
    Dim CompName As String
    CompName = Space$(glngMAX_COMPUTERNAME_LENGTH)  ' fill buffer with spaces
    Dim lngResult As Long
    Dim lngSize As Long
    lngSize = glngMAX_COMPUTERNAME_LENGTH           ' set size
    lngResult = GetComputerName(CompName, lngSize)  ' get the name
    'Debug.Print CompName                            ' show name
    'Debug.Print "Length of string in buffer - " & Len(CompName)
    CompName = StripTerminator(CompName)            ' strip buffer to just contents
    'Debug.Print "Length of string after stripping terminator - " & Len(CompName)                 ' show names length
    strMessage = strMessage & "Computer Name : " & CompName & vbCrLf & vbCrLf
    
    ' Get the User's login name
    Dim strUserName As String
    MAX_STRING_LENGTH = 100                     ' set dummy length since we don't know exact length
    strUserName = Space$(MAX_STRING_LENGTH)     ' fill buffer with spaces
    lngResult = GetUserName(strUserName, MAX_STRING_LENGTH)
    'Debug.Print strUserName
    strUserName = StripTerminator(strUserName)  ' strip buffer to just contents
    strMessage = strMessage & "Login Name : " & strUserName & vbCrLf & vbCrLf
    
    ' Get local & system Time
    Dim sysTime As SYSTEMTIME
    Dim strBuffer As String
    
    GetSystemTime sysTime
    strBuffer$ = String$(255, Chr$(0))
    lngResult& = GetTimeFormat(LOCALE_SYSTEM_DEFAULT, 0, sysTime, 0, strBuffer$, 254)
    strMessage = strMessage & "System Time : " & sysTime.wMonth & "/" & sysTime.wDay & "/" & sysTime.wYear & _
                              "              " & sysTime.wHour & ":" & sysTime.wMinute & vbCrLf
    'Debug.Print sysTime.wMonth & "/" & sysTime.wDay & "/" & sysTime.wYear
    'Debug.Print sysTime.wHour & ":" & sysTime.wMinute
    
    GetLocalTime sysTime
    strBuffer$ = String$(255, Chr$(0))
    lngResult& = GetTimeFormat(LOCALE_SYSTEM_DEFAULT, 0, sysTime, 0, strBuffer$, 254)
    strMessage = strMessage & "Local Time  : " & sysTime.wMonth & "/" & sysTime.wDay & "/" & sysTime.wYear & _
                              "              " & sysTime.wHour & ":" & sysTime.wMinute & vbCrLf & vbCrLf
    'Debug.Print sysTime.wMonth & "/" & sysTime.wDay & "/" & sysTime.wYear
    'Debug.Print sysTime.wHour & ":" & sysTime.wMinute
    
    ' Get the Windows Temporary directory
    Dim strTempDir As String
    MAX_STRING_LENGTH = 300                     ' set dummy length since we don't know exact length
    strTempDir = Space$(MAX_STRING_LENGTH)      ' fill buffer with spaces
    lngResult = GetTempPath(MAX_STRING_LENGTH, strTempDir)
    'Debug.Print strTempDir
    strTempDir = StripTerminator(strTempDir)    ' strip buffer to just contents
    strMessage = strMessage & "Windows Temp Dir : " & strTempDir & vbCrLf & vbCrLf
    
    ' Get free disk space
    Dim strDrive As String
    Dim FreeBytes&, TotalBytes&
    strDrive$ = "c:"
    If Right$(strDrive$, 1) <> "\" Then strDrive$ = strDrive$ & "\"
    
    Dim SectorsPerCluster As Long
    Dim BytesPerSector As Long
    Dim NumberOfFreeClusters As Long
    Dim TotalNumberOfClusters As Long
    lngResult& = GetDiskFreeSpace(strDrive$, SectorsPerCluster, BytesPerSector, NumberOfFreeClusters, TotalNumberOfClusters)
    
    'Debug.Print Format(SectorsPerCluster, "#,0")
    'Debug.Print Format(BytesPerSector, "#,0")
    'Debug.Print Format(NumberOfFreeClusters, "#,0")
    'Debug.Print Format(TotalNumberOfClusters, "#,0")
    TotalBytes = TotalNumberOfClusters * SectorsPerCluster * BytesPerSector
    'Debug.Print Format(TotalBytes, "#,0")
    FreeBytes = NumberOfFreeClusters * SectorsPerCluster * BytesPerSector
    'Debug.Print Format(FreeBytes, "#,0")
    'Debug.Print Format(FreeBytes / TotalBytes, "Percent")
    
    strMessage = strMessage & "C: drive information : " & vbCrLf & _
                 "Sectors : " & Format(SectorsPerCluster, "#,0") & vbCrLf & _
                 "Bytes per Sector : " & Format(BytesPerSector, "#,0") & vbCrLf & _
                 "Number of Free clusters : " & Format(NumberOfFreeClusters, "#,0") & vbCrLf & _
                 "Total number of clusters : " & Format(TotalNumberOfClusters, "#,0") & vbCrLf & _
                 "Total Bytes : " & Format(TotalBytes, "#,0") & vbCrLf & _
                 "Total Free Bytes : " & Format(FreeBytes, "#,0") & vbCrLf & _
                 "Percent of Free Bytes on drive : " & Format(FreeBytes / TotalBytes, "Percent") & vbCrLf & vbCrLf
    
    ' Get the environment string - PATH
    Dim strVarContents As String
    MAX_STRING_LENGTH = 1                           ' set dummy length since we don't know exact length
    strVarContents = Space$(MAX_STRING_LENGTH)      ' fill buffer with spaces
    lngResult = GetEnvironmentVariable("PATH", strVarContents, MAX_STRING_LENGTH)
    MAX_STRING_LENGTH = lngResult                   ' take returned length
    strVarContents = Space$(MAX_STRING_LENGTH)      ' and reinitiate
    lngResult = GetEnvironmentVariable("PATH", strVarContents, MAX_STRING_LENGTH) ' now get it
    'Debug.Print strVarContents
    strVarContents = StripTerminator(strVarContents)            ' strip buffer to just contents
    strMessage = strMessage & "System Variable:" & vbCrLf & "PATH = " & strVarContents
    
    MsgBox strMessage, , "System Info."
End Sub
Function StripTerminator(ByVal strString As String) As String
    Dim intZeroPos As Integer

    intZeroPos = InStr(strString, Chr$(0))
    If intZeroPos > 0 Then
        StripTerminator = Left$(strString, intZeroPos - 1)
    Else
        StripTerminator = strString
    End If
End Function
