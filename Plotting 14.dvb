Attribute VB_Name = "basFileIO"
Option Explicit
Declare Function GetPrivateProfileString Lib "kernel32" Alias "GetPrivateProfileStringA" (ByVal lpApplicationName As String, ByVal lpKeyName As Any, ByVal lpDefault As String, ByVal lpReturnedString As String, ByVal nSize As Long, ByVal lpFileName As String) As Long
Declare Function WritePrivateProfileString Lib "kernel32" Alias "WritePrivateProfileStringA" (ByVal lpApplicationName As String, ByVal lpKeyName As Any, ByVal lpString As Any, ByVal lpFileName As String) As Long
Public Const gintMAX_SIZE As Integer = 50
Global Const gstrNULL$ = ""                             'Empty string
Global Const gstrDefault = "Empty"
Public Sub INIExample()
    frmInput.Show
End Sub
'-----------------------------------------------------------
' FUNCTION: ReadIniFile
'
' Reads a value from the specified section/key of the
' specified .INI file
'
' IN: [strIniFile] - name of .INI file to read
'     [strSection] - section where key is found
'     [strKey] - name of key to get the value of
'     [KeyMode] - whether to read and return all keys
'                 or just the one supplied and return its item
'
' Returns: non-zero terminated value of .INI file key
'-----------------------------------------------------------
'
Public Function ReadIniFile(ByVal strIniFile As String, ByVal strSection As String, ByVal strKey As String, ByVal strDefault As String, KeyMode As Boolean) As String
'    Stop
    'Dim strBuffer As String     ' declare the buffer seperately because otherwise
                                ' it will not store returned data properly
                                ' This might be because of the Space function used
                                ' to inititate it. (Not sure)
    Dim strBuffer As String
    Dim strResult As String
    Dim intPos As Integer

    strBuffer = Space$(gintMAX_SIZE)    ' initiate buffer (a must!!!)
    If KeyMode Then                     ' true when wants all keys
        intPos = GetPrivateProfileString(strSection, vbNullString, strDefault, strBuffer, gintMAX_SIZE, strIniFile)
    Else                                ' just wants one key's item
        intPos = GetPrivateProfileString(strSection, strKey, strDefault, strBuffer, gintMAX_SIZE, strIniFile)
    End If
    If intPos > 0 Then
        ReadIniFile = Mid(strBuffer, 1, intPos) ' strip off extra chars in buffer as it is sent back
    Else
        ReadIniFile = gstrNULL                  ' return nothing on failure
    End If
End Function
Public Function WriteIniFile(ByVal strIniFile As String, ByVal strSection As String, ByVal strKey As String, ByVal strItem As String) As String
'    Stop
    Dim strResult As String
    Dim intPos As Integer
    
    intPos = WritePrivateProfileString&(strSection, strKey, strItem, strIniFile)
    If intPos > 0 Then                  ' if successful - tell them
        MsgBox frmInput.txtItem & " was sucessfully written to the Key " & frmInput.txtKey & "."
    Else
        Debug.Print "failure"
    End If
End Function

Attribute VB_Name = "basGlobal"
Option Explicit
Global Project_Found As Boolean                 ' flag for registry data
Global lngSetPlotter As Long                    ' hold plotter number for setting
Public gstrStandardPaperSize As String          ' hold paper size
Public gdblPaperWidth As Double                 ' hold paper width
Public gdblPaperHeight As Double                ' hold paper height
Public gdblWidthOrigin As Double                ' hold x origin
Public gdblHeightOrigin As Double               ' hold y origin
Public gstrRotation As String                   ' hold rotation
Public gintMetric As Integer                    ' hold metric setting
Public gstrViewType As String
Public gstrFirstX As String
Public gstrFirstY As String
Public gstrOtherX As String
Public gstrOtherY As String
Public gstrPlotName As String
Public gAcadCfg As String                       ' hold AutoCAD configuration path and name
Public gdblMultiplier As Double
Public gvarProjects As Variant
Public gcolRegData As New Collection
Public gbolPlotFormState As Boolean             ' control form display
Public gbolWindowPicked As Boolean              ' control window radio button
Public gstrViewName As String
Public gstrPlotFileName As String
Public Const gconAppname As String = "AutoCAD"
Public Const gconSectionName As String = "Plotting Projects"
Public Const gconPlotCount As String = "Plot Count"
Public Const gconlngBaseFlag As Long = 254288
Public Const gconMM As Double = 25.4
Public Const gstrNULL As String = ""

Public Sub LoadData(Filename As String, DeviceNum As String, colRegData As Collection)
    ' Section headers
    Dim strregDevice As String
    Dim strregUser As String
    Dim strregWidthTable As String
    Dim strregSpeedTable As String
    Dim strregPenTable As String
    Dim strregPort As String
    Dim strTemp As String
    ' load them with the approperiate headers for use
    strregDevice = "Plotter#" & DeviceNum & "/Device"
    strregUser = "Plotter#" & DeviceNum & "/User"
    strregSpeedTable = "Plotter#" & DeviceNum & "/Device/SpeedTable"
    strregPenTable = "Plotter#" & DeviceNum & "/Device/Pentable"
    strregWidthTable = "Plotter#" & DeviceNum & "/Device/WidthTable"
    strregPort = "Plotter#" & DeviceNum & "/Port"
    ' Paper Size
    strTemp = ReadIniFile(gAcadCfg, strregUser, "UserWidth1", gstrDefault, False)
    colRegData.Add strTemp, "UserWidth1"
    
    strTemp = ReadIniFile(gAcadCfg, strregUser, "UserHeight1", gstrDefault, False)
    colRegData.Add strTemp, "UserHeight1"
    
    strTemp = ReadIniFile(gAcadCfg, strregUser, "UserWidth2", gstrDefault, False)
    colRegData.Add strTemp, "UserWidth2"
    
    strTemp = ReadIniFile(gAcadCfg, strregUser, "UserHeight2", gstrDefault, False)
    colRegData.Add strTemp, "UserHeight2"
    
    strTemp = ReadIniFile(gAcadCfg, strregUser, "UserWidth3", gstrDefault, False)
    colRegData.Add strTemp, "UserWidth3"
    
    strTemp = ReadIniFile(gAcadCfg, strregUser, "UserHeight3", gstrDefault, False)
    colRegData.Add strTemp, "UserHeight3"
    
    strTemp = ReadIniFile(gAcadCfg, strregUser, "UserWidth4", gstrDefault, False)
    colRegData.Add strTemp, "UserWidth4"
    
    strTemp = ReadIniFile(gAcadCfg, strregUser, "UserHeight4", gstrDefault, False)
    colRegData.Add strTemp, "UserHeight4"
    
    strTemp = ReadIniFile(gAcadCfg, strregUser, "UserWidth5", gstrDefault, False)
    colRegData.Add strTemp, "UserWidth5"
    
    strTemp = ReadIniFile(gAcadCfg, strregUser, "UserHeight5", gstrDefault, False)
    colRegData.Add strTemp, "UserHeight5"
    
    ' Device and Default Selection
    strTemp = ReadIniFile(gAcadCfg, strregDevice, "MenuName", gstrDefault, False)
    colRegData.Add strTemp, "Manufacturer"
        
    strTemp = ReadIniFile(gAcadCfg, strregPort, "PortName", gstrDefault, False)
    colRegData.Add strTemp, "PortName"
        
    ' main dialog
    
    strTemp = ReadIniFile(gAcadCfg, strregUser, "IsMetric", gstrDefault, False)
    colRegData.Add strTemp, "IsMetric"
    If strTemp <> "Empty" Then                  ' is plotting metric or inches?
        If strTemp = 0 Then
            gintMetric = 0
        Else
            gintMetric = CInt(strTemp)
        End If
    Else
            gintMetric = 0
    End If
    
    strTemp = ReadIniFile(gAcadCfg, strregUser, "WidthOrigin", gstrDefault, False)
    strTemp = Clean_str(strTemp)
    colRegData.Add strTemp, "WidthOrigin"
    If strTemp <> "Empty" Then
        gdblWidthOrigin = CStr(CDbl(strTemp))
    Else
        gdblWidthOrigin = CStr(Format(0, "####0.00"))
    End If
    
    strTemp = ReadIniFile(gAcadCfg, strregUser, "HeightOrigin", gstrDefault, False)
    strTemp = Clean_str(strTemp)
    colRegData.Add strTemp, "HeightOrigin"
    If strTemp <> "Empty" Then
        gdblHeightOrigin = CStr(CDbl(strTemp))
    Else
        gdblHeightOrigin = CStr(Format(0, "####0.00"))
    End If
    
    strTemp = ReadIniFile(gAcadCfg, strregUser, "ViewType", gstrDefault, False)
    colRegData.Add strTemp, "ViewType"
    Select Case strTemp
        Case "L"
            frmPlot.rdLimits.Value = True
        Case "W"
            frmPlot.rdWindow.Value = True
        Case "E"
            frmPlot.rdExtents.Value = True
        Case "V"
            frmPlot.rdView.Value = True
        Case "Empty"
            frmPlot.rdDisplay.Value = True
    End Select
    
    strTemp = ReadIniFile(gAcadCfg, strregUser, "View", gstrDefault, False)
    colRegData.Add strTemp, "View"
    gstrPlotName = strTemp
    
    strTemp = ReadIniFile(gAcadCfg, strregUser, "ViewCorner0", gstrDefault, False)
    strTemp = Clean_str(strTemp)
    colRegData.Add strTemp, "ViewCorner0"
    
    strTemp = ReadIniFile(gAcadCfg, strregUser, "ViewCorner1", gstrDefault, False)
    strTemp = Clean_str(strTemp)
    colRegData.Add strTemp, "ViewCorner1"
    
    strTemp = ReadIniFile(gAcadCfg, strregUser, "ViewCorner2", gstrDefault, False)
    strTemp = Clean_str(strTemp)
    colRegData.Add strTemp, "ViewCorner2"
    
    strTemp = ReadIniFile(gAcadCfg, strregUser, "ViewCorner3", gstrDefault, False)
    strTemp = Clean_str(strTemp)
    colRegData.Add strTemp, "ViewCorner3"
    If strTemp <> "Empty" Then
        gstrFirstX = CStr(Format(CDbl(strTemp), "####0.0000"))
        strTemp = gcolRegData.Item("ViewCorner1")
        gstrFirstY = CStr(Format(CDbl(strTemp), "####0.0000"))
        strTemp = gcolRegData.Item("ViewCorner2")
        gstrOtherX = CStr(Format(CDbl(strTemp), "####0.0000"))
        strTemp = gcolRegData.Item("ViewCorner3")
        gstrOtherY = CStr(Format(CDbl(strTemp), "####0.0000"))
        
    Else
        gstrFirstX = CStr(Format(CDbl(0), "####0.0000"))
        gstrFirstY = CStr(Format(CDbl(0), "####0.0000"))
        gstrOtherX = CStr(Format(CDbl(16.2598), "####0.0000"))
        gstrOtherY = CStr(Format(CDbl(9), "####0.0000"))
    End If
    
    strTemp = ReadIniFile(gAcadCfg, strregUser, "Flags", gstrDefault, False)
    strTemp = Clean_str(strTemp)
    colRegData.Add strTemp, "UserFlags"
    
    strTemp = ReadIniFile(gAcadCfg, strregUser, "StandardSize", gstrDefault, False)
    colRegData.Add strTemp, "StandardSize"
    gstrStandardPaperSize = strTemp
    
    strTemp = ReadIniFile(gAcadCfg, strregUser, "PlotWidth", gstrDefault, False)
    strTemp = Clean_str(strTemp)
    colRegData.Add strTemp, "PlotWidth"
    gdblPaperWidth = CDbl(strTemp)
    
    strTemp = ReadIniFile(gAcadCfg, strregUser, "PlotHeight", gstrDefault, False)
    strTemp = Clean_str(strTemp)
    colRegData.Add strTemp, "PlotHeight"
    gdblPaperHeight = CDbl(strTemp)
    
    strTemp = ReadIniFile(gAcadCfg, strregUser, "MaxWidth", gstrDefault, False)
    colRegData.Add strTemp, "MaxWidth"
    
    strTemp = ReadIniFile(gAcadCfg, strregUser, "MaxHeight", gstrDefault, False)
    colRegData.Add strTemp, "MaxHeight"
    
    ' optimization dialog
    strTemp = ReadIniFile(gAcadCfg, strregUser, "OptimizationLevel", gstrDefault, False)
    colRegData.Add strTemp, "Optimization Level"
    
    
End Sub
Public Function Clean_str(strTemp As String) As String
    Dim Astring As String
    Dim varPos As Variant
    varPos = InStr(1, strTemp, " ")
    If varPos > 0 Then
        Astring = Left(strTemp, CLng(varPos) - 1)
    Else
        Astring = strTemp
    End If
    Clean_str = Astring
End Function
Public Sub test()
    Dim Plotters As Variant
    Plotters = GetPlotters()
    Dim i As Integer
    For i = 0 To UBound(Plotters)
        Debug.Print Plotters(i, 0)
        Debug.Print Plotters(i, 1)

    Next i
End Sub
Public Function GetPlotters() As Variant

' plotters is a variant representing a two dimensional array to be used by the
' listbox in the calling routine
' Load it with the PlotID and Plotter

    Dim strPlotID As String
    strPlotID = ThisDrawing.GetVariable("Plotid")   ' get the current plotter name
    If Len(strPlotID) = 0 Then                      ' no name means no plotter configured
        GoTo exitsub                                ' get out
    End If

    ' save the current plotter for later restoration
    Dim lngCurPlotter As Long
    lngCurPlotter = ThisDrawing.GetVariable("Plotter") ' get the plotter number

' first get all plotter info into single arrays for later transfer to a double array
' this is to get a count for creating the double array since we can't use preserve on a double
    
    Dim aryPlotters() As Long
    Dim aryPlotId() As String
    Dim NoMorePlotters As Boolean
    Dim lngI As Long
    lngI = 0
    ThisDrawing.SetVariable "Plotter", 0    ' try to set the next plotter number
    On Error Resume Next                    ' set to get out of the infinite loop
    ' start an 'infinite' loop
    ' since we don't know how many plotters are present, we must set it up this way
    ' and then depend upon the error function to break the loop when no more plotters
    ' are present
    Do Until NoMorePlotters
        ReDim Preserve aryPlotters(lngI)    ' build the single arrays
        ReDim Preserve aryPlotId(lngI)
        ' store the plotter data into the arrays
        aryPlotters(lngI) = ThisDrawing.GetVariable("Plotter")
        aryPlotId(lngI) = ThisDrawing.GetVariable("PlotId")
        lngI = lngI + 1
        ' try to set the next plotter number
        ThisDrawing.SetVariable "Plotter", CInt(lngI)
        If Err.Number <> 0 Then             ' an error is thrown when no more plotters
            Err.Clear                       ' clear it
            Exit Do                         ' exit the 'infinite' loop
        End If
    Loop
    Dim lngAryLength As Long
    lngAryLength = UBound(aryPlotters)
    ReDim Plotters(lngAryLength, lngAryLength + 1)
    For lngI = 0 To lngAryLength
        Plotters(lngI, 0) = aryPlotId(lngI)
        Plotters(lngI, 1) = aryPlotters(lngI)
        Debug.Print Plotters(lngI, 0)
        Debug.Print Plotters(lngI, 1)
    
    Next lngI
    
exitsub:
    ThisDrawing.SetVariable "Plotter", lngCurPlotter    ' reset to original plotter
    GetPlotters = Plotters
End Function

Public Sub helptest()
Dim Msg
Err.Clear
On Error Resume Next    ' Suppress errors for demonstration purposes.
Err.Raise 6 ' Generate "Overflow" error.
Msg = "Press F1 or Help to see " & Err.HelpFile & _
" topic for this error"
MsgBox Msg, , "Error: " & Err.Description, Err.HelpFile, Err.HelpContext
End Sub
Public Sub pscaletest()

    
    ' Change the setting of the PlotScale property
'    Dim newPlotScale(0 To 1) As Double
'    If currPlotScale(0) <> 0 Then
'        newPlotScale(0) = 0#: newPlotScale(1) = 0#
'    Else
'        newPlotScale(0) = 1#: newPlotScale(1) = 100#
'    End If
'    ThisDrawing.plot.PlotScale = newPlotScale
'    MsgBox "PlotScale property is now set to " & ThisDrawing.plot.PlotScale(0) & " to " & ThisDrawing.plot.PlotScale(1), , "PlotScale Example"

    

End Sub
Public Sub LoadOptimizationDialog(colRegData As Collection)
    Select Case colRegData("Optimization Level")
        Case "Empty"
            frmOptimizePenMotion.chkNoOpt.Value = True
        Case 1
            frmOptimizePenMotion.chkEndSwap.Value = True
        Case 2
            frmOptimizePenMotion.chkEndSwap.Value = True
            frmOptimizePenMotion.chkPenSort.Value = True
        Case 3
            frmOptimizePenMotion.chkEndSwap.Value = True
            frmOptimizePenMotion.chkPenSort.Value = True
            frmOptimizePenMotion.chkLimitMotion.Value = True
        Case 4
            frmOptimizePenMotion.chkEndSwap.Value = True
            frmOptimizePenMotion.chkPenSort.Value = True
            frmOptimizePenMotion.chkLimitMotion.Value = True
            frmOptimizePenMotion.chkFullMotion.Value = True
        Case 5
            frmOptimizePenMotion.chkEndSwap.Value = True
            frmOptimizePenMotion.chkPenSort.Value = True
            frmOptimizePenMotion.chkLimitMotion.Value = True
            frmOptimizePenMotion.chkFullMotion.Value = True
            frmOptimizePenMotion.chkElimHorz.Value = True
        Case 6
            frmOptimizePenMotion.chkEndSwap.Value = True
            frmOptimizePenMotion.chkPenSort.Value = True
            frmOptimizePenMotion.chkLimitMotion.Value = True
            frmOptimizePenMotion.chkFullMotion.Value = True
            frmOptimizePenMotion.chkElimHorz.Value = True
            frmOptimizePenMotion.chkElimDiag.Value = True
    End Select
End Sub
Public Sub LoadPaperSizeDialog(colRegData As Collection)
    gdblMultiplier = 1
    If gintMetric > 0 Then
        gdblMultiplier = gdblMultiplier * gconMM
    End If
    frmPaperSize.lstSizes.Clear
    With frmPaperSize.lstSizes
        .AddItem "A"
        .Column(1, .ListCount - 1) = CStr(10.5 * gdblMultiplier)
        .Column(2, .ListCount - 1) = CStr(8 * gdblMultiplier)
        .AddItem "B"
        .Column(1, .ListCount - 1) = CStr(16 * gdblMultiplier)
        .Column(2, .ListCount - 1) = CStr(10 * gdblMultiplier)
        .AddItem "C"
        .Column(1, .ListCount - 1) = CStr(21 * gdblMultiplier)
        .Column(2, .ListCount - 1) = 16 * gdblMultiplier
        .AddItem "D"
        .Column(1, .ListCount - 1) = 33 * gdblMultiplier
        .Column(2, .ListCount - 1) = 21 * gdblMultiplier
        .AddItem "E"
        .Column(1, .ListCount - 1) = 43 * gdblMultiplier
        .Column(2, .ListCount - 1) = 33 * gdblMultiplier
        .AddItem "F"
        .Column(1, .ListCount - 1) = 40 * gdblMultiplier
        .Column(2, .ListCount - 1) = 28 * gdblMultiplier
        .AddItem "G"
        .Column(1, .ListCount - 1) = 90 * gdblMultiplier
        .Column(2, .ListCount - 1) = 11 * gdblMultiplier
        .AddItem "H"
        .Column(1, .ListCount - 1) = 143 * gdblMultiplier
        .Column(2, .ListCount - 1) = 28 * gdblMultiplier
        .AddItem "J"
        .Column(1, .ListCount - 1) = 176 * gdblMultiplier
        .Column(2, .ListCount - 1) = 34 * gdblMultiplier
        .AddItem "A4"
        .Column(1, .ListCount - 1) = 11.2 * gdblMultiplier
        .Column(2, .ListCount - 1) = 7.8 * gdblMultiplier
        .AddItem "A3"
        .Column(1, .ListCount - 1) = 15.6 * gdblMultiplier
        .Column(2, .ListCount - 1) = 10.7 * gdblMultiplier
        .AddItem "A2"
        .Column(1, .ListCount - 1) = 22.4 * gdblMultiplier
        .Column(2, .ListCount - 1) = 15.6 * gdblMultiplier
        .AddItem "A1"
        .Column(1, .ListCount - 1) = 32.2 * gdblMultiplier
        .Column(2, .ListCount - 1) = 22.4 * gdblMultiplier
        .AddItem "A0"
        .Column(1, .ListCount - 1) = 45.9 * gdblMultiplier
        .Column(2, .ListCount - 1) = 32.2 * gdblMultiplier
        .AddItem "MAX"
        .Column(1, .ListCount - 1) = 182 * gdblMultiplier
        .Column(2, .ListCount - 1) = 34.95 * gdblMultiplier
        Dim dblWidth, dblHeight As Double
        If colRegData("UserWidth1") > 0 Then                    ' user fields
            dblWidth = CDbl(colRegData("UserWidth1"))
            dblHeight = CDbl(colRegData("UserHeight1"))
            frmPaperSize.edUserWidth1 = CStr(dblWidth * gdblMultiplier)
            frmPaperSize.edUserHeight1 = CStr(dblHeight * gdblMultiplier)
            .AddItem "USER"
            .Column(1, .ListCount - 1) = CStr(dblWidth * gdblMultiplier)
            .Column(2, .ListCount - 1) = CStr(dblHeight * gdblMultiplier)
        End If
        If colRegData("UserWidth2") > 0 Then                    ' user1 fields
            dblWidth = CDbl(colRegData("UserWidth2"))
            dblHeight = CDbl(colRegData("UserHeight2"))
            frmPaperSize.edUserWidth2 = CStr(dblWidth * gdblMultiplier)
            frmPaperSize.edUserHeight2 = CStr(dblHeight * gdblMultiplier)
            .AddItem "USER1"
            .Column(1, .ListCount - 1) = CStr(dblWidth * gdblMultiplier)
            .Column(2, .ListCount - 1) = CStr(dblHeight * gdblMultiplier)
        End If
        If colRegData("UserWidth3") > 0 Then                    ' user2 fields
            dblWidth = CDbl(colRegData("UserWidth3"))
            dblHeight = CDbl(colRegData("UserHeight3"))
            frmPaperSize.edUserWidth3 = CStr(dblWidth * gdblMultiplier)
            frmPaperSize.edUserHeight3 = CStr(dblHeight * gdblMultiplier)
            .AddItem "USER2"
            .Column(1, .ListCount - 1) = CStr(dblWidth * gdblMultiplier)
            .Column(2, .ListCount - 1) = CStr(dblHeight * gdblMultiplier)
        End If
        If colRegData("UserWidth4") > 0 Then                    ' user3 fields
            dblWidth = CDbl(colRegData("UserWidth4"))
            dblHeight = CDbl(colRegData("UserHeight4"))
            frmPaperSize.edUserWidth4 = CStr(dblWidth * gdblMultiplier)
            frmPaperSize.edUserHeight4 = CStr(dblHeight * gdblMultiplier)
            .AddItem "USER3"
            .Column(1, .ListCount - 1) = CStr(dblWidth * gdblMultiplier)
            .Column(2, .ListCount - 1) = CStr(dblHeight * gdblMultiplier)
        End If
        If colRegData("UserWidth5") > 0 Then                    ' user4 fields
            dblWidth = CDbl(colRegData("UserWidth5"))
            dblHeight = CDbl(colRegData("UserHeight5"))
            frmPaperSize.edUserWidth5 = CStr(dblWidth * gdblMultiplier)
            frmPaperSize.edUserHeight5 = CStr(dblHeight * gdblMultiplier)
            .AddItem "USER4"
            .Column(1, .ListCount - 1) = CStr(dblWidth * gdblMultiplier)
            .Column(2, .ListCount - 1) = CStr(dblHeight * gdblMultiplier)
        End If
    End With
End Sub
Public Sub SetPaperSelection(colRegData As Collection, strStandardPaperSize As String)
    ' take the global size and find it in the list and highlight it
    Dim lngIdx As Long
    gstrStandardPaperSize = strStandardPaperSize
    lngIdx = Lst_Memb_Pos(strStandardPaperSize, frmPaperSize.lstSizes)   ' get the position
    frmPaperSize.lstSizes.Select (lngIdx)                                    ' select it

End Sub
Public Sub LoadPlotLabels()
    ' set up plot dialog labels for plotdraw, plotarea
    ' also set plot inch edit box here
    If gintMetric = 0 Then                                  ' not metric?
        frmPlot.lbPlotDraw.Caption = "Plotted Inches    =     Drawing Units    "
        frmPlot.lblPlotArea.Caption = "Plot Area " & CStr(Format(gdblPaperWidth, "####0.00")) & " by " & CStr(Format(gdblPaperHeight, "####0.00"))
        If frmPlot.ckScaleToFit.Value = False Then          ' scale to fit not selected?
            frmPlot.edPlotInch.Text = "1"
        Else                                                ' is scale to fit
            If gstrRotation = "0" Or gstrRotation = "180" Then
                frmPlot.edPlotInch.Text = CStr(Format(gdblPaperWidth, "####0.00"))
            Else
                frmPlot.edPlotInch.Text = CStr(Format(gdblPaperHeight, "####0.00"))
            End If
        End If
    Else                                                    ' is metric
        frmPlot.lbPlotDraw.Caption = "Plotted MM.       =     Drawing Units    "
        frmPlot.lblPlotArea.Caption = "Plot Area " & CStr(Format(gdblPaperWidth * gconMM, "####0.00")) & " by " & CStr(Format(gdblPaperHeight * gconMM, "####0.00"))
        If frmPlot.ckScaleToFit.Value = False Then
            frmPlot.edPlotInch.Text = gconMM
        Else
            If gstrRotation = "0" Or gstrRotation = "180" Then
                frmPlot.edPlotInch.Text = CStr(Format(gdblPaperWidth * gconMM, "####0.00"))
            Else
                frmPlot.edPlotInch.Text = CStr(Format(gdblPaperHeight * gconMM, "####0.00"))
            End If
        End If
    End If
End Sub
Public Sub SetRotation()
    Select Case gstrRotation
        Case "0"
            frmPlotRotationOrigin.rd0.Value = True
        Case "90"
            frmPlotRotationOrigin.rd90.Value = True
        Case "180"
            frmPlotRotationOrigin.rd180.Value = True
        Case "270"
            frmPlotRotationOrigin.rd270.Value = True
        Case Else
            frmPlotRotationOrigin.rd0.Value = True
    End Select

End Sub
Public Sub RegFlags()
    Dim lngFlags As Long
    Dim strTemp As String
    strTemp = gcolRegData("UserFlags")
    lngFlags = CLng(strTemp)
    If (lngFlags And 16384) = 16384 Then        ' autospool is 16384
        frmPlot.ckAutoSpool.Value = True
        lngFlags = lngFlags - 16384
    End If
    If (lngFlags And 1024) = 1024 Then          ' Rotation is 270
        gstrRotation = "270"
        lngFlags = lngFlags - 1024
    End If
    If (lngFlags And 512) = 512 Then            ' Rotation is 180
        gstrRotation = "180"
        lngFlags = lngFlags - 512
    End If
    If (lngFlags And 256) = 256 Then            ' Rotation is 90
        gstrRotation = "90"
        lngFlags = lngFlags - 256
    End If
    If gstrRotation = "" Then                   ' Rotation is 0
        gstrRotation = "0"
    End If
    If (lngFlags And 64) = 64 Then              ' plot to file
        frmPlot.ckPlotToFile.Value = True
        lngFlags = lngFlags - 64
    End If
    If (lngFlags And 32) = 32 Then              ' adjust area fill
        frmPlot.ckAdjustFill.Value = True
        lngFlags = lngFlags - 32
    End If
    If (lngFlags And 16) = 16 Then              ' hide lines
        frmPlot.ckHideLines.Value = True
        lngFlags = lngFlags - 16
    End If
    If (lngFlags And 6) = 6 Then                ' scale to fit off
        frmPlot.ckScaleToFit.Value = False
        lngFlags = lngFlags - 6
    End If
    If (lngFlags And 4) = 4 Then                ' scale to fit on
        frmPlot.ckScaleToFit.Value = True
        lngFlags = lngFlags - 4
    End If

End Sub
Public Sub Main()
    frmPlot.Show
End Sub

Public Function View_Corners() As Variant
' calculate the corners of the current view
' and return them in a variant array
' first 3 elements are the Lower left corner
' last 3 elemts are the upper right corner
' this is better than extmin and extmax because it gives accurate results
' even when there are no entities
    Dim dist, org, result As Variant
    Dim pnts(5), distx, disty, ratio, viewsize, orgx, orgy, orgz As Double
    
    dist = ThisDrawing.GetVariable("Screensize")
    viewsize = ThisDrawing.GetVariable("viewsize")
    org = ThisDrawing.GetVariable("viewctr")
    distx = dist(0)
    disty = dist(1)
    ratio = distx / disty
    distx = ratio * viewsize
    disty = viewsize
    orgx = org(0): orgy = org(1): orgz = org(2)
    pnts(0) = orgx + (-1 * (0.5 * distx))
    pnts(1) = orgy + (-1 * (0.5 * disty))
    pnts(2) = orgz
    pnts(3) = orgx + (0.5 * distx)
    pnts(4) = orgy + (0.5 * disty)
    pnts(5) = orgz
    result = pnts
    
    View_Corners = result
End Function
Public Sub testit()
    Dim myvar As Variant
    myvar = View_Corners
    Dim i As Integer
    Dim pnt1(2) As Double
    Dim pnt2(2) As Double
    
    For i = 0 To 2
         pnt1(i) = myvar(i)
    Next i
    Dim j As Integer
    j = 0
    For i = 3 To 5
         pnt2(j) = myvar(i)
         j = j + 1
    Next i
    Debug.Print ThisDrawing.ModelSpace.AddCircle(pnt1, 1)
    Debug.Print ThisDrawing.ModelSpace.AddCircle(pnt2, 1)
    
End Sub

Attribute VB_Name = "basRegistry"
Option Explicit
Global Const gintMAX_SIZE As Integer = 50
Global Const gstrNULL$ = ""                             'Empty string


Public Sub RegExample()
    frmRegAccess.Show
End Sub
'
'     [strSection] - section where key is found
'     [strKey] - name of key to get the value of
'
'-----------------------------------------------------------
'
Public Function ReadRegistry(ByVal strAppName, ByVal strSection As String, ByVal strKey As String) As String
'    Stop
    Dim strResult As String
    On Error Resume Next                        ' getsetting throws an error if all
                                                ' arguments are not present
    strResult = GetSetting(strAppName, strSection, strKey)  ' get the data
    'Debug.Print Err.Number
    If Err.Number > 0 Then                      ' Was an error thrown?
        ReadRegistry = gstrNULL                 ' return nothing
    Else
        ReadRegistry = strResult                ' return the item
    End If
End Function
Public Function WriteRegistry(ByVal strAppName, ByVal strSection As String, ByVal strKey As String, ByVal strItem As String)
'    Stop
    Dim strResult As String
    Dim intPos As Integer

    Call SaveSetting(strAppName, strSection, strKey, strItem)
    If Err.Number > 0 Then
        Debug.Print "failure"
    Else
        MsgBox "Data sucessfully written to the Registry Key. "
    End If
End Function
Public Function ReadAllRegistry(ByVal strAppName, ByVal strSection As String) As Variant
    
    Dim MySettings As Variant
    ReadAllRegistry = GetAllSettings(strAppName, strSection)


End Function

Function StripTerminator(ByVal strString As String) As String
' returns the string with out the terminator or any characters following it
' or it returns the original string when no terminator present
    Dim intZeroPos As Integer

    intZeroPos = InStr(strString, Chr$(0))                  'get terminators position
    If intZeroPos > 0 Then
        StripTerminator = Left$(strString, intZeroPos - 1)  'get up to it
    Else
        StripTerminator = strString                         ' no, return the string
    End If
End Function

Attribute VB_Name = "basToolbox"
Const gconSEP_DIR As String = "\"

Public Function parse(strLine As String, strDelimit As String, lngPosition As Long) As String
' this function takes the
'                                    position    position   position
'                                       1            2         3
' strLine holds the string  ie. "All good | men are | leaving the boat."
'                                              ^
'                                           boundary
' strdelimit is a one character string containing the delimiter to be used
' tempvar is returned
' lngPosition is what information position in the string you want
' Lpipe and Rpipe are the boundaries around the data

    Dim c As Long
    Dim Lpipe As Long
    Dim Rpipe As Long
    Dim mark As Long
    Dim tempvar As String
    Dim start As Long
    Dim datalen As Long
    Dim cnt As Long
    c = 1
    Lpipe = 0
    mark = 1
    tempvar = ""
    For cnt = 1 To lngPosition
        Do While Mid(strLine, c, 1) <> strDelimit And Len(strLine) >= c
            c = c + 1
        Loop
        Rpipe = c
        If mark = lngPosition - 1 Then
            Lpipe = c
        End If
        c = c + 1
        mark = mark + 1
    Next cnt
    start = Lpipe + 1
    datalen = (Rpipe - Lpipe) - 1
    parse = Mid(strLine, start, datalen)
End Function
Public Function chk_plural(var As Long, mode As Long)
' var is a passed in length of some item and mode is the type of word to return
' if the var is equal to zero or the var is greater than 1 then a plural is returned
' this function is used to create correct sentence structure for messages or
' data output.
' ie. You spin through a list of items and find none present and want to tell the
' user. Take the number of items found and build your sentence like this:

' inti = 5
' MsgBox CStr(inti) & " item" & chk_plural(inti, 1) & " " & chk_plural(inti, 4) & _
'        " been found."
        
    Dim plural As Boolean
    If var = 0 Or var > 1 Then plural = True
    
    Select Case mode
        Case 1
            If plural = True Then
                chk_plural = "s"
            Else
                chk_plural = ""
            End If
        Case 2
            If plural = True Then
                chk_plural = "are"
            Else
                chk_plural = "is"
            End If
        Case 3
            If plural = True Then
                chk_plural = "were"
            Else
                chk_plural = "was"
            End If
        Case 4
            If plural = True Then
                chk_plural = "have"
            Else
                chk_plural = "has"
            End If
        Case Else
            plural = ""
    End Select

End Function
Public Function FindFile(Filename As String) As Boolean
    
    Dim fname As String
    Dim varResult As Boolean
    fname = Dir(Filename)
    If Len(fname) = 0 Then
        varResult = False
    Else
        varResult = True
    End If
    FindFile = varResult

End Function

Public Sub Fatal_error(error As Long, ByVal data As String)
' call this function as fatal_error erronum, data
' notice that you do not use () around the arguments when calling

    Select Case error
    Case 1
       MsgBox "Error code 1: Could not find the file " & _
                      UCase(data) & ". Please contact your supervisor."
    Case 2
        MsgBox "Error code 2: Could not open the file " & _
                      UCase(data) & ". Please contact your supervisor."
    Case 3
        MsgBox "Error code 3: Could not find the section header " & _
               "[" & UCase(data) & "]." & _
               " Please contact your supervisor."
    Case 4
        MsgBox "Error code 4: Could not find the key " & _
                UCase(data) & ". Please contact your supervisor."
    Case Else   ' Other values.
        MsgBox "Unknown error code " & CStr(error) & " for the data " & UCase(data) & _
               "Please contact your supervisor."
    End Select
    End         ' terminate the program
    
End Sub
Public Function count_occurrences(line As String, strDelimit As String) As Long
' returns how many delimiters are in the line
    Dim i, cnt As Long
    cnt = 0
    For i = 1 To Len(line)
        If strDelimit = Mid(line, i, Len(strDelimit)) Then
            cnt = cnt + 1
        End If
    Next i
    
    count_occurrences = cnt

End Function

Public Function Token(line As String, Astring As String) As String
' take astring and return all text up to it from the line string
' if astring is not present in the line - return the whole line
    Dim x As Variant
    x = InStr(1, line, Astring)
    If x Then
       Token = Mid(line, 1, x - 1)
    Else
       Token = line
    End If
End Function

Public Function RightToken(line As String, Astring As String) As String
' take astring and return everything from line starting with astring
' if astring is not present in the line - return the whole line
    Dim x As Variant
    x = InStr(1, line, Astring)
    If x Then
       RightToken = Mid(line, x, Len(line))
    Else
       RightToken = line
    End If
End Function

Public Function strip_path(line As String) As String
    Dim dname As String
    Dim cnt As Long
    Dim ct As Long
    dname = UCase(line)
    If Mid(line, 2, 1) = ":" Then
        dname = Mid(dname, 3, Len(line))
    End If
    cnt = 1
    ct = 0
    Dim i As Long
    For i = 1 To Len(dname)
        If Mid(dname, cnt, 1) = "\" Then
            ct = cnt
        End If
        cnt = cnt + 1
    Next i
    strip_path = Mid(dname, ct + 1, Len(dname))

End Function

Public Function spin(spinner As String) As String

Select Case spinner
    Case ""
        spin = "-"
    Case " "
        spin = "-"
    Case "-"
        spin = "\"
    Case "\"
        spin = "|"
    Case "|"
        spin = "/"
    Case "/"
        spin = "-"
    Case Else   ' Other values.
        spin = spinner
End Select

End Function
Public Function AddDirSep(strPathName As String) As String
' adds a backslash to the end of a directory string
' gstrSEP_DIR is a global constant
    If Right$(RTrim$(strPathName), Len(gconSEP_DIR)) <> gstrSEP_DIR Then
        strPathName = RTrim$(strPathName) & gconSEP_DIR                 ' add it when not on the end
    End If
    AddDirSep = strPathName
End Function
Public Function add_backslashes(dirstr As String)
' this function is necessary when writing out AutoLISP code that includes directories
' Since AutoLISP needs either two backslashes or one forward slash
    Dim i As Long
    Dim holdstr As String
    For i = 1 To Len(dirstr)
        If Mid(dirstr, i, 1) = "\" Then
            holdstr = holdstr & Mid(dirstr, i, 1) & "\"
        Else
            holdstr = holdstr & Mid(dirstr, i, 1)
        End If
    Next i
    add_backslashes = holdstr
End Function
Public Function Lst_Memb(line As String, ctrl As ListBox) As Boolean
' check to see if line argument is in the list control
    Dim temp As Variant
    Dim i As Long
    Dim result As Boolean
    result = False
    For i = 0 To ctrl.ListCount - 1
        ctrl.ListIndex = i
        temp = ctrl.Text
        If temp = line Then
            result = True
        End If
        
    Next i
    
    Lst_Memb = result
End Function
Public Function Lst_Memb_Pos(line As String, ctrl As ListBox) As Long
' check to see if line argument is in the list control
' if there return the index number
' if not return 0
    Dim temp As Variant
    Dim i As Long
    Dim result As Long
    result = 0
    For i = 0 To ctrl.ListCount - 1
        ctrl.ListIndex = i
        temp = ctrl.Text
        If temp = line Then
            result = ctrl.ListIndex
            Exit For
        End If
    Next i
    Lst_Memb_Pos = result
End Function

Public Function Lst_Memb_VB(line As String, ctrl As Control) As Boolean
' This is a VB version that
' checks to see if line argument is in the list control
    Dim temp As String
    Dim i As Long
    Dim result As Boolean
    result = False
    For i = 0 To ctrl.ListCount - 1
        temp = ctrl.ItemData(i)
        temp = ctrl.Text
        If temp = line Then
            result = True
        End If
        
    Next i
    
    Lst_Memb = result
End Function

Public Function Enttype(Ent As Object) As String
        
        Select Case Ent.EntityType
            Case acArc
                Enttype = "ARC"
            Case acCircle
                Enttype = "CIRCLE"
            Case acEllipse
                Enttype = "ELLIPSE"
            Case acLine
                Enttype = "LINE"
            Case acPoint
                Enttype = "POINT"
            Case acRay
                Enttype = "RAY"
            Case ac3dFace
                Enttype = "3DFACE"
            Case ac3dPolyline
                Enttype = "3DPLINE"
            Case ac3dSolid
                Enttype = "3DSOLID"
            Case acAttribute
                Enttype = "ATTRIBUTE"
            Case acDimAligned
                Enttype = "DIMALIGNED"
            Case acDimAngular
                Enttype = "DIMANGULAR"
            Case acDimDiametric
                Enttype = "DIMDIAMETRIC"
            Case acDimOrdinate
                Enttype = "DIMORDINATE"
            Case acDimRadial
                Enttype = "DIMRADIAL"
            Case acDimRotated
                Enttype = "DIMROTATED"
            Case acGroup
                Enttype = "GROUP"
            Case acHatch
                Enttype = "HATCH"
            Case acLeader
                Enttype = "LEADER"
            Case acMtext
                Enttype = "MTEXT"
            Case acPolyline
                Enttype = "PLINE"
            Case acPolylineLight
                Enttype = "LTPLINE"
            Case acPolymesh
                Enttype = "PMESH"
            Case acRaster
                Enttype = "RASTER"
            Case acRegion
                Enttype = "REGION"
            Case acShape
                Enttype = "SHAPE"
            Case acSolid
                Enttype = "SOLID"
            Case acSpline
                Enttype = "SPLINE"
            Case acText
                Enttype = "TEXT"
            Case acTolerance
                Enttype = "TOLERANCE"
            Case acTrace
                Enttype = "TRACE"
            Case acXline
                Enttype = "XLINE"
            Case Else
                Enttype = "UNKNOWN"
        End Select

End Function
Public Function DoesControlExist(Form As UserForm, ctrlName As String) As Boolean
' this function takes the userform and the suspected control name and verifies
' whether or not the control is present on the form
' True is returned when it is found and false when it is not found
' The control name is case sensitive normally so ucase is used to illiminate the
' problem
        Dim MyControl As Control
        Dim result As Boolean
        result = False
        For Each MyControl In Form.Controls
            If UCase(MyControl.Name) = UCase(ctrlName) Then
                result = True
                Exit For
            End If
        Next
        DoesControlExist = result
End Function


Public Function Strip_extension(Filename As String) As String
' This function takes a string containing a filename and
' returns the filename without the extension as a string
' should no extension be present in the filename, the filename is returned
    Dim Extension As String
    Extension = InStr(Filename, ".")
    If Extension > 0 Then
        Strip_extension = Left(Filename, Extension - 1)
    Else
        Strip_extension = Filename
    End If
    
End Function

Public Function Lst_Memb_Idx(line As String, ctrl As Control) As Long
' check to see if line argument is in the list control
    Dim temp As String
    Dim i As Long
    Dim result As Long
    result = 0
'    i = 0
    For i = 0 To ctrl.ListCount - 1
        temp = ctrl.List(i, 1)
        If temp = line Then
            result = i
        End If
        
    Next i
    Lst_Memb_Idx = result
End Function

Attribute VB_Name = "frmDeviceDefault"
Attribute VB_Base = "0{F6EB6EF1-3710-11D2-99EF-00609761BD90}{F6EB6ECF-3710-11D2-99EF-00609761BD90}"
Attribute VB_Creatable = False
Attribute VB_PredeclaredId = True
Attribute VB_Exposed = False
Attribute VB_TemplateDerived = False
Attribute VB_Customizable = False
Option Explicit

Private Sub btnCancel_Click()
    Me.Hide
End Sub

Private Sub btnHelp_Click()
    MsgBox "Help currently unavailable", , "Help"
End Sub

Private Sub btnOK_Click()
    lngSetPlotter = lstDeviceCfg.Value
    Me.Hide
End Sub

Private Sub btnReplacePc2_Click()
    cmdFileIO.Filter = "(*.pc2)|*.pc2"                  ' Specify default filter
    cmdFileIO.FilterIndex = 0                           ' set focus of type
    cmdFileIO.DialogTitle = "Replace from PC2 File"     ' Dialog caption
    cmdFileIO.Filename = ""                             ' default name
    cmdFileIO.Flags = &H4                               ' read only box invisible
    cmdFileIO.CancelError = True                        ' enable cancel tracking
    On Error Resume Next                                ' set up for checking for cancel
    cmdFileIO.ShowOpen                                  ' show it
    If Err.Number <> 0 Then                             ' greater than 0 if canceled
        If Err.Number = 32755 Then
            Debug.Print "User canceled."
        End If
    Else
        ThisDrawing.plot.LoadPC2 cmdFileIO.Filename     ' save the selected filename
    End If

End Sub

Private Sub btnSavePc2_Click()
    cmdFileIO.Filter = "(*.pc2)|*.pc2"                  ' Specify default filter
    cmdFileIO.FilterIndex = 0                           ' set focus of type
    cmdFileIO.DialogTitle = "Save PC2 File"             ' Dialog caption
    Dim strFileName As String
    strFileName = ThisDrawing.GetVariable("dwgname")    ' get drawing name
    strFileName = Strip_extension(strFileName)          ' take off extension
    cmdFileIO.Filename = strFileName & ".pc2"           ' default name
    cmdFileIO.Flags = &H4                               ' read only box invisible
    cmdFileIO.CancelError = True                        ' enable cancel tracking
    On Error Resume Next                                ' set up for checking for cancel
    cmdFileIO.ShowSave                                  ' show it
    If Err.Number <> 0 Then                             ' greater than 0 if canceled
        If Err.Number = 32755 Then
            Debug.Print "User canceled."
        End If
    Else
        ThisDrawing.plot.SavePC2 cmdFileIO.Filename     ' save the selected filename
    End If

End Sub

Private Sub UserForm_Initialize()
    Dim Plotters As Variant
    Plotters = GetPlotters()            ' get any plotters
    If Not IsEmpty(Plotters) Then
        lstDeviceCfg.List = Plotters    ' load the plotters into the listbox
        ' now figure out which list item is the current plotter
        ' and highlight it
        Dim lngPlotter, lngItemLineNumber As Long
        lngPlotter = ThisDrawing.GetVariable("Plotter") ' get current plotter number
        ' pass the number (converted to a string for comparison) and the listbox
        ' to a function that returns the index number of the item
        lngItemLineNumber = Lst_Memb_Idx(CStr(lngPlotter), frmDeviceDefault.lstDeviceCfg)
        ' use the index to highlight the item line
        lstDeviceCfg.Text = lstDeviceCfg.List(lngItemLineNumber)
        lblManufacturerData.Caption = gcolRegData("Manufacturer")
        lblPortData.Caption = gcolRegData("PortName")
    End If

End Sub

Attribute VB_Name = "frmOptimizePenMotion"
Attribute VB_Base = "0{F6EB6EED-3710-11D2-99EF-00609761BD90}{F6EB6ED3-3710-11D2-99EF-00609761BD90}"
Attribute VB_Creatable = False
Attribute VB_PredeclaredId = True
Attribute VB_Exposed = False
Attribute VB_TemplateDerived = False
Attribute VB_Customizable = False
Option Explicit

Private Sub btnCancel_Click()
    Me.Hide
End Sub

Private Sub btnOK_Click()
    Me.Hide
End Sub
Private Sub Do_Pens(Toggle As Control)

End Sub
Private Sub chkNoOpt_Change()
    If chkNoOpt.Value = True Then
       ' frmOptimizePenMotion.chkEndSwap.Value = False
       ' frmOptimizePenMotion.chkPenSort.Value = False
       ' frmOptimizePenMotion.chkLimitMotion.Value = False
       ' frmOptimizePenMotion.chkFullMotion.Value = False
       ' frmOptimizePenMotion.chkElimHorz.Value = False
       ' frmOptimizePenMotion.chkElimDiag.Value = False
    End If

End Sub

Private Sub chkEndSwap_Change()
    If chkEndSwap.Value = True Then
        'frmOptimizePenMotion.chkNoOpt.Value = False
        'frmOptimizePenMotion.chkPenSort.Value = False
        'frmOptimizePenMotion.chkLimitMotion.Value = False
        'frmOptimizePenMotion.chkFullMotion.Value = False
        'frmOptimizePenMotion.chkElimHorz.Value = False
        'frmOptimizePenMotion.chkElimDiag.Value = False
    End If
End Sub

Private Sub chkPenSort_Change()
    
    If chkPenSort.Value = True Then
        frmOptimizePenMotion.chkEndSwap.Value = True
        'frmOptimizePenMotion.chkPenSort.Value = False
        'frmOptimizePenMotion.chkLimitMotion.Value = False
        'frmOptimizePenMotion.chkFullMotion.Value = False
        'frmOptimizePenMotion.chkElimHorz.Value = False
        'frmOptimizePenMotion.chkElimDiag.Value = False
    End If
End Sub
Private Sub chkLimitMotion_Click()
    If chkLimitMotion.Value = True Then
        frmOptimizePenMotion.chkEndSwap.Value = True
        frmOptimizePenMotion.chkPenSort.Value = True
        'frmOptimizePenMotion.chkFullMotion.Value = False
        'frmOptimizePenMotion.chkElimHorz.Value = False
        'frmOptimizePenMotion.chkElimDiag.Value = False
    End If
End Sub

Private Sub chkFullMotion_Click()
    If chkFullMotion.Value = True Then
        frmOptimizePenMotion.chkEndSwap.Value = True
        frmOptimizePenMotion.chkPenSort.Value = True
        frmOptimizePenMotion.chkLimitMotion.Value = True
        'frmOptimizePenMotion.chkElimHorz.Value = False
        'frmOptimizePenMotion.chkElimDiag.Value = False
    End If
End Sub

Private Sub chkElimHorz_Click()
    If chkElimHorz.Value = True Then
        frmOptimizePenMotion.chkEndSwap.Value = True
        frmOptimizePenMotion.chkPenSort.Value = True
        frmOptimizePenMotion.chkLimitMotion.Value = True
        frmOptimizePenMotion.chkFullMotion.Value = True
        'frmOptimizePenMotion.chkElimDiag.Value = False
    End If
End Sub

Private Sub chkElimDiag_Click()
    If chkElimDiag.Value = True Then
        frmOptimizePenMotion.chkEndSwap.Value = True
        frmOptimizePenMotion.chkPenSort.Value = True
        frmOptimizePenMotion.chkLimitMotion.Value = True
        frmOptimizePenMotion.chkFullMotion.Value = True
        frmOptimizePenMotion.chkElimHorz.Value = True
    End If
End Sub

Private Sub UserForm_Initialize()
    LoadOptimizationDialog gcolRegData

End Sub

Attribute VB_Name = "frmPaperSize"
Attribute VB_Base = "0{F6EB6EF5-3710-11D2-99EF-00609761BD90}{F6EB6ED1-3710-11D2-99EF-00609761BD90}"
Attribute VB_Creatable = False
Attribute VB_PredeclaredId = True
Attribute VB_Exposed = False
Attribute VB_TemplateDerived = False
Attribute VB_Customizable = False
Option Explicit
Public dblPaperMaxWidth As Double
Public dblPaperMaxHeight As Double

Private Sub btnCancel_Click()
    Me.Hide
End Sub

Private Sub btnOK_Click()
    gstrStandardPaperSize = lstSizes.Text
    gdblPaperWidth = lstSizes.Column(1, lstSizes.ListIndex)
    gdblPaperHeight = lstSizes.Column(2, lstSizes.ListIndex)
    LoadPlotLabels
    Me.Hide
End Sub

Private Sub edUserWidth1_Enter()
    lblWarning.Caption = ""                             ' clear any warnings

End Sub
Private Sub edUserWidth2_Enter()
    lblWarning.Caption = ""                             ' clear any warnings

End Sub
Private Sub edUserWidth3_Enter()
    lblWarning.Caption = ""                             ' clear any warnings

End Sub
Private Sub edUserWidth4_Enter()
    lblWarning.Caption = ""                             ' clear any warnings

End Sub
Private Sub edUserWidth5_Enter()
    lblWarning.Caption = ""                             ' clear any warnings

End Sub
Private Sub edUserHeight1_Enter()
    lblWarning.Caption = ""                             ' clear any warnings

End Sub
Private Sub edUserHeight2_Enter()
    lblWarning.Caption = ""                             ' clear any warnings

End Sub
Private Sub edUserHeight3_Enter()
    lblWarning.Caption = ""                             ' clear any warnings

End Sub
Private Sub edUserHeight4_Enter()
    lblWarning.Caption = ""                             ' clear any warnings

End Sub
Private Sub edUserHeight5_Enter()
    lblWarning.Caption = ""                             ' clear any warnings

End Sub

Private Sub edUserHeight1_Change()
    If CDbl(edUserHeight1.Text) > dblPaperMaxHeight * gdblMultiplier Then  ' if to big warn them
        lblWarning.Caption = "WARNING:  Paper height is greater than driver MAX height."
    End If

End Sub

Private Sub edUserHeight2_Change()
    If CDbl(edUserHeight2.Text) > dblPaperMaxHeight * gdblMultiplier Then   ' if to big warn them
        lblWarning.Caption = "WARNING:  Paper height is greater than driver MAX height."
    End If

End Sub

Private Sub edUserHeight3_Change()
    If CDbl(edUserHeight3.Text) > dblPaperMaxHeight * gdblMultiplier Then   ' if to big warn them
        lblWarning.Caption = "WARNING:  Paper height is greater than driver MAX height."
    End If

End Sub

Private Sub edUserHeight4_Change()
    If CDbl(edUserHeight4.Text) > dblPaperMaxHeight * gdblMultiplier Then   ' if to big warn them
        lblWarning.Caption = "WARNING:  Paper height is greater than driver MAX height."
    End If

End Sub

Private Sub edUserHeight5_Change()
    If CDbl(edUserHeight5.Text) > dblPaperMaxHeight * gdblMultiplier Then   ' if to big warn them
        lblWarning.Caption = "WARNING:  Paper height is greater than driver MAX height."
    End If

End Sub

Private Sub edUserWidth1_Change()
    If CDbl(edUserWidth1.Text) > dblPaperMaxWidth * gdblMultiplier Then   ' if to big warn them
        lblWarning.Caption = "WARNING:  Paper width is greater than driver MAX width."
    End If
    If Len(edUserWidth1.Text) > 0 And Len(edUserWidth1.Text) > 0 Then
    End If
End Sub

Private Sub edUserWidth2_Change()
    If CDbl(edUserWidth2.Text) > dblPaperMaxWidth * gdblMultiplier Then   ' if to big warn them
        lblWarning.Caption = "WARNING:  Paper width is greater than driver MAX width."
    End If

End Sub

Private Sub edUserWidth3_Change()
    If CDbl(edUserWidth3.Text) > dblPaperMaxWidth * gdblMultiplier Then   ' if to big warn them
        lblWarning.Caption = "WARNING:  Paper width is greater than driver MAX width."
    End If

End Sub

Private Sub edUserWidth4_Change()
    If CDbl(edUserWidth4.Text) > dblPaperMaxWidth * gdblMultiplier Then   ' if to big warn them
        lblWarning.Caption = "WARNING:  Paper width is greater than driver MAX width."
    End If

End Sub

Private Sub edUserWidth5_Change()
    If CDbl(edUserWidth5.Text) > dblPaperMaxWidth * gdblMultiplier Then   ' if to big warn them
        lblWarning.Caption = "WARNING:  Paper width is greater than driver MAX width."
    End If

End Sub

Private Sub rdLandscape_Click()
    fmOrientation.Tag = "Landscape"
End Sub

Private Sub rdPortrait_Click()
    fmOrientation.Tag = "Portrait"
End Sub

Private Sub UserForm_Initialize()
    rdLandscape.Value = True
    dblPaperMaxWidth = CDbl(gcolRegData("MaxWidth"))
    dblPaperMaxHeight = CDbl(gcolRegData("MaxHeight"))
    LoadPaperSizeDialog gcolRegData                             ' load the dialog
    ' get the stored standard paper size
    Dim strSize As String
    strSize = gcolRegData.Item("StandardSize")
    SetPaperSelection gcolRegData, strSize

End Sub

Attribute VB_Name = "frmPlot"
Attribute VB_Base = "0{F6EB6EDD-3710-11D2-99EF-00609761BD90}{F6EB6EC7-3710-11D2-99EF-00609761BD90}"
Attribute VB_Creatable = False
Attribute VB_PredeclaredId = True
Attribute VB_Exposed = False
Attribute VB_TemplateDerived = False
Attribute VB_Customizable = False
Option Explicit
Private Sub bthHelp_Click()
    MsgBox "Help currently unavailable", , "Help"
End Sub
Private Sub btnCancel_Click()
    End
End Sub
Private Sub btnDeviceDefault_Click()
    frmDeviceDefault.Show

End Sub

Private Sub btnFileName_Click()
    cmdDia.Filter = "(*.plt)|*.plt"                  ' Specify default filter
    cmdDia.FilterIndex = 0                           ' set focus of type
    cmdDia.DialogTitle = "Creat Plot File"           ' Dialog caption
    Dim strFileName As String
    strFileName = ThisDrawing.GetVariable("DWGNAME") ' default name
    strFileName = Strip_extension(strFileName)
    cmdDia.Filename = strFileName & ".plt"
    cmdDia.Flags = &H4                               ' read only box invisible
    cmdDia.CancelError = True                        ' enable cancel tracking
    On Error Resume Next                             ' set up for checking for cancel
    cmdDia.ShowOpen                                  ' show it
    If Err.Number <> 0 Then                          ' greater than 0 if canceled
        If Err.Number = 32755 Then
            Debug.Print "User canceled."
        End If
    Else
        gstrPlotFileName = cmdDia.Filename
    End If
    
End Sub

Private Sub btnOK_Click()
    Dim Found_Entry As Boolean
    Found_Entry = False                     ' default initialization is false but always good to be safe
    If Len(cbProjects.Text) <> 0 Then       ' got any info in the list?
        ' yes
        If Not IsEmpty(gvarProjects) Then   ' if registry info exists
            Dim intI As Integer
            ' check to see if the selected item is already in the registry returned
            ' during the initialization process or was it a new entry?
            For intI = LBound(gvarProjects, 1) To UBound(gvarProjects, 1)
                If cbProjects.Text = gvarProjects(intI, 0) Then
                    Found_Entry = True
                End If
            Next intI
        End If
        If Not Found_Entry Then
            ' item is not already in the registry, must be a new project
            ' add the default info to the registry for the new entry before proceeding
            ' first add it to the projects list so we can find it later
            Debug.Print WriteRegistry(gconAppname, gconSectionName, cbProjects.Text, "")
            ' now add any actual section, key and item information
            ' This one is an example of keeping track of how many plots have been plotted for this project
            ' so set a new projects plot count to zero
            Debug.Print WriteRegistry(gconAppname, gconSectionName & "\" & cbProjects.Text, gconPlotCount, 0)
            'end
        End If
        ' now that any new project has been taken care of
        ' lets process the plot related datA before actually plotting
        Dim lngPlotCount As Long
        ' Get the plot count for the project
        lngPlotCount = ReadRegistry(gconAppname, gconSectionName & "\" & cbProjects.Text, gconPlotCount)
        lngPlotCount = lngPlotCount + 1     ' bump the plot count for the project by 1
        ' now write it back to the registry
        Debug.Print WriteRegistry(gconAppname, gconSectionName & "\" & cbProjects.Text, gconPlotCount, lngPlotCount)
        ' now actually plot it
        GoPlot
    Else
        ' no info in list box
        MsgBox "You must fill out the project name before plotting.", , "Error"
    End If
End Sub
Public Sub GoPlot()
    ThisDrawing.plot.AdjustAreaFill = frmPlot.ckAdjustFill
    ThisDrawing.plot.HideLines = frmPlot.ckHideLines
    ThisDrawing.plot.Rotation = CLng(frmPlotRotationOrigin.fmPlotRotation.Tag)
    'ThisDrawing.plot.PlotOrientation
    Dim dblaryPnt(2) As Double
    dblaryPnt(0) = CDbl(0)
    dblaryPnt(1) = CDbl(0)
    dblaryPnt(2) = CDbl(0)
    dblaryPnt(0) = dblaryPnt(0) + CDbl(frmPlotRotationOrigin.edXOrigin)
    dblaryPnt(1) = dblaryPnt(1) + CDbl(frmPlotRotationOrigin.edYOrigin)
    Dim varPnt As Variant
    varPnt = dblaryPnt
    ThisDrawing.plot.Origin = varPnt
    Select Case frmPaperSize.fmOrientation.Tag
        Case "Landscape"
            ThisDrawing.plot.PlotOrientation = acPlotOrientationLandscape
        Case "Portrait"
            ThisDrawing.plot.PlotOrientation = acPlotOrientationPortrait
        Case Else
            ThisDrawing.plot.PlotOrientation = acPlotOrientationLandscape
    End Select
    Select Case frmPlot.frmSizeOrientation.Tag
        Case "Inches"
            ThisDrawing.plot.PlotUnits = acEnglish
        Case "Metric"
            ThisDrawing.plot.PlotUnits = acMetric
        Case Else
            ThisDrawing.plot.PlotUnits = acEnglish
    End Select
    Select Case frmParameters.Tag
        Case "D"
            
        Case "E"
            ' the only way to do this is to zoom extents and then
            ' put the view back where it was when done
            ' since the plotting will take place later in the routine, set a flag
            ' that we used zoom
            Dim pnts As Variant
            pnts = View_Corners
            Dim i As Integer
            Dim llpnt(2) As Double
            Dim urpnt(2) As Double
            For i = 0 To 2
                 llpnt(i) = pnts(i)
            Next i
            Dim j As Integer
            j = 0
            For i = 3 To 5
                 urpnt(j) = pnts(i)
                 j = j + 1
            Next i
            ThisDrawing.ActiveViewport.ZoomExtents
            ThisDrawing.plot.PlotExtents
        Case "L"
            ThisDrawing.plot.PlotLimits
        Case "V"
            ThisDrawing.plot.PlotView frmViewName.lstViewName.List(frmViewName.lstViewName.ListIndex)
        Case "W"
            Dim llCorner(2) As Double
            Dim urCorner(2) As Double
            llCorner(0) = CDbl(frmWindowSelection.edFirstX.Text)
            llCorner(1) = CDbl(frmWindowSelection.edFirstY.Text)
            llCorner(2) = CDbl(0)
            urCorner(0) = CDbl(frmWindowSelection.edOtherX.Text)
            urCorner(1) = CDbl(frmWindowSelection.edOtherY.Text)
            urCorner(2) = CDbl(0)
            ThisDrawing.plot.PlotWindow llCorner, urCorner
    End Select
    Dim newPaperSize(0 To 1) As Double
    newPaperSize(0) = CDbl(frmPaperSize.lstSizes.List(frmPaperSize.lstSizes.ListIndex, 1))
    newPaperSize(1) = CDbl(frmPaperSize.lstSizes.List(frmPaperSize.lstSizes.ListIndex, 2))
    ThisDrawing.plot.PaperSize = newPaperSize
    Debug.Print ThisDrawing.plot.PlotScale(0)
    Debug.Print ThisDrawing.plot.PlotScale(1)
    
    If frmPlot.ckPlotToFile.Value = True Then
        ThisDrawing.plot.PlotToFile cmdDia.Filename
    Else
        ThisDrawing.plot.PlotToDevice frmDeviceDefault.lstDeviceCfg.List(frmDeviceDefault.lstDeviceCfg.ListIndex)
    End If
    If frmParameters.Tag = "E" Then
        ThisDrawing.ActiveViewport.ZoomWindow llpnt, urpnt
    End If

End Sub

Private Sub btnOptimize_Click()
    frmOptimizePenMotion.Show
End Sub

Private Sub btnPreview_Click()
    If rdFull = True Then
        Me.Hide
        ThisDrawing.plot.PlotPreview 1
        Me.Show
    Else
        ThisDrawing.plot.PlotPreview 0
    End If
End Sub

Private Sub btnRotateOrigin_Click()
    If gintMetric = 0 Then              ' if not metric
        frmPlotRotationOrigin.edXOrigin.Text = CStr(Format(gdblWidthOrigin, "####0.00"))
        frmPlotRotationOrigin.edYOrigin.Text = CStr(Format(gdblHeightOrigin, "####0.00"))
    Else
        frmPlotRotationOrigin.edXOrigin.Text = CStr(Format(gdblWidthOrigin * gconMM, "####0.00"))
        frmPlotRotationOrigin.edYOrigin.Text = CStr(Format(gdblHeightOrigin * gconMM, "####0.00"))
    End If
    SetRotation
    frmPlotRotationOrigin.Show
End Sub
Private Sub btnSize_Click()
    frmPaperSize.Show
End Sub

Private Sub btnView_Click()
    frmViewName.Show
End Sub

Private Sub btnWindow_Click()
    gbolPlotFormState = True
    frmWindowSelection.Show
End Sub

Private Sub ckAutoSpool_Click()
    If ckAutoSpool.Value = True Then        ' if autospool checked
        btnFileName.Enabled = False         ' disable the file name button
    Else
        If ckPlotToFile.Value = True Then   ' if plot to file is checked
            btnFileName.Enabled = True      ' enable the file name button
        Else                                ' no
            btnFileName.Enabled = False     ' disable the button
        End If
    End If
End Sub

Private Sub ckPlotToFile_Click()
    If ckPlotToFile.Value = True Then       ' if plot to file is checked
        btnFileName.Enabled = True          ' enable the filename button
        ckAutoSpool.Enabled = True          ' enable the autospool check box
    Else                                    ' no
        btnFileName.Enabled = False         ' disable the file name button
        ckAutoSpool.Value = False           ' uncheck the autospool check box
        ckAutoSpool.Enabled = False         ' diable the autospool check box
    End If
End Sub

Private Sub ckScaleToFit_Click()
    If ckScaleToFit.Value = True Then                   ' is it selected?
        LoadPlotLabels
        frmPlot.edPlotInch.Enabled = False              ' disable Inches box
        frmPlot.edDrawUnit.Enabled = False              ' disable drawing unit box
        frmPlot.edPlotInch.BackColor = vbMenuBar        ' change background color of inches
        frmPlot.edDrawUnit.BackColor = vbMenuBar        ' change background color of drawing units box
    Else
        LoadPlotLabels
        frmPlot.edPlotInch.Enabled = True               ' enable inches
        frmPlot.edDrawUnit.Enabled = True               ' enable drawing units
        frmPlot.edPlotInch.BackColor = vbWindowBackground   ' set background color
        frmPlot.edDrawUnit.BackColor = vbWindowBackground   ' set background color
        frmPlot.edDrawUnit.Text = "1"                       ' put 1 in box
    End If
End Sub

Private Sub ckTextFill_Click()
    If ckTextFill.Value = True Then
        ThisDrawing.SetVariable "Textfill", 1
    Else
        ThisDrawing.SetVariable "Textfill", 0
    End If
End Sub

Private Sub rdDisplay_Click()
    frmParameters.Tag = "D"
End Sub
Private Sub rdExtents_Click()
    frmParameters.Tag = "E"
End Sub
Private Sub rdMM_Click()
    frmSizeOrientation.Tag = "Metric"                   ' register selection with the frame
    ThisDrawing.plot.PlotUnits = acMetric
    gintMetric = 1
    LoadPlotLabels
    LoadPaperSizeDialog gcolRegData
    SetPaperSelection gcolRegData, gstrStandardPaperSize
End Sub
Private Sub rdInches_Click()
    frmSizeOrientation.Tag = "Inches"                   ' register selection with the frame
    ThisDrawing.plot.PlotUnits = acEnglish
    gintMetric = 0
    LoadPlotLabels
    LoadPaperSizeDialog gcolRegData
    SetPaperSelection gcolRegData, gstrStandardPaperSize
End Sub
Private Sub rdLimits_Click()
    frmParameters.Tag = "L"
End Sub
Private Sub rdView_Click()
    frmParameters.Tag = "V"
End Sub
Private Sub rdWindow_Click()
    frmParameters.Tag = "W"
End Sub
Private Sub UserForm_Initialize()
    Dim intSettings As Integer
    ' get all projects in the AutoCAD\Plotting Projects registry
    gvarProjects = ReadAllRegistry(gconAppname, gconSectionName)
    ' if there are any, add them to the pulldown
    If Not IsEmpty(gvarProjects) Then
        For intSettings = LBound(gvarProjects, 1) To UBound(gvarProjects, 1)
            cbProjects.AddItem gvarProjects(intSettings, 0) ' add to pulldown
        Next intSettings
        cbProjects.Text = cbProjects.List(0)        ' display first item
    End If
    ' set default for the rest of the form
    lngSetPlotter = ThisDrawing.GetVariable("Plotter") ' get current plotter number as a default
    lbDeviceDefault.Caption = ThisDrawing.GetVariable("Plotid")
    ' prepare the configuration file name and path
    gAcadCfg = "acad"
    Dim appPath As String
    appPath = ThisDrawing.Application.Path
    appPath = AddDirSep(appPath)
    Dim AcadVer As Integer
    AcadVer = CInt(ThisDrawing.Application.Version)
    Select Case AcadVer
        Case Is > 13
            gAcadCfg = appPath & gAcadCfg & CStr(AcadVer) & ".cfg"
        Case Else
            gAcadCfg = appPath & gAcadCfg & ".cfg"
    End Select
    ' get current plotter number as a default
    lngSetPlotter = ThisDrawing.GetVariable("Plotter")
    ' get the registry data from acadx.cfg for the current plotter
    ' add one because plotter number is zero based but saved index
    ' is not
    LoadData gAcadCfg, CStr(lngSetPlotter + 1), gcolRegData
    LoadMainDialog gcolRegData                              ' general set up of dialogs
    ' one time only loading
    rdFull.Value = True                                     ' full preview default
    If rdView.Value = False Then
        rdView.Enabled = False
    Else
        rdView.Enabled = True
    End If
    edTextRes.Text = ThisDrawing.GetVariable("Textqlty")
    gstrPlotFileName = ThisDrawing.GetVariable("DWGNAME")                              ' default name
    RegFlags                                                ' process registration flags
    ' disable pens and optimization til more time to write pen modules
    If ckPlotToFile.Value = True Then
        btnFileName.Enabled = True
    Else
        btnFileName.Enabled = False
    End If
    frmPlot.btnPenParams.Enabled = False
    frmPlot.btnOptimize.Enabled = False
    cbProjects.SetFocus                                     ' set focus to this control
End Sub

Public Sub LoadMainDialog(colRegData As Collection)
    ' load main dialog frmPlot
    If gintMetric = 0 Then                                  ' no metric?
        frmPlot.rdInches = True                             ' enable inches
        ' load paper width
        frmPlot.edPlotInch.Text = CStr(Format(gdblPaperWidth, "####0.00"))
    Else
        frmPlot.rdMM = True                                 ' enable metric
        ' load paper width in metric
        frmPlot.edPlotInch.Text = CStr(Format(gconMM * CLng(gdblPaperWidth), "####0.00"))
    End If
    LoadPlotLabels
    Dim lngI As Long
    ' get the active space
    lngI = ThisDrawing.ActiveSpace
    ' now see if there are any entities in the space
    Dim lngEntCount, lngViewCount As Long
    If lngI = 0 Then                                    ' if paperspace
        lngEntCount = ThisDrawing.PaperSpace.Count - 1  ' subtract one because paperspace itself is considered an entity
    Else
        lngEntCount = ThisDrawing.ModelSpace.Count      ' model space count
    End If
    If lngEntCount = 0 Then
        frmPlot.rdExtents.Enabled = False               ' no entities - no extents
    End If
    lngViewCount = ThisDrawing.Views.Count              ' get view count
    If lngViewCount > 0 Then                            ' any views?
        frmPlot.rdView.Enabled = True                   ' yes - enable the button
        frmPlot.btnView.Enabled = True
    Else
        frmPlot.rdView.Enabled = False                  ' no - diable it
        frmPlot.btnView.Enabled = False
    End If
End Sub
Private Sub CommandButton1_Click()
    Dim currPlotScale As Variant
    currPlotScale = ThisDrawing.plot.PlotScale
    MsgBox "PlotScale property is set to " & _
             ThisDrawing.plot.PlotScale(0) & _
    " to " & ThisDrawing.plot.PlotScale(1), , "PlotScale Example"
    Dim newPlotScale(0 To 1) As Double
    newPlotScale(0) = edPlotInch
    newPlotScale(1) = edDrawUnit
    ThisDrawing.plot.PlotScale = newPlotScale
    MsgBox "PlotScale property is now set to " & ThisDrawing.plot.PlotScale(0) & " to " & ThisDrawing.plot.PlotScale(1), , "PlotScale Example"

End Sub

Attribute VB_Name = "frmPlotRotationOrigin"
Attribute VB_Base = "0{F6EB6EE9-3710-11D2-99EF-00609761BD90}{F6EB6ED9-3710-11D2-99EF-00609761BD90}"
Attribute VB_Creatable = False
Attribute VB_PredeclaredId = True
Attribute VB_Exposed = False
Attribute VB_TemplateDerived = False
Attribute VB_Customizable = False

Option Explicit

Private Sub btnCancel_Click()
    Me.Hide
End Sub

Private Sub btnOK_Click()
    gdblWidthOrigin = CDbl(edXOrigin.Text)
    gdblHeightOrigin = CDbl(edYOrigin.Text)
    gstrRotation = fmPlotRotation.Tag
    LoadPlotLabels
    Me.Hide
End Sub

Private Sub rd0_Click()
    fmPlotRotation.Tag = "0"
End Sub

Private Sub rd180_Click()
    fmPlotRotation.Tag = "180"

End Sub

Private Sub rd270_Click()
    fmPlotRotation.Tag = "270"

End Sub

Private Sub rd90_Click()
    fmPlotRotation.Tag = "90"
End Sub

Private Sub UserForm_Initialize()
    SetRotation
    If gintMetric = 0 Then
        edXOrigin.Text = CStr(Format(gdblWidthOrigin, "####0.00"))
        edYOrigin.Text = CStr(Format(gdblHeightOrigin, "####0.00"))
    Else
        edXOrigin.Text = CStr(Format(gdblWidthOrigin * gconMM, "####0.00"))
        edYOrigin.Text = CStr(Format(gdblHeightOrigin * gconMM, "####0.00"))
    End If
End Sub

Attribute VB_Name = "frmViewName"
Attribute VB_Base = "0{F6EB6EE5-3710-11D2-99EF-00609761BD90}{F6EB6ED7-3710-11D2-99EF-00609761BD90}"
Attribute VB_Creatable = False
Attribute VB_PredeclaredId = True
Attribute VB_Exposed = False
Attribute VB_TemplateDerived = False
Attribute VB_Customizable = False
Option Explicit

Private Sub btnCancel_Click()
    Me.Hide
End Sub

Private Sub btnOK_Click()
    Dim lngI As Long
    For lngI = 0 To lstViewName.ListCount - 1       ' spin through and get item
        If lstViewName.Selected(lngI) = True Then   ' found selected item?
            gstrViewName = lstViewName.List(lngI)   ' store it
        End If
    Next lngI
    frmPlot.rdView.Enabled = True
    frmPlot.rdView.Value = True
    Me.Hide
End Sub

Private Sub UserForm_Initialize()
    Dim lngCnt, lngI, lngIdx As Long
    lngCnt = ThisDrawing.Views.Count - 1            ' get how many views in drawing
    For lngI = 0 To lngCnt                          ' spin through them
        lstViewName.AddItem ThisDrawing.Views.Item(lngI).Name ' add to the listbox
        If gstrPlotName = ThisDrawing.Views.Item(lngI).Name Then
            lngIdx = lngI
        End If
    Next lngI
    lstViewName.Selected(lngIdx) = True                  ' select it
End Sub

Attribute VB_Name = "frmWindowSelection"
Attribute VB_Base = "0{F6EB6EE1-3710-11D2-99EF-00609761BD90}{F6EB6ED5-3710-11D2-99EF-00609761BD90}"
Attribute VB_Creatable = False
Attribute VB_PredeclaredId = True
Attribute VB_Exposed = False
Attribute VB_TemplateDerived = False
Attribute VB_Customizable = False
Option Explicit

Private Sub btnCancel_Click()
    Me.Hide                             ' dismiss window dialog
    If Not gbolPlotFormState Then       ' was the plot dialog dismissed?
        frmPlot.Show                    ' yes - then show it
    End If
End Sub

Private Sub btnOK_Click()
    Me.Hide                             ' dismiss window dialog
    If Not gbolPlotFormState Then       ' was the plot dialog dismissed?
        If gbolWindowPicked Then        ' was a window picked?
            frmPlot.rdWindow.Enabled = True ' yes - enable the window radio button
            frmPlot.rdWindow = True     ' show it
        End If
        frmPlot.Show                    ' yes it was dismissed - then show it
    End If
End Sub

Private Sub btnPick_Click()
    Me.Hide                                     ' dismiss window dialog
    frmPlot.Hide                                ' dismiss the plot form
    gbolPlotFormState = False                   ' set the flag
    Dim aryFirstPnt, aryOtherPnt As Variant
    On Error Resume Next
    ' Get the first point using a prompt
    aryFirstPnt = ThisDrawing.Utility.GetPoint(, "First corner: ")
    If Err.Number > 0 Then                      ' did they cancel?
        Err.Clear                               ' yes - clear it
    Else                                        ' no - get the next point
        aryOtherPnt = ThisDrawing.Utility.GetCorner(aryFirstPnt, "Other corner: ")
        ' check if that both points are there
        If Not IsEmpty(aryFirstPnt) And Not IsEmpty(aryOtherPnt) Then
            edFirstX.Text = CStr(Format(aryFirstPnt(0), "######0.0000"))   ' yes - process them
            edFirstY.Text = CStr(Format(aryFirstPnt(1), "######0.0000"))
            gbolWindowPicked = True                 ' set flag that a window was selected
            edOtherX.Text = CStr(Format(aryOtherPnt(0), "######0.0000"))
            edOtherY.Text = CStr(Format(aryOtherPnt(1), "######0.0000"))
        End If
    End If

    Me.Show
End Sub

Private Sub UserForm_Initialize()
    edFirstX.Text = gstrFirstX
    edFirstY.Text = gstrFirstY
    edOtherX.Text = gstrOtherX
    edOtherY.Text = gstrOtherY
End Sub
