Attribute VB_Name = "Module1"
Option Explicit

Sub DimTest1()


    Dim STD_Style, New_Style As AcadDimStyle
    Err.Clear
    On Error Resume Next
    Set New_Style = ThisDrawing.DimStyles.Item("MY_STYLE1")
    If Err.Number <> 0 Then
      Err.Clear
      Set New_Style = ThisDrawing.DimStyles.Add("MY_STYLE1")
    End If
    ThisDrawing.ActiveDimStyle = New_Style
    ThisDrawing.SetVariable "DIMTOL", 1
    ThisDrawing.SetVariable "DIMUNIT", 1

End Sub

Sub DimTest2()

    Dim STD_Style, New_Style As AcadDimStyle
    Set New_Style = ThisDrawing.DimStyles.Item("MY_STYLE1")
    New_Style.Delete


End Sub

Sub GroupTest()
    Dim sset As AcadSelectionSet                  ' collection of selection sets
  
    Set sset = ThisDrawing.SelectionSets.Add("SS2") ' create a new set
    sset.Clear                                    ' clear it to be safe
    sset.Select acSelectionSetAll
    Dim grp As AcadGroup
    Set grp = SS_2_Group(sset, 0)

End Sub


Function SS_2_Group(SS As AcadSelectionSet, Nm As String) As AcadGroup
  Err.Clear
  On Error Resume Next
  Set SS_2_Group = ThisDrawing.Groups.Item(Nm)
  If Err.Number <> 0 Then
    Err.Clear
    Set SS_2_Group = ThisDrawing.Groups.Add(Nm)
  End If
  Dim J As Long, I As Long
  J = SS.Count - 1
  ReDim Items(0 To J) As Object
  For I = 0 To SS.Count - 1
     Set Items(I) = SS.Item(I)
  Next I
  SS_2_Group.AppendItems (Items)
End Function

Sub TestLayer()

    Dim L1 As AcadLayer
    For Each L1 In ThisDrawing.Layers
       If L1.Color <> acWhite Then
          L1.Color = acWhite
       End If
    Next L1

End Sub

Sub FindLayer()

    Dim LYR As AcadLayer
    Dim ABC As String
    '…ABC contains a layer name of interest…
    Err.Clear: On Error Resume Next
    ABC = "layer1"
    Set LYR = ThisDrawing.Layers.Item(ABC)
    If Err.Number <> 0 Then
       '…Layer did not exist…
       Err.Clear
     Else
      '…Layer found okay…
    End If

End Sub
Sub testmakelayer()
    MakeLayer "John", 5, "Dashed"

End Sub
Sub MakeLayer(NewLayer As String, Clr As Integer, LT As String)
    Dim L1 As AcadLayer: Dim I As Integer
    I = ThisDrawing.Layers.Count - 1
    While (I >= 0)
       Set L1 = ThisDrawing.Layers.Item(I)
       If L1.Name = NewLayer Then
          I = -1
       End If
       I = I - 1
    Wend
    If I <> -2 Then 'Was not found.
       Set L1 = ThisDrawing.Layers.Add(NewLayer)
       Err.Clear: On Error Resume Next
       L1.Color = Clr
       If Err.Number <> 0 Then
          MsgBox "Color number is invalid in MakeLayer function."
       End If
       Err.Clear: On Error Resume Next
       L1.Linetype = LT
       If Err.Number <> 0 Then
          MsgBox "Line type name invalid in MakeLayer function."
       End If
    End If
End Sub

Sub MakeLineType()

    Open "MY_LIN.LIN" For Output As #1
    Print #1, "*MY_LIN,My line-type experiment"
    Print #1, "A,0.5,-0.25,0.25,-0.25"
    Close #1
    Dim LTs As AcadLineTypes
    Set LTs = ThisDrawing.Linetypes
    LTs.Load "MY_LIN", "MY_LIN.LIN"

End Sub

Sub RegApp()

    Dim R1 As AcadRegisteredApplication
    Set R1 = ThisDrawing.RegisteredApplications.Item(0)
    ThisDrawing.RegisteredApplications.Add "MYAPP"

End Sub

Sub TestUCS()

    ' Current UCS is expected to the World Coordinate System (WCS)
    Dim UCS_Mine As AcadUCS 'get UCS info from table
    Set UCS_Mine = ThisDrawing.UserCoordinateSystems.Item("MY_UCS")
    Dim P1 As Variant 'user input of a point
    P1 = ThisDrawing.Utility.GetPoint(, "Center point")
    Dim Obj As AcadCircle 'draw the circle, radius is one
    Set Obj = ThisDrawing.ModelSpace.AddCircle(P1, 1#)
    Dim TrnsMtx As Variant 'get the transformation matrix
    TrnsMtx = UCS_Mine.GetUCSMatrix
    Obj.TransformBy (TrnsMtx) 'apply transformation
    Obj.Center = P1 'reset center point to original
    Obj.Update 'regenerate the object on the screen


End Sub

Sub CreatePaperSpaceViewPort()

    'switch to paper space
    ThisDrawing.ActiveSpace = acPaperSpace
    Dim PT(0 To 2) As Double
    PT(0) = 7#: PT(1) = 9#: PT(2) = 0#
    Dim NVP As AcadPViewport 'create new paper space view port object
    Set NVP = ThisDrawing.PaperSpace.AddPViewport(PT, 6#, 8#)
    PT(0) = 1#: PT(1) = 1#: PT(2) = 1#
    NVP.Direction = PT 'point is (1,1,1) for isometric view
    NVP.Display True 'force display update
    ThisDrawing.MSpace = True ' switch to model space
    ThisDrawing.ActivePViewport = NVP 'set the active paper space port
    
    ZoomAll
    ThisDrawing.MSpace = False ' switch back to paper space
    ZoomAll

End Sub


Sub TestBlock()

     Dim B1 As AcadBlock
     Dim PT(0 To 2) As Double
     PT(0) = 0#: PT(1) = 0#: PT(2) = 0#
     Set B1 = ThisDrawing.Blocks.Add(PT, "MYBLOCK")
    'Block object is B1, we can now add entity objects to it.
    'This example draws a 1x1 square with a cross
    'connecting opposite corners
      Dim P1(0 To 2) As Double
      Dim P2(0 To 2) As Double
      Dim P3(0 To 2) As Double
      Dim P4(0 To 2) As Double
      P1(0) = 0#: P1(1) = 0#: P1(2) = 0#
      P2(0) = 1#: P2(1) = 0#: P2(2) = 0#
      P3(0) = 1#: P3(1) = 1#: P3(2) = 0#
      P4(0) = 0#: P4(1) = 1#: P4(2) = 0#
     'Draw the 1x1 square as four lines
      B1.AddLine P1, P2
      B1.AddLine P2, P3
      B1.AddLine P3, P4
      B1.AddLine P4, P1
    'Draw the crossing lines from corner to corner
      B1.AddLine P1, P3
      B1.AddLine P2, P4

End Sub

Sub TestBlock1()

    Dim B1 As AcadBlock
    On Error Resume Next
    Set B1 = ThisDrawing.Blocks.Item("MYBLOCK")
    If Err.Number <> 0 Then
      'The block does not exist in the drawing
     Else
      'The block exists, B1 is a collection of entity objects
    End If

End Sub
Sub TestBlockExtreme()

    Dim MinPnt As Variant
    Dim MaxPnt As Variant
    Block_Extreme "Myname", MinPnt, MaxPnt
    
End Sub


Sub Block_Extreme(Nam As String, MinPnt As Variant, MaxPnt As Variant)
  Dim B1 As AcadBlock
  Set B1 = ThisDrawing.Blocks.Item("MYBLOCK")
  Dim XMin, YMin, XMax, YMax As Double
  XMin = 999999.9: YMin = 999999.9
  XMax = -99999.9: YMax = -99999.9
  Dim E1 As Object
  Dim P1, P2 As Variant
  Dim J As Long, I As Long
  J = B1.Count - 1
  For I = 0 To J
    Set E1 = B1.Item(I)
    E1.GetBoundingBox P1, P2
    If P2(0) > XMax Then XMax = P2(0)
    If P2(1) > YMax Then YMax = P2(1)
    If P1(0) < XMin Then XMin = P1(0)
    If P1(1) < YMin Then YMin = P1(1)
  Next I
  P1(0) = XMin: P1(1) = YMin: MinPnt = P1
  P1(0) = XMax: P1(1) = YMax: MaxPnt = P1
End Sub

Sub TestBlock2()

    Dim PP1, PP2 As Variant
    Dim PP0 As Variant
    PP0 = ThisDrawing.Utility.GetPoint(, "Pick an object: ")
    Dim S1 As AcadSelectionSet
    Set S1 = ThisDrawing.SelectionSets.Add("SS3")
    S1.Clear
    S1.SelectAtPoint (PP0)
    Dim E1 As Object
    Set E1 = S1.Item(0)
    If E1.EntityType = acBlockReference Then
       MsgBox "Found a block reference! - " & E1.Name
       Call Block_Extreme(E1.Name, PP1, PP2)
      ' ...
    End If
    
End Sub

Sub testmore()

  Dim PP0, IPs, PP1, PP2 As Variant
  Dim S1 As AcadSelectionSet
  Dim E1, E2, E1S(0) As Object
  Dim IP(2) As Double
  '
  PP0 = ThisDrawing.Utility.GetPoint(, "Pick a block insert: ")
  Set S1 = ThisDrawing.SelectionSets.Add("SS5")
  S1.Clear
  S1.SelectAtPoint (PP0)
  Set E1 = S1.Item(0)
  'only work with block reference (insert) objects
  If E1.EntityType = acBlockReference Then
    'Get limits of inserted block
     E1.GetBoundingBox PP1, PP2
    'Build selection set of objects crossing the bounding box
     S1.Clear
     S1.Select acSelectionSetCrossing, PP1, PP2
     'Remove block reference from selection set
     Set E1S(0) = E1
     S1.RemoveItems E1S
     'Loop through selection set
     Dim J As Long, I As Long, k As Long
     J = S1.Count - 1
     For I = 0 To J
        'Compute the intersection points
        Set E2 = S1.Item(I)
        IPs = E1.IntersectWith(E2, acExtendNone)
        'Go through the intersections found
        For k = LBound(IPs) To UBound(IPs)
           IP(0) = IPs(k): IP(1) = IPs(k + 1): IP(2) = IPs(k + 2)
           k = k + 2
           'draw a point at the intersection location.
           ThisDrawing.ModelSpace.AddPoint IP
        Next k
     Next I
    Else
     MsgBox "You selected the wrong type of entity!"
  End If

End Sub

Sub getatt()

    ' E1 is either type Object or AcadBlockReference and has a value.
    Dim ATS As Variant
    ATS = E1.GetAttributes
    Dim EA As AcadAttributeReference
    Dim I As Long
    For I = 0 To UBound(ATS)
         Set EA = ATS(I)
         ' Variable (EA) now contains the attribute reference object
    Next I

End Sub

Sub ViewAttribs()
  Dim E1 As Object
  Dim ATS As Variant
  Dim EA As AcadAttributeReference
  Dim MS As AcadModelSpace
  Set MS = ThisDrawing.ModelSpace
  Dim I As Long, J As Long, k As Long, s As String, L As Long
  I = MS.Count - 1
  For J = 0 To I
    Set E1 = MS.Item(J)
    If E1.EntityType = acBlockReference Then
       ATS = E1.GetAttributes
       k = UBound(ATS) + 1
       If k > 0 Then
          s$ = "Found block - " & E1.Name & _
               " - with " & Str$(k) & " attributes { "
          For L = 0 To k - 1
             Set EA = ATS(L)
             s$ = s$ + EA.TagString & "/" & EA.TextString & " "
          Next L
          s$ = s$ & "}"
          MsgBox s$
       End If
    End If
  Next J
End Sub
