Attribute VB_Name = "Module1"
'  ad_DwgVer
'
'  This routine determines the AutoCAD version of the current drawing.
'    This version checks for most versions. The 'unknowns' will be
'    added as they become known.
'  Demand load:  -vbarun;ad_DwgVer.dvb!ad_DwgVer;
'
'  version 1.00
'  1/1/2001
'  updated 1/19/01
'
'  Copyright©2001 ActiveDwg.com
'
'  This routine is provided for demonstration purposes only and must
'    not be used for critical applications without your verification
'    that this routine will perform as you intended.
'  This routine may be freely utilized for your own personal use so long
'    as the entire contents of this header remain intact.
'  This routine is provided "as-is" and no declaration, written or implied,
'    is made as to its reliability for any particular task. Any use of this
'    routine is solely at your own risk.
'
Option Explicit
Public Sub ad_DwgVer()
   Dim DwgHeader As String * 6
   Dim DwgFile As Long
   
   DwgFile = FreeFile(0)
   
   Open ThisDrawing.FullName For Binary Access Read As #DwgFile
   Get #DwgFile, , DwgHeader
   Close #DwgFile
   
   Select Case DwgHeader
      Case "AC1015":   'Autocad 2000
         MsgBox "AutoCAD 2000/i"
      Case "AC1014":   'Autocad R14
         MsgBox "AutoCAD 14"
      Case "AC1013":   'Autocad R14
         MsgBox "AutoCAD 14"
      Case "AC1012":   'Autocad R13
         MsgBox "AutoCAD 13"
      Case "AC1011":   'Autocad R13
         MsgBox "AutoCAD 13"
      Case "AC1010":   'Autocad R13
         MsgBox "AutoCAD 13"
      Case "AC1009":   'Autocad R11/R12
         MsgBox "AutoCAD 11/12"
      Case "AC1006":   'Autocad R10
         MsgBox "AutoCAD 10"
      Case "AC1004":   'Autocad R9
         MsgBox "AutoCAD 9"
      Case "AC1003":   'Autocad R2.6
         MsgBox "AutoCAD 2.6"
      Case "AC1002":   'Autocad R2.5
         MsgBox "AutoCAD 2.5"
      Case Else:       'Unknown Header
         MsgBox "Unknown Header"
   End Select
End Sub
