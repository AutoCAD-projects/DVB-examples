Attribute VB_Name = "Module1"
Option Explicit

Public Sub PlayDate()

    Dim MyDate, ADate, bdate, MyStr As Variant
    Stop

    MyDate = #1/27/93#
    ADate = 1 / 27 / 93
    bdate = "1/27/93"
    Debug.Print VarType(MyStr)                  ' 0 - empty

    MyStr = Format(ADate, "Long Date")          ' Line #1
    Debug.Print MyStr
    Debug.Print VarType(MyStr)                  ' 8 = string type

    MyStr = Format(bdate, "Long Date")          ' Line #2
    Debug.Print MyStr
    Debug.Print VarType(MyStr)                  ' 8 = string type

    MyStr = Format(MyDate, "Long Date")         ' Line #3
    Debug.Print MyStr
    Debug.Print VarType(MyStr)                  ' 8 = string type

End Sub
