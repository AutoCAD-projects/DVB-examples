Attribute VB_Name = "Module1"

Public Excell As Excel.Application
Public SS As AcadSelectionSet
Public excelSheet As Object

Sub holes()
  
  Set Excell = GetObject(, "Excel.Application")
  Excell.Visible = True
  Set excelSheet = Excell.ActiveWorkbook.Sheets.Add
  
  Set SS = Get_Circles
  
  Send_Holes_To_Excel
  
  excelSheet.Range("A1").Sort _
  key1:=excelSheet.Range("B1"), _
  key2:=excelSheet.Range("C1"), _
  key3:=excelSheet.Range("D1")
  
  Set_Hole_Numbers

End Sub

Function Get_Circles() As AcadSelectionSet
  
  Dim Cir1, Cir2 As Variant
  Dim CirA(0 To 0) As Integer
  Dim CirB(0 To 0) As Variant
  CirA(0) = 0
  CirB(0) = "CIRCLE"
  Cir1 = CirA: Cir2 = CirB
  On Error Resume Next
  Set Get_Circles = ThisDrawing.SelectionSets.Add("HOLES")
  If Err.Number <> 0 Then
    Err.Clear
    Set Get_Circles = ThisDrawing.SelectionSets.Item("HOLES")
  End If
  Get_Circles.Clear
  Get_Circles.Select acSelectionSetAll, , , Cir1, Cir2

End Function

Sub Send_Holes_To_Excel()
  
  Dim Ent As AcadCircle
  CN = 1: CX = 2: CY = 3: CR = 4
  R = 1
  Dim PTV As Variant
  For Each Ent In SS
    excelSheet.Cells(R, CN).Value = Ent.Handle
    PTV = Ent.Center
    excelSheet.Cells(R, CX).Value = PTV(0)
    excelSheet.Cells(R, CY).Value = PTV(1)
    excelSheet.Cells(R, CR).Value = Ent.Radius
    R = R + 1
  Next Ent

End Sub

Sub Set_Hole_Numbers()
  
  Dim PTV As Variant
  Dim PTC(0 To 2) As Double
  I = 1
  TH = ThisDrawing.GetVariable("TEXTSIZE")
  While excelSheet.Cells(I, 1).Value <> ""
    PTC(0) = excelSheet.Cells(I, 2).Value
    PTC(1) = excelSheet.Cells(I, 3).Value
    PTC(2) = 0#
    ThisDrawing.ModelSpace.AddText Str$(I), PTC, TH
    I = I + 1
  Wend

End Sub

Sub update_radii()
  
  Dim Excell As Object
  Set Excell = GetObject(, "Excel.Application")
  Set excelSheet = Excell.ActiveWorkbook.Sheets("Sheet1")
  Dim Ent As AcadCircle
  I = 1
  While excelSheet.Cells(I, 1).Value <> ""
    HN$ = excelSheet.Cells(I, 1).Value
    Set Ent = ThisDrawing.HandleToObject(HN$)
    If Ent.Radius <> excelSheet.Cells(I, 4) Then
      Ent.Radius = excelSheet.Cells(I, 4)
      Ent.Layer = "CHANGED"
    End If
    I = I + 1
  Wend

End Sub
