Attribute VB_Name = "Module1"
'  ad_AttributeUpdate
'
'  This routine takes user defined input to update block attributes
'     in the current drawing. Of particular note is the dynamic
'     updating of the buttons and, on completion, the reporting of
'     the total number of blocks updated in the title bar.
'  Note:After you select the block, right-click to go back to the
'     form. We hope to update it to allow multiple block sources,
'     one of these days.
'  Demand load:  -vbarun;ad_AttributeUpdate.dvb!ad_AttributeUpdate;
'
'  version 1.00
'  8/4/2000
'
'  Copyright©2000 ActiveDwg.com
'
'  This routine is provided for demonstration purposes only and must
'    not be used for critical applications without your verification
'    that this routine will perform as you intended.
'  This routine may be freely utilized for your own personal use so long
'    as the entire contents of this header remain intact.
'  This routine is provided "as-is" and no declaration, written or implied,
'    is made as to its reliability for any particular task. Any use of this
'    routine is solely at your own risk.
'
Sub ad_AttributeUpdate()
    UserForm1.Show
End Sub

Attribute VB_Name = "UserForm1"
Attribute VB_Base = "0{2DC5EAAD-980F-11D5-863F-00C04F948912}{2DC5E741-980F-11D5-863F-00C04F948912}"
Attribute VB_GlobalNameSpace = False
Attribute VB_Creatable = False
Attribute VB_PredeclaredId = True
Attribute VB_Exposed = False
Attribute VB_TemplateDerived = False
Attribute VB_Customizable = False
'  ad_AttributeUpdate
'
'  This routine takes user defined input to update block attributes
'     in the current drawing. Of particular note is the dynamic
'     updating of the buttons and, on completion, the reporting of
'     the total number of blocks updated in the title bar.
'  Note:After you select the block, right-click to go back to the
'     form. We hope to update it to allow multiple block sources,
'     one of these days.
'  Demand load:  -vbarun;ad_AttributeUpdate.dvb!ad_AttributeUpdate;
'
'  version 1.00
'  8/3/2000
'
'  Copyright©2000 ActiveDwg.com
'
'  This routine is provided for demonstration purposes only and must
'    not be used for critical applications without your verification
'    that this routine will perform as you intended.
'  This routine may be freely utilized for your own personal use so long
'    as the entire contents of this header remain intact.
'  This routine is provided "as-is" and no declaration, written or implied,
'    is made as to its reliability for any particular task. Any use of this
'    routine is solely at your own risk.
'
Option Explicit
Dim BlockObj As Object
Dim BlockObjAttributes
Dim i As Integer
Public BlockName As String
Dim BlockMatch As String

Private Sub AttributeList_Change()

        Cmd_UpdateAllType.Caption = "Update All With '" & AttributeList.Text & "'"
        Cmd_ReplaceAll.Enabled = True
        Cmd_ReplaceThisOne.Enabled = True
        Cmd_UpdateAllType.Enabled = True
  
End Sub

Private Sub Cmd_GetBlock_Click()
  On Error GoTo ErrorCatch
  Me.Hide
  Dim sset As Object
  Dim handle
  Set sset = ThisDrawing.SelectionSets.Add("Block_Edit")
  sset.SelectOnScreen
  Set BlockObj = ThisDrawing.HandleToObject(sset.Item(0).handle)
  BlockName = BlockObj.Name
  BlockObjAttributes = BlockObj.GetAttributes
  For i = LBound(BlockObjAttributes) To UBound(BlockObjAttributes)
     AttributeList.AddItem BlockObjAttributes(i).TextString
  Next i
  ThisDrawing.SelectionSets.Item("Block_Edit").Delete
  Me.Caption = "Block Name: " & BlockName
  Cmd_ReplaceAll.Caption = "Update All '" & BlockObjAttributes(0).TextString & "'s'"
  Cmd_ReplaceThisOne.Caption = "Update This '" & BlockObjAttributes(0).TextString & "' Only"
  Cmd_GetBlock.Enabled = False
  BlockMatch = BlockObjAttributes(0).TextString
  Me.Show
  Exit Sub
ErrorCatch:
  Err.Clear
End Sub

Private Sub Cmd_ReplaceAll_Click()
  On Error GoTo errcontrol
  Dim count As Integer
  Dim ent As Object
  
'We need to trap the routine if the change is to simply add a new
'   part to the connection list. If the Part to change is defined
'   as "" then ALL blank spaces in the block will be changed to
'   the new item. This trap breaks out after adding one item in
'   the first blank placeholder.
  If AttributeList.Text = "" Then
      For Each ent In ThisDrawing.ModelSpace
        If ent.EntityName = "AcDbBlockReference" Then
          If ent.Name = BlockName Then
            BlockObjAttributes = ent.GetAttributes
            If BlockObjAttributes(0).TextString = BlockMatch Then
              For i = LBound(BlockObjAttributes) To UBound(BlockObjAttributes)
                If BlockObjAttributes(i).TextString = AttributeList.Text Then
                  BlockObjAttributes(i).TextString = NewAttribute.Text
                  count = count + 1
                  GoTo NextBlock
                End If
              Next
            End If
          End If
        End If
NextBlock:
    Next
  Else
      For Each ent In ThisDrawing.ModelSpace
        If ent.EntityName = "AcDbBlockReference" Then
          If ent.Name = BlockName Then
            BlockObjAttributes = ent.GetAttributes
            If BlockObjAttributes(0).TextString = BlockMatch Then
              For i = LBound(BlockObjAttributes) To UBound(BlockObjAttributes)
                If BlockObjAttributes(i).TextString = AttributeList.Text Then
                  BlockObjAttributes(i).TextString = NewAttribute.Text
                  count = count + 1
                End If
              Next
            End If
          End If
        End If
    Next
  End If
  ThisDrawing.Application.Update
  Me.Caption = count & " Blocks Updated"
  NewAttribute.Text = ""
  AttributeList.Clear
  Cmd_GetBlock.Enabled = True
  Cmd_ReplaceAll.Enabled = False
  Cmd_ReplaceThisOne.Enabled = False
  Cmd_UpdateAllType.Enabled = False
  Exit Sub
errcontrol:
  MsgBox Err.Description
  Err.Clear
End Sub

Private Sub Cmd_ReplaceThisOne_Click()
'We need to trap the routine if the change is to simply add a new
'   part to the connection list. If the Part to change is defined
'   as "" then ALL blank spaces in the block will be changed to
'   the new item. This trap breaks out after adding one item in
'   the first blank placeholder.
  If AttributeList.Text = "" Then
      For i = LBound(BlockObjAttributes) To UBound(BlockObjAttributes)
        If BlockObjAttributes(i).TextString = AttributeList.Text Then
          BlockObjAttributes(i).TextString = NewAttribute.Text
        End If
      Next i
  Else
      For i = LBound(BlockObjAttributes) To UBound(BlockObjAttributes)
        If BlockObjAttributes(i).TextString = AttributeList.Text Then
          BlockObjAttributes(i).TextString = NewAttribute.Text
        End If
      Next i
  End If
  ThisDrawing.Application.Update
  Me.Caption = "1 Block Updated"
  NewAttribute.Text = ""
  AttributeList.Clear
  Cmd_GetBlock.Enabled = True
  Cmd_ReplaceAll.Enabled = False
  Cmd_UpdateAllType.Enabled = False
End Sub

Private Sub Cmd_Quit_Click()
  Unload Me
End Sub

Private Sub Option_ModelSpace_Click()
  ThisDrawing.ActiveSpace = acModelSpace
End Sub

Private Sub Option_PaperSpace_Click()
  ThisDrawing.ActiveSpace = acPaperSpace
End Sub

Private Sub Cmd_UpdateAllType_Click()
  On Error GoTo errcontrol
  Dim count As Integer
  Dim ent As Object
'We need to trap the routine if the change is to simply add a new
'   part to the connection list. If the Part to change is defined
'   as "" then ALL blank spaces in the block will be changed to
'   the new item. This trap breaks out after adding one item in
'   the first blank placeholder.
  If AttributeList.Text = "" Then
      For Each ent In ThisDrawing.ModelSpace
        If ent.EntityName = "AcDbBlockReference" Then
          If ent.Name = BlockName Then
            BlockObjAttributes = ent.GetAttributes
              For i = LBound(BlockObjAttributes) To UBound(BlockObjAttributes)
                If BlockObjAttributes(i).TextString = AttributeList.Text Then
                  BlockObjAttributes(i).TextString = NewAttribute.Text
                  count = count + 1
                  GoTo NextBlock
                End If
              Next
          End If
        End If
NextBlock:
    Next
  Else
      For Each ent In ThisDrawing.ModelSpace
        If ent.EntityName = "AcDbBlockReference" Then
          If ent.Name = BlockName Then
            BlockObjAttributes = ent.GetAttributes
              For i = LBound(BlockObjAttributes) To UBound(BlockObjAttributes)
                If BlockObjAttributes(i).TextString = AttributeList.Text Then
                  BlockObjAttributes(i).TextString = NewAttribute.Text
                  count = count + 1
                End If
              Next
          End If
        End If
    Next
  End If
  ThisDrawing.Application.Update
  Me.Caption = count & " Blocks Updated"
  NewAttribute.Text = ""
  AttributeList.Clear
  Cmd_GetBlock.Enabled = True
  Cmd_ReplaceAll.Enabled = False
  Cmd_ReplaceThisOne.Enabled = False
  Cmd_UpdateAllType.Enabled = False
  Exit Sub
errcontrol:
  MsgBox Err.Description
  Err.Clear

End Sub

Private Sub UserForm_Initialize()
  AttributeList.Style = fmStyleDropDownList
  Me.Caption = "ActiveDwg Attribute Update"
  Cmd_ReplaceAll.Enabled = False
  Cmd_ReplaceThisOne.Enabled = False
  Cmd_UpdateAllType.Enabled = False
End Sub
