Attribute VB_Name = "Module1"
'
'  ad_AcadDate
'
'  This routine demonstrates the retrieval and conversion of
'     drawing date information from the internal AutoCAD format
'     to Julian format and conversion of the elapsed timer.
'  It was developed in AutoCAD 2000.
'  Demand load:  -vbarun;ad_AcadDate.dvb!ad_AcadDate;
'
'  version 1.00
'  5/17/2001
'
'  Copyright©2001 ActiveDwg.com
'
'  This routine is provided for demonstration purposes only and must
'    not be used for critical applications without your verification
'    that this routine will perform as you intended.
'  This routine may be freely utilized for your own personal use so long
'    as the entire contents of this header remain intact.
'  This routine is provided "as-is" and no declaration, written or implied,
'    is made as to its reliability for any particular task. Any use of this
'    routine is solely at your own risk.
'

Option Explicit

Sub ad_AcadDate()
  Dim adDwgCreate As Date
  Dim adDwgUpdate As Date
  Dim adDwgEdit As Double
  Dim adDwgUsrTimer As Double
  
  adDwgCreate = ThisDrawing.GetVariable("TDCREATE") - 2415019
  adDwgUpdate = ThisDrawing.GetVariable("TDUPDATE") - 2415019
  adDwgEdit = ThisDrawing.GetVariable("TDINDWG")
  adDwgUsrTimer = ThisDrawing.GetVariable("TDUSRTIMER")
  
  adDwgEdit = adDwgEdit * 24
  adDwgUsrTimer = adDwgUsrTimer * 24
  
  adDwgEdit = Round(adDwgEdit, 2)
  adDwgUsrTimer = Round(adDwgUsrTimer, 2)
  
  MsgBox "Stats for " & ThisDrawing.Name & vbCrLf & _
         "Drawing Created " & adDwgCreate & vbCrLf & _
         "Drawing Last Updated " & adDwgUpdate & vbCrLf & _
         "Drawing Edit Time " & adDwgEdit & " hours" & vbCrLf & _
         "User Timer " & adDwgUsrTimer & " hours"
End Sub

Public Function Round(adNum As Double, adPlaces As Integer) As Double
  Dim adTmp As Integer
  adNum = CDbl(adNum)
  adTmp = Fix(adNum)
  adNum = CInt((adNum - adTmp) * 10 ^ adPlaces)
  Round = adTmp + adNum / 10 ^ adPlaces
End Function
