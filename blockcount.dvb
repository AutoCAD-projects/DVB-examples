Attribute VB_Name = "BlockCount"
Attribute VB_Base = "0{D0F15D55-00F3-11D3-99EA-7A5B76000000}{D0F15D04-00F3-11D3-99EA-7A5B76000000}"
Attribute VB_Creatable = False
Attribute VB_PredeclaredId = True
Attribute VB_Exposed = False
Attribute VB_TemplateDerived = False
Attribute VB_Customizable = False

Private Sub CommandButton1_Click()
    End
End Sub

Private Sub ListBox1_Click()
  LL$ = ListBox1.List(ListBox1.ListIndex)
  While Mid$(LL$, Len(LL$), 1) <> " "
    LL$ = Mid$(LL$, 1, Len(LL$) - 1)
  Wend
  While Mid$(LL$, Len(LL$), 1) = " "
    LL$ = Mid$(LL$, 1, Len(LL$) - 1)
  Wend
  Dats(1) = LL$: Filter1 = Grps: Filter2 = Dats
  SS.Clear
  SS.Select acSelectionSetAll, , , Filter1, Filter2
  BlockCount.Hide
  SS.Highlight True
  LL$ = ThisDrawing.Utility.GetString(0, "Press Enter to continue…")
  SS.Highlight False
End Sub

Attribute VB_Name = "Module1"
Global SS As AcadSelectionSet
Global BLKS As AcadBlocks
Global BLK As AcadBlock
Global Grps(0 To 1) As Integer
Global Dats(0 To 1) As Variant
Global Filter1, Filter2 As Variant

Sub BlockCounter()
  Grps(0) = 0: Dats(0) = "INSERT"
  Grps(1) = 2: Dats(1) = ""
  On Error Resume Next
  Set SS = ThisDrawing.SelectionSets.Add("SS")
  If Err.Number <> 0 Then
    Set SS = ThisDrawing.SelectionSets.Item("SS")
  End If
  SS.Clear
  Set BLKS = ThisDrawing.Blocks
  J = BLKS.Count - 1
  For I = 2 To J
    Set BLK = BLKS.Item(I)
    Dats(1) = BLK.Name
    Filter1 = Grps
    Filter2 = Dats
    SS.Select acSelectionSetAll, , , Filter1, Filter2
    Out$ = BLK.Name & " " & Str$(SS.Count)
    BlockCount.ListBox1.AddItem Out$
    SS.Clear
  Next I
  While 1 = 1
    BlockCount.Show
  Wend
End Sub

Attribute VB_Name = "ThisDrawing"
Attribute VB_Base = "0{8E75D913-3D21-11D2-85C4-080009A0C626}"
Attribute VB_Creatable = False
Attribute VB_PredeclaredId = True
Attribute VB_Exposed = True
Attribute VB_TemplateDerived = False
Attribute VB_Customizable = True
Dim Time_Start
Dim Dwg_Name As String


Private Sub AcadDocument_Activate()
  Time_Start = Timer
  Dwg_Name = ThisDrawing.FullName
End Sub
'
Private Sub AcadDocument_Deactivate()
  MsgBox "Time Spent in " & Dwg_Name & " was " & Timer - Time_Start
End Sub
