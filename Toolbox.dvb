Attribute VB_Name = "BasWindows"

Option Explicit

'   Paladin
'   Copyright (C) 1998,1999 by Paladin.  All rights reserved.

'   Permission to use or modify this software is hereby granted to the
'   licensee, provided that the above copyright notice appears in all
'   copies and that both that copyright notice and this permission
'   notice appear in all supporting documentation.

'   Permission is hereby granted to use this routine on the condition that
'   this header remains with the routine. No warrantity is implied or
'   expressed.

'   Original version   2-4-98  John Gibb
'            revised    -  -
    
    Global Const conGW_HWNDFIRST = 0
    Global Const conGW_HWNDLAST = 1
    Global Const conGW_HWNDNEXT = 2
    Global Const conGW_HWNDPREV = 3
    Global Const conGW_OWNER = 4
    Global Const gintMAX_SIZE = 255
    Global Const gstrNULL = ""

' API declarations
' If Win16 evaluates as true, do the statements following the #If.
#If Win16 Then
    Declare Function GetWindowsDirectory Lib "Kernel" (ByVal lpBuffer As String, ByVal nSize As Integer) As Integer
    Declare Function GetSystemDirectory Lib "Kernel" (ByVal lpBuffer As String, ByVal nSize As Integer) As Integer
    Declare Function GetTopWindow Lib "User" (ByVal hwnd As Integer) As Integer
    Declare Function GetNextWindow Lib "User" (ByVal hwnd As Integer, ByVal wFlag As Integer) As Integer
    Declare Function GetWindow Lib "User" (ByVal hwnd As Integer, ByVal wCmd As Integer) As Integer
    Declare Function GetWindowText Lib "User" (ByVal hwnd As Integer, ByVal lpString As String, ByVal aint As Integer) As Integer
    Declare Function SetActiveWindow Lib "User" (ByVal hwnd As Integer) As Integer
    Declare Function SetWindowPlacement Lib "User" (ByVal hwnd As Integer, lpwndpl As WINDOWPLACEMENT) As Integer
    Declare Function GetWindowPlacement Lib "User" (ByVal hwnd As Integer, lpwndpl As WINDOWPLACEMENT) As Integer

    Type RECT
        Left As Integer
        Top As Integer
        Right As Integer
        Bottom As Integer
    End Type

    Type WINDOWPLACEMENT
        Length As Integer
        flags As Integer
        showCmd As Integer
        ptMinPosition As POINTAPI
        ptMaxPosition As POINTAPI
        rcNormalPosition As RECT
    End Type

#ElseIf Win32 Then
    '. Place exclusively 32-bit Windows statements here.
    Declare Function GetWindowsDirectory Lib "Kernel32" Alias "GetWindowsDirectoryA" (ByVal lpBuffer As String, ByVal nSize As Integer) As Integer
    Declare Function GetSystemDirectory Lib "Kernel32" Alias "GetSystemDirectoryA" (ByVal lpBuffer As String, ByVal nSize As Integer) As Integer
    Declare Function GetNextWindow Lib "user32" (ByVal hwnd As Long, ByVal wFlag As Long) As Long
    Declare Function GetWindow Lib "user32" (ByVal hwnd As Long, ByVal wCmd As Long) As Long

    Declare Function GetTopWindow Lib "user32" (ByVal hwnd As Long) As Long
    Declare Function GetWindowText Lib "user32" Alias "GetWindowTextA" (ByVal hwnd As Long, ByVal lpString As String, ByVal cch As Long) As Long
    Declare Function SetActiveWindow Lib "user32" (ByVal hwnd As Long) As Long
    Declare Function SetWindowPlacement Lib "user32" (ByVal hwnd As Long, lpwndpl As WINDOWPLACEMENT) As Long
    Declare Function GetWindowPlacement Lib "user32" (ByVal hwnd As Long, lpwndpl As WINDOWPLACEMENT) As Long
    Declare Function Polygon Lib "gdi32" (ByVal hdc As Long, ByRef lpPoint As POINTAPI, ByVal nCount As Long) As Long
    Type POINTAPI
        x As Long
        y As Long
    End Type

    Type RECT
        Left As Long
        Top As Long
        Right As Long
        Bottom As Long
    End Type

    Type WINDOWPLACEMENT
        Length As Long
        flags As Long
        showCmd As Long
        ptMinPosition As POINTAPI
        ptMaxPosition As POINTAPI
        rcNormalPosition As RECT
    End Type

#Else
    '. Place other platform statements here.
#End If


'-----------------------------------------------------------
' FUNCTION: GetWindowsDir
'
' Calls the windows API to get the windows directory and
' ensures that a trailing dir separator is present
'
' Returns: The windows directory
'-----------------------------------------------------------
'
Function GetWindowsDir() As String
    Dim strBuf As String

    strBuf = Space$(gintMAX_SIZE)

    '
    'Get the windows directory and then trim the buffer to the exact length
    'returned and add a dir sep (backslash) if the API didn't return one
    '
    If GetWindowsDirectory(strBuf, gintMAX_SIZE) > 0 Then
        strBuf = StripTerminator$(strBuf)
        AddDirSep strBuf

        GetWindowsDir = UCase16(strBuf)
    Else
        GetWindowsDir = gstrNULL
    End If
End Function

''''''''''''''''''''''''''''''''''''''''''''''''''''''''''''''''''''''
' Usage for setting an active window:
'    SetActiveWindow(FindWindow("<Window Title goes here>"))
''''''''''''''''''''''''''''''''''''''''''''''''''''''''''''''''''''''
Public Function FindWindow(sStr As String) As Long
    Dim hWindow As Long
    Dim hLastWnd As Long
    Dim sBuff As String * 64
    
    FindWindow = 0
    
    hWindow = GetTopWindow(0)
    hLastWnd = GetWindow(hWindow, conGW_HWNDLAST)
    While hWindow <> hLastWnd
        Call GetWindowText(hWindow, sBuff, 64)
        If InStr(sBuff, sStr) > 0 Then
            FindWindow = hWindow
            Exit Function
        End If
        hWindow = GetWindow(hWindow, conGW_HWNDNEXT)
    Wend
End Function

'-----------------------------------------------------------
' FUNCTION: UCase16
'
' Returns the upper-case conversion of a string
'   under 16 bits, or else returns an unmodified
'   copy of the string under 32 bits.
'
' IN: [str] - String to copy/upper-case
'
'-----------------------------------------------------------
'
Function UCase16(ByVal str As String)
#If Win16 Then
    UCase16 = UCase$(str)
#Else
    UCase16 = str
#End If
End Function

Attribute VB_Name = "basToolTest"

'   Paladin
'   Copyright (C) 1998,1999 by Paladin.  All rights reserved.

'   Permission to use or modify this software is hereby granted to the
'   licensee, provided that the above copyright notice appears in all
'   copies and that both that copyright notice and this permission
'   notice appear in all supporting documentation.

'   Permission is hereby granted to use this routine on the condition that
'   this header remains with the routine. No warrantity is implied or
'   expressed.

'   Original version   2-4-98  John Gibb
'            revised    -  -
    
Public Function parse_test()
    Dim strLine As String
    Const conDelimit As String = "|"
    Dim lngPosition As Long
    Stop
    strLine = "height|length|weight|depth|age|color"
    For lngPosition = 1 To 6 Step 2
        MsgBox "Position #" & CStr(lngPosition) & " = " & _
                parse(strLine, conDelimit, lngPosition), , "Parse Test"
    Next lngPosition
End Function
Public Sub plural_test()
    Dim inti As Long
    Stop
    For inti = 0 To 2
     MsgBox CStr(inti) & " item" & chk_plural(inti, 1) & " " & _
            chk_plural(inti, 4) & " been found.", , "Chk_Plural Test"
    Next inti
End Sub
Public Sub isfile_test()
    Dim strFname As String
    Stop
    strFname = "c:\autoexec.bat"
    If Not IsFile(strFname) Then
        MsgBox "File " & UCase(strFname) & " not found.", , "IsFile Test"
    Else
        MsgBox "File " & UCase(strFname) & " found.", , "IsFile Test"
    End If

    strFname = "adge#.jwg"
    If Not IsFile(strFname) Then
        MsgBox "File " & UCase(strFname) & " not found.", , "IsFile Test"
    Else
        MsgBox "File " & UCase(strFname) & " found.", , "IsFile Test"
    End If
    
End Sub
Public Sub findfile_test()
    Dim strFname As String
    Stop
    strFname = "acad.mnc"
    Dim TempName As Variant
    TempName = FindFile(strFname)
    If IsNull(TempName) Then
        MsgBox "File " & UCase(strFname) & " not found.", , "FindFile Test"
    Else
        MsgBox "File " & UCase(TempName) & " found.", , "FindFile Test"
    End If

    strFname = "acad.mnm"
    TempName = FindFile(strFname)
    If IsNull(TempName) Then
        MsgBox "File " & UCase(strFname) & " not found.", , "FindFile Test"
    Else
        MsgBox "File " & UCase(TempName) & " found.", , "FindFile Test"
    End If
    
End Sub
Public Sub fatal_test()
    
    Dim strFname As String
    Stop
    strFname = "c:\autoexec.bat"
    If Not IsFile(strFname) Then
        Fatal_error 1, strFname
    Else
        MsgBox "File " & UCase(strFname) & " found.", , "Fatal_Error Test"
    End If
    
    strFname = "adge#.jwg"
    If Not IsFile(strFname) Then
        Fatal_error 1, fname
    Else
        MsgBox "File " & UCase(strFname) & " found.", , "Fatal_Error Test"
    End If
End Sub
Public Sub count_test()
    Dim lngNum, lngNum1  As Long
    Dim strFname As String
    Dim strDelimit As String
    Stop
    strFname = "c:\autoexec.bat"
    strDelimit = "\"
    lngNum = count_occurrences(strFname, strDelimit)
    strDelimit = ":"
    lngNum1 = count_occurrences(strFname, strDelimit)
    If lngNum > 0 Or lngNum1 > 0 Then
        MsgBox "Found one of the delimiters. " & _
               vbCrLf & "You got yourself a path on the string.", , "Count_Occurrences Test"
    Else
        MsgBox "No delimiters were found." & _
               vbCrLf & "The string has no path.", , "Count_Occurrences Test"
    End If
End Sub
Public Sub getsubstr_test()
    Dim strLine As String
    Dim strPath As String
    Dim strFname As String
    Stop
    strLine = "c:\autoexec.bat"
    strFname = "autoexec"
    strPath = Token(strLine, strFname)
    MsgBox "The path is " & strPath, , "Token Test"
End Sub
Public Sub getrsubstr_test()
    Dim strLine As String
    Dim strSub As String
    Dim strFname As String
    Stop
    strLine = "c:\autoexec.bat"
    strSub = "autoexec"
    strFname = RightToken(strLine, strSub)
    MsgBox "The file name is " & strFname, , "RightToken Test"
End Sub
Public Sub split_test()
    Dim strFname As String
    Dim strLine As String
    Stop
    strLine = "c:\autoexec.bat"
    strFname = strip_path(strLine)
    MsgBox "Line before processing was " & UCase(strLine) & _
           vbCrLf & vbCrLf & "The file name is " & strFname, , "Strip_path Test"
End Sub
Public Sub spin_test()
    frmSpinner.Show
End Sub

Public Sub backslash_test()
    Dim strPath1 As String
    Dim strPath2 As String
    Stop
    strPath1 = "c:"
    strPath2 = "c:\"
    MsgBox "Directory name 1 is " & AddDirSep(strPath1) & _
           vbCrLf & "Directory name 2 is " & AddDirSep(strPath2), , "AddDirSep Test"
End Sub
Public Sub back2_test()
    Dim strPath1 As String
    Dim strPath2 As String
    Stop
    strPath1 = "c:"
    strPath2 = "c:\test\temp\"
    MsgBox "Directory name 1 is " & add_backslashes(strPath1) & _
           vbCrLf & "Directory name 2 is " & add_backslashes(strPath2), , "Add_Backslashes Test"
End Sub

Public Sub list_test()
    frmList.Show
End Sub

Public Sub ent_test()
    frmShowObjectType.Show

End Sub
Public Sub find_test()
    Dim strName As String
    Dim lngResult As Long
    Stop
    strName = "AutoCAD Text Window"
    lngResult = FindWindow(strName)
    If lngResult > 0 Then
        MsgBox "Found the application: " & strName, , "Find Application"
    Else
        MsgBox "Application not loaded.", , "Find Application"
    End If
End Sub
Public Sub control_test()
    frmList.check_control
End Sub
Public Sub FormatPnt_test()
    Stop
    Dim strPntX As String, strPntY As String, strPntZ As String
    strPntX = "1.123456789"
    strPntY = "2.123456789"
    strPntZ = "3.123456789"
    Dim lngI As Long
    Dim strMsg As String
    strMsg = "Point before format = " & "(" & strPntX & "," & strPntY & "," & strPntZ & ")" & vbCrLf
    lngI = ThisDrawing.GetVariable("luprec")
    strMsg = strMsg & "Point after format using your LUPREC setting = " & _
             "(" & FormatPnt(strPntX, lngI) & "," & FormatPnt(strPntY, lngI) & "," & FormatPnt(strPntZ, lngI) & ")"
    'MsgBox strMsg
    strMsg = strMsg & vbCrLf & vbCrLf
    For lngI = 0 To 9
        strMsg = strMsg & vbCrLf & "Point after format using a LUPREC setting of " & CStr(lngI) & " = " & _
                 "(" & FormatPnt(strPntX, lngI) & "," & FormatPnt(strPntY, lngI) & "," & FormatPnt(strPntZ, lngI) & ")"
    Next lngI
    MsgBox strMsg, , "FormatPnt Test"
End Sub
Public Sub replacechr_test()
    Stop
    Dim strLine As String, strMsg As String
    strLine = "Empnumber,Empname,Address,State,Zip"
    strMsg = "Orignal string was : " & strLine & vbCrLf & vbCrLf
    strMsg = strMsg & "**** Substitue a '|' for all commas in the string. ****" & vbCrLf & vbCrLf
    strMsg = strMsg & "New string is : " & Replace_Chr(strLine, ",", "|")
    MsgBox strMsg, , "Replace_Chr Test"
End Sub
Public Sub GetWindowsDir_test()
    Stop
    Dim strMsg As String
    strMsg = "Your system's Windows directory is : " & GetWindowsDir
    MsgBox strMsg, , "GetWindowsDir Test"
End Sub

Public Sub Pad_Test()
    Stop
    Dim strHold As String, strLine As String, strMsg As String
    strLine = "Jim kkksssb"
    strMsg = "strLine = " & strLine & "." & vbCrLf
    strMsg = strMsg & "The length of strLine before getting blanks is " & CStr(Len(strLine)) & vbCrLf & vbCrLf
    Dim strTemp As String
    strLine = Pad(strLine, 10)  ' pad the line to a total of 10 characters
    strMsg = strMsg & "The length after getting blanks added is " & CStr(Len(strLine)) & vbCrLf
    strMsg = strMsg & "strLine now = " & strLine & "."
    MsgBox strMsg, , "Pad Test"
End Sub
Public Sub GetPath_Test()
    'Stop
    Dim strLine As String, strMsg As String
    strLine = "C:\TEMP\JUNK.DAT"
    strMsg = "strLine = " & strLine & vbCrLf
    Dim strPath As String
    strPath = Get_Path(strLine)
    If Len(strPath) = 0 Then
        strTemp = "Null"
    End If
    strMsg = strMsg & "The path is " & strPath & "."
    MsgBox strMsg, , "Get_Path Test"
End Sub

Public Sub GetExtension_Test()
    Stop
    Dim strLine As String
    strLine = "C:\AUTOEXEC.BAT"
    Dim strMsg As String
    strMsg = "Line is: " & strLine & vbCrLf
    strMsg = strMsg & "Extension returned is : " & Get_Extension(strLine) & vbCrLf & vbCrLf
    strLine = "C:\AUTOEXEC"
    strMsg = strMsg & "New line is: " & strLine & vbCrLf
    Dim strTemp As Variant
    strTemp = Get_Extension(strLine)
    If IsNull(strTemp) Then
        strTemp = "Null"
    End If
    strMsg = strMsg & "Extension returned is : " & strTemp
    MsgBox strMsg, , "Get_Extension Test"
End Sub

Public Sub ViewCorners_Test()
    Dim aryCorners As Variant
    aryCorners = View_Corners
    Dim strMsg As String, ll As String, ur As String, TempPnt As String
    Dim Luprec As Long
    Luprec = ThisDrawing.GetVariable("luprec")
    TempPnt = aryCorners(0)
    ll = "(" & CStr(FormatPnt(TempPnt, Luprec))
    TempPnt = aryCorners(1)
    ll = ll & "," & CStr(FormatPnt(TempPnt, Luprec)) & ","
    TempPnt = aryCorners(2)
    ll = ll & CStr(FormatPnt(TempPnt, Luprec)) & ")"
    strMsg = "The lower left point of the view is " & ll & vbCrLf
    strMsg = strMsg & "The upper right point of the view is "
    TempPnt = aryCorners(3)
    ur = "(" & CStr(FormatPnt(TempPnt, Luprec))
    TempPnt = aryCorners(4)
    ur = ur & "," & CStr(FormatPnt(TempPnt, Luprec)) & ","
    TempPnt = aryCorners(5)
    ur = ur & CStr(FormatPnt(TempPnt, Luprec)) & ")"
    strMsg = "The lower left point of the view is " & ll & vbCrLf
    strMsg = strMsg & "The upper right point of the view is " & ur
    
    MsgBox strMsg, , "View_Corners Test"
End Sub

Attribute VB_Name = "basToolbox"

'   Paladin
'   Copyright (C) 1998,1999 by Paladin.  All rights reserved.

'   Permission to use or modify this software is hereby granted to the
'   licensee, provided that the above copyright notice appears in all
'   copies and that both that copyright notice and this permission
'   notice appear in all supporting documentation.

'   Permission is hereby granted to use this routine on the condition that
'   this header remains with the routine. No warrantity is implied or
'   expressed.

'   Original version   2-4-98  John Gibb
'            revised    -  -

Const gconSEP_DIR As String = "\"

Public Function parse(strLine As String, strDelimit As String, lngPosition As Long) As String
' this function takes the
'                                    position    position   position
'                                       1            2         3
' strLine holds the string  ie. "All good | men are | leaving the boat."
'                                              ^
'                                           boundary
' strdelimit is a one character string containing the delimiter to be used
' tempvar is returned
' lngPosition is what information position in the string you want
' Lpipe and Rpipe are the boundaries around the data

    Dim c As Long
    Dim Lpipe As Long
    Dim Rpipe As Long
    Dim mark As Long
    Dim tempvar As String
    Dim start As Long
    Dim datalen As Long
    Dim cnt As Long
    c = 1
    Lpipe = 0
    mark = 1
    tempvar = ""
    For cnt = 1 To lngPosition
        Do While Mid(strLine, c, 1) <> strDelimit And Len(strLine) >= c
            c = c + 1
        Loop
        Rpipe = c
        If mark = lngPosition - 1 Then
            Lpipe = c
        End If
        c = c + 1
        mark = mark + 1
    Next cnt
    start = Lpipe + 1
    datalen = (Rpipe - Lpipe) - 1
    parse = Mid(strLine, start, datalen)
End Function
Public Function chk_plural(var As Long, mode As Long)
' var is a passed in length of some item and mode is the type of word to return
' if the var is equal to zero or the var is greater than 1 then a plural is returned
' this function is used to create correct sentence structure for messages or
' data output.
' ie. You spin through a list of items and find none present and want to tell the
' user. Take the number of items found and build your sentence like this:

' inti = 5
' MsgBox CStr(inti) & " item" & chk_plural(inti, 1) & " " & chk_plural(inti, 4) & _
'        " been found."
        
    Dim plural As Boolean
    If var = 0 Or var > 1 Then plural = True
    
    Select Case mode
        Case 1
            If plural = True Then
                chk_plural = "s"
            Else
                chk_plural = ""
            End If
        Case 2
            If plural = True Then
                chk_plural = "are"
            Else
                chk_plural = "is"
            End If
        Case 3
            If plural = True Then
                chk_plural = "were"
            Else
                chk_plural = "was"
            End If
        Case 4
            If plural = True Then
                chk_plural = "have"
            Else
                chk_plural = "has"
            End If
        Case Else
            plural = ""
    End Select

End Function
Public Function IsFile(Filename As String) As Boolean
' check to see if the file exists on the hard drive
' return true or false
    Dim fname As String
    Dim varResult As Boolean
    fname = Dir(Filename)
    If Len(fname) = 0 Then
        varResult = False
    Else
        varResult = True
    End If
    IsFile = varResult

End Function
Public Function FindFile(Filename As String) As Variant
' This function mimics the AutoLISP Findfile function except
' that it passes back a NULL when the file is not found instead of a nil
' It passes back the full path and filename if it is found

    ' first split any path from the file name
    Dim strPath As String, strFileName As String
    Dim aryPaths() As String
    strPath = Get_Path(Filename)
    strFileName = strip_path(Filename)
    Dim fname As String
    Dim varResult As Boolean
    If Len(strPath) > 0 Then
        ' path on filename argument - use it and get out
        fname = Dir(Filename)
        If Len(fname) > 0 Then
            fname = Filename
            varResult = True
        End If
    Else
        ' no path found on filename argument - search the heirarchy
        ' get the autoCAD work (current) directory first
        Dim strWorkDir As String
        strWorkDir = CurDir
        strWorkDir = AddDirSep(strWorkDir)
        ' now get the drawing path DWGPREFIX (if any)
        Dim strDwgDir As String
        strDwgDir = ThisDrawing.GetVariable("dwgprefix")
        ' check to see if they are the same
        If UCase(strDwgDir) = UCase(strWorkDir) Then
            ' the same so just use on of them
            ReDim Preserve aryPaths(0)
            aryPaths(0) = strDwgDir
        Else
            ' not the same so use both for searching
            ReDim Preserve aryPaths(0)
            aryPaths(0) = strWorkDir
            ReDim Preserve aryPaths(1)
            aryPaths(1) = strDwgDir
        End If
        ' now get the ACADPREFIX (ACAD support path)
        Dim strSupportPath As String
        strSupportPath = ThisDrawing.GetVariable("acadprefix")
        ' now parse out all of the directories from the support path
        ' into an array
        Dim lngDirs As Long
        lngDirs = count_occurrences(strSupportPath, ";") + 1
        Dim lngI As Long, lngJ As Long
        lngJ = 1
        Dim upper As Long
        upper = UBound(aryPaths) + 1
        For lngI = upper To (lngDirs + upper)
            ReDim Preserve aryPaths(lngI)
            aryPaths(lngI) = AddDirSep(parse(strSupportPath, ";", lngJ))
            lngJ = lngJ + 1
        Next lngI
        ' now spin through the array and check each directory for the filename
        For lngI = 0 To UBound(aryPaths)
            fname = Dir(aryPaths(lngI) & strFileName)
            If Len(fname) > 0 Then
                fname = aryPaths(lngI) & fname
                varResult = True
                Exit For
            End If
        Next lngI
    End If ' path found on filename argument
    If varResult Then
        FindFile = fname
    Else
        FindFile = Null
    End If

End Function

Public Sub Fatal_error(error As Long, ByVal data As String)
' call this function as fatal_error erronum, data
' notice that you do not use () around the arguments when calling

    Select Case error
    Case 1
       MsgBox "Error code 1: Could not find the file " & _
                      UCase(data) & ". Please contact your supervisor."
    Case 2
        MsgBox "Error code 2: Could not open the file " & _
                      UCase(data) & ". Please contact your supervisor."
    Case 3
        MsgBox "Error code 3: Could not find the section header " & _
               "[" & UCase(data) & "]." & _
               " Please contact your supervisor."
    Case 4
        MsgBox "Error code 4: Could not find the key " & _
                UCase(data) & ". Please contact your supervisor."
    Case Else   ' Other values.
        MsgBox "Unknown error code " & CStr(error) & " for the data " & UCase(data) & _
               "Please contact your supervisor."
    End Select
    End         ' terminate the program
    
End Sub
Public Function count_occurrences(Line As String, strDelimit As String) As Long
' returns how many delimiters are in the line
    Dim i, cnt As Long
    cnt = 0
    For i = 1 To Len(Line)
        If strDelimit = Mid(Line, i, Len(strDelimit)) Then
            cnt = cnt + 1
        End If
    Next i
    
    count_occurrences = cnt

End Function

Public Function Token(Line As String, aString As String) As String
' take astring and return all text up to it from the line string
' if astring is not present in the line - return the whole line
    Dim x As Variant
    x = InStr(1, Line, aString)
    If x Then
       Token = Mid(Line, 1, x - 1)
    Else
       Token = Line
    End If
End Function

Public Function RightToken(Line As String, aString As String) As String
' take astring and return everything from line starting with astring
' if astring is not present in the line - return the whole line
    Dim x As Variant
    x = InStr(1, Line, aString)
    If x Then
       RightToken = Mid(Line, x, Len(Line))
    Else
       RightToken = Line
    End If
End Function
Public Function Get_Path(Line As String) As String
    Dim lngI As Long
    Dim strPath As String
    strPath = ""
    For lngI = Len(Line) To 1 Step -1
        If Mid(Line, lngI, 1) = "\" Or _
           Mid(Line, lngI, 1) = ":" Then
            strPath = Mid(Line, 1, lngI)
            Exit For
        End If
    Next lngI
    Get_Path = strPath
End Function
Public Function strip_path(Line As String) As String
    Dim dname As String
    Dim cnt As Long
    Dim ct As Long
    dname = UCase(Line)
    If Mid(Line, 2, 1) = ":" Then
        dname = Mid(dname, 3, Len(Line))
    End If
    cnt = 1
    ct = 0
    Dim i As Long
    For i = 1 To Len(dname)
        If Mid(dname, cnt, 1) = "\" Then
            ct = cnt
        End If
        cnt = cnt + 1
    Next i
    strip_path = Mid(dname, ct + 1, Len(dname))

End Function

Public Function spin(spinner As String) As String

Select Case spinner
    Case ""
        spin = "-"
    Case " "
        spin = "-"
    Case "-"
        spin = "\"
    Case "\"
        spin = "|"
    Case "|"
        spin = "/"
    Case "/"
        spin = "-"
    Case Else   ' Other values.
        spin = spinner
End Select

End Function
Public Function AddDirSep(strPathName As String) As String
' adds a backslash to the end of a directory string
' gstrSEP_DIR is a global constant
    If Right$(RTrim$(strPathName), Len(gconSEP_DIR)) <> gstrSEP_DIR Then
        strPathName = RTrim$(strPathName) & gconSEP_DIR                 ' add it when not on the end
    End If
    AddDirSep = strPathName
End Function
Public Function add_backslashes(dirstr As String)
' this function is necessary when writing out AutoLISP code that includes directories
' Since AutoLISP needs either two backslashes or one forward slash
    Dim i As Long
    Dim holdstr As String
    For i = 1 To Len(dirstr)
        If Mid(dirstr, i, 1) = "\" Then
            holdstr = holdstr & Mid(dirstr, i, 1) & "\"
        Else
            holdstr = holdstr & Mid(dirstr, i, 1)
        End If
    Next i
    add_backslashes = holdstr
End Function
Public Function Lst_Memb(Line As String, ctrl As ListBox) As Boolean
' check to see if line argument is in the list control
    Dim temp As Variant
    Dim i As Long
    Dim result As Boolean
    result = False
    For i = 0 To ctrl.ListCount - 1
        ctrl.ListIndex = i
        temp = ctrl.Text
        If temp = Line Then
            result = True
        End If
        
    Next i
    
    Lst_Memb = result
End Function

Public Function Enttype(Ent As Object) As String
        
        Select Case Ent.EntityType
            Case acArc
                Enttype = "ARC"
            Case acCircle
                Enttype = "CIRCLE"
            Case acEllipse
                Enttype = "ELLIPSE"
            Case acLine
                Enttype = "LINE"
            Case acPoint
                Enttype = "POINT"
            Case acRay
                Enttype = "RAY"
            Case ac3dFace
                Enttype = "3DFACE"
            Case ac3dPolyline
                Enttype = "3DPLINE"
            Case ac3dSolid
                Enttype = "3DSOLID"
            Case acAttribute
                Enttype = "ATTRIBUTE"
            Case acDimAligned
                Enttype = "DIMALIGNED"
            Case acDimAngular
                Enttype = "DIMANGULAR"
            Case acDimDiametric
                Enttype = "DIMDIAMETRIC"
            Case acDimOrdinate
                Enttype = "DIMORDINATE"
            Case acDimRadial
                Enttype = "DIMRADIAL"
            Case acDimRotated
                Enttype = "DIMROTATED"
            Case acGroup
                Enttype = "GROUP"
            Case acHatch
                Enttype = "HATCH"
            Case acLeader
                Enttype = "LEADER"
            Case acMtext
                Enttype = "MTEXT"
            Case acPolyline
                Enttype = "POLYLINE"
            Case acPolylineLight
                Enttype = "LWPOLYLINE"
            Case acPolymesh
                Enttype = "PMESH"
            Case acRaster
                Enttype = "RASTER"
            Case acRegion
                Enttype = "REGION"
            Case acShape
                Enttype = "SHAPE"
            Case acSolid
                Enttype = "SOLID"
            Case acSpline
                Enttype = "SPLINE"
            Case acText
                Enttype = "TEXT"
            Case acTolerance
                Enttype = "TOLERANCE"
            Case acTrace
                Enttype = "TRACE"
            Case acXline
                Enttype = "XLINE"
            Case Else
                Enttype = "UNKNOWN"
        End Select

End Function
Public Function DoesControlExist(Form As UserForm, ctrlName As String) As Boolean
' this function takes the userform and the suspected control name and verifies
' whether or not the control is present on the form
' True is returned when it is found and false when it is not found
' The control name is case sensitive normally so ucase is used to illiminate the
' problem
        Dim MyControl As Control
        Dim result As Boolean
        result = False
        For Each MyControl In Form.Controls
            If UCase(MyControl.Name) = UCase(ctrlName) Then
                result = True
                Exit For
            End If
        Next
        DoesControlExist = result
End Function

Public Function Strip_extension(Filename As String) As String
' This function takes a string containing a filename and
' returns the filename without the extension as a string
' should no extension be present in the filename, the filename is returned
    Dim Extension As String
    Extension = InStr(Filename, ".")
    If Extension > 0 Then
        Strip_extension = Left(Filename, Extension - 1)
    Else
        Strip_extension = Filename
    End If
    
End Function
Public Function Lst_Memb_Idx(Line As String, ctrl As Control) As Long
' check to see if line argument is in the list control
    Dim temp As String
    Dim i As Long
    Dim result As Long
    result = 0
'    i = 0
    For i = 0 To ctrl.ListCount - 1
        temp = ctrl.List(i, 1)
        If temp = Line Then
            result = i
        End If
        
    Next i
    Lst_Memb_Idx = result
End Function
Public Function Lst_Memb_Pos(Line As String, ctrl As ListBox) As Long
' check to see if line argument is in the list control
' if there return the index number
' if not return 0
    Dim temp As Variant
    Dim i As Long
    Dim result As Long
    result = 0
    For i = 0 To ctrl.ListCount - 1
        ctrl.ListIndex = i
        temp = ctrl.Text
        If temp = Line Then
            result = ctrl.ListIndex
            Exit For
        End If
    Next i
    Lst_Memb_Pos = result
End Function

Public Function Replace_Chr(Line As String, SearchChr As String, ReplaceChr As String) As String
' replace all occurances of the search character with the replacement character in the line and returns the line
' if no occurances are found in the line the line is returned unchanged.
    Dim strResult As String
    strResult = Line
    If InStr(1, Line, SearchChr) Then
        strResult = ""
        Dim lngI As Long
        For lngI = 1 To Len(Line)
            If Mid(Line, lngI, 1) = SearchChr Then
                strResult = strResult & ReplaceChr
            Else
                strResult = strResult & Mid(Line, lngI, 1)
            End If
        Next lngI
    End If
    Replace_Chr = strResult
End Function
Function StripTerminator(ByVal strString As String) As String
' returns the string with out the terminator or any characters following it
' or it returns the original string when no terminator present
    Dim intZeroPos As Integer
    Dim strResult As String
    strResult = strString
    intZeroPos = InStr(strString, Chr$(0))                  'get terminators position
    If intZeroPos > 0 Then
        strResult = Left$(strString, intZeroPos - 1)        'get up to it
    End If
    StripTerminator = strResult                             ' no, return the string
End Function

Public Function View_Corners() As Variant
' calculate the corners of the current view
' and return them in a variant array
' first 3 elements are the Lower left corner
' last 3 elemts are the upper right corner
' this is better than extmin and extmax because it gives accurate results
' even when there are no entities
    Dim dist, org, result As Variant
    Dim pnts(5), distx, disty, ratio, viewsize, orgx, orgy, orgz As Double
    
    dist = ThisDrawing.GetVariable("Screensize")
    viewsize = ThisDrawing.GetVariable("viewsize")
    org = ThisDrawing.GetVariable("viewctr")
    distx = dist(0)
    disty = dist(1)
    ratio = distx / disty
    distx = ratio * viewsize
    disty = viewsize
    orgx = org(0): orgy = org(1): orgz = org(2)
    pnts(0) = orgx + (-1 * (0.5 * distx))
    pnts(1) = orgy + (-1 * (0.5 * disty))
    pnts(2) = orgz
    pnts(3) = orgx + (0.5 * distx)
    pnts(4) = orgy + (0.5 * disty)
    pnts(5) = orgz
    result = pnts
    
    View_Corners = result
End Function
Public Function FormatPnt(aString As String, Units As Long) As String
    Dim strTemp As String
    Select Case Units
        Case 0
            strTemp = Format(aString, "#########0")
        Case 1
            strTemp = Format(aString, "#########0.0")
        Case 2
            strTemp = Format(aString, "#########0.0#")
        Case 3
            strTemp = Format(aString, "#########0.0##")
        Case 4
            strTemp = Format(aString, "#########0.0###")
        Case 5
            strTemp = Format(aString, "#########0.0####")
        Case 6
            strTemp = Format(aString, "#########0.0#####")
        Case 7
            strTemp = Format(aString, "#########0.0######")
        Case 8
            strTemp = Format(aString, "#########0.0#######")
        Case Else
            strTemp = Format(aString, "#########0.0#######")
    End Select
    FormatPnt = strTemp
End Function

Public Function Get_Extension(Line As String) As Variant
' take and return everything from the line after the right most period
' if a period is not present in the line - Null is returned
    Dim x As Long, lngI As Long
    For lngI = Len(Line) To 1 Step -1
        If Mid(Line, lngI, 1) = "." Then
            x = lngI
            Exit For
        End If
    Next lngI
    If x > 1 Then
       Get_Extension = Mid(Line, x + 1, Len(Line))
    Else
       Get_Extension = Null
    End If
End Function

Public Function Pad(string1 As String, stringlen As Long) As String
' return string1 with as many spaces filled on the end as needed to
' equal the stringlen passed in
' if string1 is less than the stringlen, just return string1
    Dim temp As Long
    Dim Mystring As String
    Dim i As Integer
    temp = stringlen - Len(string1)
    If temp > 0 Then
     Mystring = String(temp, " ")
    Else
     Mystring = ""
    End If
    Pad = string1 & Mystring
End Function

Attribute VB_Name = "frmList"
Attribute VB_Base = "0{F2A59773-A32E-11D2-99D1-72BDA8000000}{F2A59768-A32E-11D2-99D1-72BDA8000000}"
Attribute VB_Creatable = False
Attribute VB_PredeclaredId = True
Attribute VB_Exposed = False
Attribute VB_TemplateDerived = False
Attribute VB_Customizable = False
Public Sub check_control()
    Dim bolResult As Boolean
    bolResult = DoesControlExist(frmList, lstAlpha.Name)
    If bolResult Then
        MsgBox "The control lstAlpha exists on the form frmList", , "Results"
    Else
        MsgBox "The control lstAlpha does not exist on the form frmList", , "Results"
    End If

End Sub
Private Sub btnOK_Click()
    End
End Sub


Private Sub txtUser_KeyPress(ByVal KeyAscii As MSForms.ReturnInteger)
    If KeyAscii = 66 Or KeyAscii = 98 Then                  ' if b or B process it
        Dim bolResult As Variant
        Dim txtUser As String
        txtUser = Chr(KeyAscii)
        Stop
        bolResult = Lst_Memb(txtUser, lstAlpha)
        If bolResult Then
            MsgBox txtUser & " is in the list.", , "List"
        Else
            MsgBox txtUser & " is not in the list.", , "List"
        End If
    Else
        MsgBox "Please type either B or b.", , "List"
    End If

End Sub

Private Sub UserForm_Initialize()
    lstAlpha.AddItem "A"
    lstAlpha.AddItem "B"
    lstAlpha.AddItem "C"
    lstAlpha.AddItem "D"
    lstAlpha.AddItem "E"
    lstAlpha.AddItem "F"

End Sub

Attribute VB_Name = "frmShowObjectType"
Attribute VB_Base = "0{F2A59777-A32E-11D2-99D1-72BDA8000000}{F2A5976A-A32E-11D2-99D1-72BDA8000000}"
Attribute VB_Creatable = False
Attribute VB_PredeclaredId = True
Attribute VB_Exposed = False
Attribute VB_TemplateDerived = False
Attribute VB_Customizable = False
Private Sub btnGetObj_Click()
    Me.Hide
    Dim retEnt As Object
    Dim strEtype As String
    Dim pnt As Variant
    
    
    ' The following example waits for a input from user and returns the Line in retEnt
Retry:
    On Error Resume Next
    ThisDrawing.Utility.GetEntity retEnt, pnt, "Select an object"

    Select Case Err
        Case -2147352567
            GoTo ExitSub
        Case Is <> 0
            Err.Clear
            MsgBox "You need to select an existing object"
        Case Else
            strEtype = Enttype(retEnt)
            MsgBox "The object type is: " & strEtype
    End Select
    
    GoTo Retry
    
ExitSub:
    End
    'Enttype

End Sub

Attribute VB_Name = "frmSpinner"
Attribute VB_Base = "0{F2A5976E-A32E-11D2-99D1-72BDA8000000}{F2A59760-A32E-11D2-99D1-72BDA8000000}"
Attribute VB_Creatable = False
Attribute VB_PredeclaredId = True
Attribute VB_Exposed = False
Attribute VB_TemplateDerived = False
Attribute VB_Customizable = False
Public strSpinner As String

Private Sub btnOK_Click()
    End
End Sub

Private Sub btnStart_Click()
    Dim strSpinner As String
    Dim lngCnt As Long
    Dim lngIdx As Long
    Stop
    lngCnt = 0
    strSpinner = " "
    While lngCnt < 1000
        strSpinner = spin(strSpinner)
        lbSpin.Caption = "Working... " & strSpinner
        DoEvents
        ' place work here
        lngCnt = lngCnt + 1
    Wend
    lbSpin.Caption = ""
End Sub
