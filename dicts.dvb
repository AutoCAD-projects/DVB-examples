Attribute VB_Name = "Module1"
'Option Explicit
Public Dict As AcadDictionary


Sub Dicts()


    ' Dictionary objects should be global
    '
    On Error Resume Next
    Set Dict = ThisDrawing.Dictionaries.Item("My Dictionary")
    If Err.Number <> 0 Then
      Err.Clear
      Set Dict = ThisDrawing.Dictionaries.Add("My Dictionary")
    End If

  '  WriteXrecord "My stuff", 2.2, 4, "Result"
    ReadMyXrecord "My stuff", 2.2, 4, "Result"

End Sub




Sub WriteXrecord(Key As String, R As Double, I As Integer, S As String)
  Dim Xtyp(2) As Integer
  Dim XVar(2) As Variant
  Xtyp(0) = 40: XVar(0) = R
  Xtyp(1) = 60: XVar(1) = I
  Xtyp(2) = 1: XVar(2) = S
  Dim Xrec As AcadXRecord
  Set Xrec = Dict.AddXRecord(Key)
  Xrec.SetXRecordData Xtyp, XVar
End Sub


Sub ReadMyXrecord(Key As String, R As Double, I As Integer, S As String)
  Dim Xtyp, XVar As Variant
  Dim XR As AcadXRecord
  Set XR = Dict.Item(Key)
  XR.GetXRecordData Xtyp, XVar
  Dim J As Long
  For J = LBound(Xtyp) To UBound(Xtyp)
    If Xtyp(J) = 1 Then S = XVar(J)
    If Xtyp(J) = 40 Then R = XVar(J)
    If Xtyp(J) = 70 Then I = XVar(J)
  Next J
End Sub

Sub xdata()

    Dim Lin As AcadLine
    Dim PV1 As Variant, PV2 As Variant
    Dim PT1(0 To 2) As Double
    Dim PT2(0 To 2) As Double
    PT1(0) = 1#: PT1(1) = 1#: PT1(2) = 0#
    PT2(0) = 2#: PT2(1) = 1#: PT1(2) = 0#
    PV1 = PT1: PV2 = PT2
    Set Lin = ThisDrawing.ModelSpace.AddLine(PV1, PV2)
    
    Dim PT(1) As Integer
    Dim PV(1) As Variant
    Dim RR As Double
    RR = ThisDrawing.GetVariable("CDATE")
    PT(0) = 1001: PV(0) = "CREATED"
    PT(1) = 1040: PV(1) = RR
    ThisDrawing.RegisteredApplications.Add "CREATED"
    Lin.SetXData PT, PV



End Sub

Function Getdate() As Double
  Dim SS As AcadSelectionSet
  On Error Resume Next
  Set SS = ThisDrawing.SelectionSets.Add("TEMP")
  If Err.Number <> 0 Then
    Set SS = ThisDrawing.SelectionSets.Item("TEMP")
    Err.Clear
    SS.Clear
  End If
  'function continues
  Dim FT(1) As Integer, FV(1) As Variant
  Dim vFT As Variant, vFV As Variant
  FT(0) = 0: FV(0) = "LINE"
  FT(1) = 1001: FV(1) = "CREATED"
  vFT = FT: vFV = FV
  SS.Select acSelectionSetAll, , , vFT, vFV
  If SS.Count > 0 Then
    Dim Ent As AcadLine
    Set Ent = SS.Item(0)
    Ent.GetXData "CREATED", vFT, vFV
    GetSavedDate = vFV(1)
   Else
    GetSavedDate = 0#
  End If
End Function
