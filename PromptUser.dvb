Attribute VB_Name = "Module1"
Sub RunDialog()
UserForm1.Show
End Sub

Attribute VB_Name = "UserForm1"
Attribute VB_Base = "0{A271A4B4-E23C-11D2-AE6C-0060B0FC14A8}{A271A4A6-E23C-11D2-AE6C-0060B0FC14A8}"
Attribute VB_Creatable = False
Attribute VB_PredeclaredId = True
Attribute VB_Exposed = False
Attribute VB_TemplateDerived = False
Attribute VB_Customizable = False
Public strOp As String
Private Sub CheckBox1_Click()

Dim op As Boolean

op = CheckBox1.Value
  If op = True Then
    strOp = "ON"
    CheckBox1.Value = True
  Else
    strOp = "OFF"
     CheckBox1.Value = False
 End If

'UserForm1.Hide
MsgBox "User has Toggled CheckBox " & strOp

End Sub

Private Sub CommandButton1_Click()
Dim sysVarName As String
  
  UserForm1.Hide
' Save the Value in a User System Variable
sysVarName = "USERS1"
ThisDrawing.SetVariable sysVarName, strOp

End Sub

Private Sub UserForm_Click()

End Sub

Private Sub UserForm_Initialize()
  strOp = "ON"
End Sub
