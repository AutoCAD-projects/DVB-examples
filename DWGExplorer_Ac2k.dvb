Attribute VB_Name = "AppStuff"
'
' AppStuff
'
' this module's functions kick off the apps.
'
' R0  28 Feb 98  MJHunter, activecad@humbugreality.com
' R1  31 Mar 99  MJHunter  Modifications for AutoCAD 2000
'
Option Explicit
'
' Sub DWGEx
'   (
'   )
'
' returns:  nothing.
'
' this function runs the DWG Explorer.
'
' R0  28 Feb 98  MJHunter, activecad@humbugreality.com
'
Sub DWGEx()
    MainWin.Show
End Sub
'
' Sub WorkOnDwg
'   (
'   the drawing on which to work.
'   dwg     As  String
'   )
'
' returns:  nothing.
'
' this function.
'
' R0  28 Feb 98  MJHunter, activecad@humbugreality.com
'
Sub WorkOnDwg(dwg As String)

    On Error GoTo ERR_HANDLER
    
    '-----------------------------------------------
    ' open the drawing.
    Dim doc As AcadDocument
    Set doc = Documents.Open(dwg)
    
    '-----------------------------------------------
    ' modify this routine to do something useful
    '   here!
    Debug.Print "Opened " & ThisDrawing.Name & "!"
    
    '-----------------------------------------------
    ' uncomment this line if you want to save your
    '   changes.
    'doc.Save
    '-----------------------------------------------
    ' or could you save the drawing with a different
    '   name.
    'doc.SaveAs "newname.dwg"
    '-----------------------------------------------
    ' or you could save the drawing as a different
    '   version.
    'doc.SaveAs doc.FullName, acR12_dxf
    
    '-----------------------------------------------
    ' close the document now that we're done with
    '   it.
    doc.Close False
    
    Exit Sub

ERR_HANDLER:
    '-----------------------------------------------
    ' just print the error to the debug window.
    Debug.Print "Error in AppStuff.WorkOnDwg: " & Err.Number & " -- " & Err.Description
    Resume ERR_END
    
ERR_END:
End Sub

Attribute VB_Name = "FindFiles"
' FindFiles
'
' this module's functions search for files and directories.
'
' R0  28 Feb 98  MJHunter, activecad@humbugreality.com
'
Option Explicit
'
' Sub FindFile
'   (
'   )
'
' returns:  nothing.
'
' this function builds a collection containing every file with a
'   specific extension in or below a specified directory.
'
' call FindFile like this:
'
'   Dim files As Collection
'   Set files = New Collection
'   FindFile files, "c:\thedrawings\masters", "dwg"
'
' when FindFile returns, you can use it like this:
'   Dim cnt As Long
'   cnt = 0
'   For cnt = 1 To files.Count
'       **do something here**
'   Next cnt
'
' R0  28 Feb 98  MJHunter, activecad@humbugreality.com
'
Public Sub FindFile(ByRef files As Collection, doDir$, ext$)
    '-----------------------------------------------
    ' look through every file and directory for
    '   files with the specified extension.
    '-----------------------------------------------
    Dim dirs As Collection
    Set dirs = New Collection
    Dim file$
    '-----------------------------------------------
    ' add the trailing backslash, if it's not there.
    '-----------------------------------------------
    If (Right(doDir$, 1) <> "\") Then
        doDir$ = doDir$ & "\"
    End If
    
    '-----------------------------------------------
    ' go find the files!
    '-----------------------------------------------
    file$ = Dir(doDir$ & "*.*", vbDirectory)
    Do While (file$ <> "")
        '-----------------------------------------------
        ' check to see if this file is actually a
        '   directory.  ignore the special "." and ".."
        '   files.
        '-----------------------------------------------
        If ((file$ <> ".") And (file$ <> "..")) Then
            If ((GetAttr(doDir$ & file$) And vbDirectory) = vbDirectory) Then
                '-----------------------------------------------
                ' this is a directory, so save it so we can
                '   recurse into it later.
                '-----------------------------------------------
                dirs.Add doDir$ & file$
            Else
                '-----------------------------------------------
                ' this is a file, so check its extension.  if
                '   the extension matches what we're looking
                '   for, save the filename.
                '-----------------------------------------------
                Dim thisExt$
                If (Len(file$) > 4) Then
                    If (UCase(Right(file$, 3)) = UCase(ext$)) Then
                        files.Add doDir$ & file$
                    End If
                End If
            End If
        End If
        '-----------------------------------------------
        ' find the next file.
        '-----------------------------------------------
        file$ = Dir
    Loop
    
    '-----------------------------------------------
    ' now, recurse into any directories we found.
    '-----------------------------------------------
    If (dirs.Count > 0) Then
        Dim curDir%
        For curDir% = 1 To dirs.Count
            FindFile files, dirs(curDir%), ext$
        Next curDir%
    End If
    Set dirs = Nothing
End Sub

Attribute VB_Name = "FolderBrowse"
'
' FolderBrowse
'
' this module's functions allow the user to browse for a specific
'   folder or printer.
'
' R0  28 Feb 98  MJHunter, activecad@humbugreality.com
'
Option Explicit

'-----------------------------------------------
' the various parameters you can use to control
'   what the user browses for.  for more info,
'   see the December 1997 Visual Basic
'   Programmer's Journal (www.windx.com).
'-----------------------------------------------
Private Type BROWSEINFO
    '-----------------------------------------------
    ' owner.
    Owner As Long
    '-----------------------------------------------
    ' root IDL; can be null.
    RootIdl As Long
    '-----------------------------------------------
    ' receives display name.
    DisplayName As String
    '-----------------------------------------------
    ' title to display.
    Title As String
    '-----------------------------------------------
    ' BIF constants, or 0.
    Flags As Long
    '-----------------------------------------------
    ' callback address.
    CallbackAddress As Long
    '-----------------------------------------------
    ' callback info.
    CallbackParam As Long
    '-----------------------------------------------
    ' index to the system image list
    Image As Long
End Type

'-----------------------------------------------
' only allow the user to browse for printers.
'-----------------------------------------------
Private Const BIF_BROWSEFORPRINTER = &H2000&

'-----------------------------------------------
' start the browsing at the desktop level.
'-----------------------------------------------
Private Const CSIDL_DESKTOP = &H0

'-----------------------------------------------
' API calls.
'-----------------------------------------------
Private Declare Function SHGetSpecialFolderLocation Lib "Shell32.DLL" (ByVal hwndOwner As Long, ByVal Folder As Long, ByRef idl As Long) As Long
Private Declare Function SHGetPathFromIDList Lib "Shell32.DLL" (ByVal idl As Long, ByVal Path As String) As Long
Private Declare Function SHBrowseForFolder Lib "Shell32.DLL" (ByRef bi As BROWSEINFO) As Long
Private Declare Function GlobalFree Lib "kernel32" (ByVal hMem As Long) As Long
'
' Sub BrowseFolders
'   (
'   )
'
' returns:  the folder the user chose, or "" if the user cancelled.
'
' this function lets the user browse for a file.
'
' R0  28 Feb 98  MJHunter, activecad@humbugreality.com
'
Public Function BrowseFolders() As String
    BrowseFolders = DoBrowse(0, "Browse for Folder")
End Function
'
' Sub BrowsePrinters
'   (
'   )
'
' returns:  the printer the user chose, or "" if the user cancelled.
'
' this function lets the user browse for a printer.
'
' R0  28 Feb 98  MJHunter, activecad@humbugreality.com
'
Public Function BrowsePrinters() As String
    BrowsePrinters = DoBrowse(BIF_BROWSEFORPRINTER, "Browse for Printers")
End Function
'
' Sub DoBrowse
'   (
'   flags specifying what can be browsed.
'   inFlags     As  Long
'   the title to use for the Browse dialog.
'   inTitle     As  String
'   )
'
' returns:  the object the user chose, or "" if the user cancelled.
'
' this function lets the user browse for a folder, printer, or other
'   system resource.  the 'inFlags' parameter determines what the user
'   can browse for; see the Windows API help for SHBrowseForFolder for
'   more info.
'
' R0  28 Feb 98  MJHunter, activecad@humbugreality.com
'
Private Function DoBrowse(ByVal inFlags As Long, ByVal inTitle As String) As String

    On Error GoTo ERR_HANDLER
    '-----------------------------------------------
    ' assume failure.
    DoBrowse = ""
    
    '-----------------------------------------------
    ' the maximum string length.
    Const MAX_LEN = 260
    
    '-----------------------------------------------
    ' if we can get a reference to the Desktop
    '   object,
    Dim theIdl As Long
    If (SHGetSpecialFolderLocation(0, CSIDL_DESKTOP, theIdl) = 0) Then
        '-----------------------------------------------
        ' set up the BrowseInfo information
        Dim bif As BROWSEINFO
        With bif
            .Owner = 0
            .RootIdl = theIdl
            .DisplayName = Space(MAX_LEN)
            .Title = inTitle
            .Flags = inFlags
        End With
        '-----------------------------------------------
        ' and let the user browse.
        theIdl = SHBrowseForFolder(bif)
        '-----------------------------------------------
        ' if the user chose something,
        Dim folderPath As String
        If (theIdl <> 0) Then
            '-----------------------------------------------
            ' attempt to turn the ID into a full path;
            '   otherwise, use the filename from the
            '   BrowseInfo data.
            folderPath = Space(MAX_LEN)
            If (CBool(SHGetPathFromIDList(theIdl, folderPath))) Then
                DoBrowse = TrimStringAtNull(folderPath)
            Else
                DoBrowse = TrimStringAtNull(folderPath = bif.Title)
            End If
        End If
        '-----------------------------------------------
        ' BrowseForFolder() allocates some memory, but
        '   it's up to us to free it.
        Call GlobalFree(theIdl)
    End If
    
    Exit Function

ERR_HANDLER:
    '-----------------------------------------------
    ' just print the error to the debug window.
    Debug.Print "Error in FolderBrowse.DoBrowse: " & Err.Number & " -- " & Err.Description
    Resume ERR_END
    
ERR_END:
End Function
'
' Sub TrimStringAtNull
'   (
'   the string to trim.
'   value   As  String
'   )
'
' returns:  the input string truncated at the first null character.
'
' this function truncates a string at its first null character.
'
' R0  28 Feb 98  MJHunter, activecad@humbugreality.com
'
Private Function TrimStringAtNull(ByVal value As String) As String

    On Error GoTo ERR_HANDLER
    
    '-----------------------------------------------
    ' the location of the first null character.
    Dim loc As Integer
    
    '-----------------------------------------------
    ' look for a null character.
    loc = InStr(value, vbNullChar)
    Select Case loc
        '-----------------------------------------------
        ' if it is anywhere after the first character,
        Case Is > 1
            '-----------------------------------------------
            ' trim the string at its location.
            TrimStringAtNull = Left$(value, loc - 1)
        '-----------------------------------------------
        ' it is isn't found,
        Case 0
            '-----------------------------------------------
            ' there's nothing to do.
            TrimStringAtNull = loc
        '-----------------------------------------------
        ' if it's the first character,
        Case 1
            '-----------------------------------------------
            ' we have an empty string.
            TrimStringAtNull = ""
    End Select
    
    Exit Function

ERR_HANDLER:
    '-----------------------------------------------
    ' just print the error to the debug window.
    Debug.Print "Error in FolderBrowse.TrimStringAtNull: " & Err.Number & " -- " & Err.Description
    Resume ERR_END
    
ERR_END:
End Function

Attribute VB_Name = "MainWin"
Attribute VB_Base = "0{B376325B-9076-11D3-B162-00C04F7FE74F}{B3763251-9076-11D3-B162-00C04F7FE74F}"
Attribute VB_Creatable = False
Attribute VB_PredeclaredId = True
Attribute VB_Exposed = False
Attribute VB_TemplateDerived = False
Attribute VB_Customizable = False
'
' MainWin
'
' this form is the UI for the app.
'
' R0  28 Feb 98  MJHunter, activecad@humbugreality.com
' R1  31 Mar 99  MJHunter  Modifications for AutoCAD 2000
'
Option Explicit
'
' Sub BrowseForStartDir_Click
'   (
'   )
'
' returns:  nothing.
'
' this function lets the user browse for the top-level
'   folder, then sets the StartDir text box to the user's
'   choice.
'
' R0  28 Feb 98  MJHunter, activecad@humbugreality.com
'
Private Sub BrowseForStartDir_Click()
    StartDir.Text = BrowseFolders
End Sub
'
' Sub Go_Click
'   (
'   )
'
' returns:  nothing.
'
' this function discovers every DWG file in or under the
'   starting directory, then calls DoIt for each drawing.
'
' R0  20 Oct 97  MJHunter
'
Private Sub Go_Click()

    On Error GoTo ERR_HANDLER
    
    '-----------------------------------------------
    ' remove any spaces from the starting directory.
    StartDir.Text = Trim$(StartDir.Text)
    
    '-----------------------------------------------
    ' make sure the starting directory has a
    '   trailing backslash.
    If (Right$(StartDir.Text, 1) <> "\") Then
        StartDir.Text = StartDir.Text & "\"
    End If
    
    '-----------------------------------------------
    ' search for DWG files.
    Dim files As Collection
    Set files = New Collection
    FindFile files, StartDir.Text, "DWG"
    
    '-----------------------------------------------
    ' initialize the progress bar.
    Progress.Min = 0
    Progress.Max = files.Count
    Progress.value = 0
    
    '-----------------------------------------------
    ' do something to each drawing.
    Dim cnt As Long
    For cnt = 1 To files.Count
        Progress.value = cnt
        WorkOnDwg files(cnt)
    Next cnt
    
    Beep
    MsgBox "All done!", vbOKOnly, "DWG Explorer"
    Unload Me
    
    Exit Sub
    
ERR_HANDLER:
    '-----------------------------------------------
    ' just print the error to the debug window.
    Debug.Print "Error in MainWin.Go_Click: " & Err.Number & " -- " & Err.Description
    Resume ERR_END
    
ERR_END:
End Sub
