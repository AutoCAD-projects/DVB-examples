Attribute VB_Name = "modMain"
'--------------------------------------------------------------------------------------------------------------------
' Purpose: AutoCAD startup routine
'--------------------------------------------------------------------------------------------------------------------
Option Explicit
Const PathSource As String = "Z:\ServerDvbFiles\"
Const PathUser As String = "C:\Temp\"

Public Sub AcadStartup()
On Error GoTo ErrTrap
'--------------------------------------------------------------------------------------------------------------------
' Purpose: To load macros and/or projects and/or menus into AutoCAD. This subroutine will run everytime AutoCAD is opened.
'--------------------------------------------------------------------------------------------------------------------
Dim colFiles    As New Collection
Dim fileName    As Variant 'Path and File name variable in loop
Dim fileLoad    As String

    'Call FileCopy(PathSource & "*.*", PathUser & "*.*")
    Call RecursiveDir(colFiles, PathUser, "*.dvb", False)
    For Each fileName In colFiles
        fileLoad = fileName
        Call LoadDvb(fileLoad)
    Next fileName

ExitProcedure:
    On Error Resume Next
    Exit Sub

ErrTrap:
    Select Case Err.Number
        Case Is <> 0
            Call DisplayErrorMessage("AcadStartup", "modMain", Err.Number, Err.Description)
            Resume ExitProcedure
        Case Else
            Resume ExitProcedure
    End Select
    
End Sub

Public Function RecursiveDir( _
ByVal pcolFiles As Collection, _
ByVal pstrFolder As String, _
ByVal pstrFileSpec As String, _
ByVal pbIncludeSubfolders As Boolean) As Variant
'--------------------------------------------------------------------------------------------------------------------
' Purpose: loop through all directories and subdirectories
'--------------------------------------------------------------------------------------------------------------------
On Error GoTo ErrTrap
Dim colFolders  As New Collection
Dim varTemp     As Variant
Dim varFolder   As Variant

    'Add files in strFolder matching strFileSpec to colFiles
    pstrFolder = TrailingSlash(pstrFolder)
    varTemp = Dir(pstrFolder & pstrFileSpec)
    Do While varTemp <> vbNullString
        pcolFiles.Add pstrFolder & varTemp
        varTemp = Dir
    Loop

    If pbIncludeSubfolders Then
        'Fill colFolders with list of subdirectories of strFolder
        varTemp = Dir(pstrFolder, vbDirectory)
        Do While varTemp <> vbNullString
            If (varTemp <> ".") And (varTemp <> "..") Then
                If (GetAttr(pstrFolder & varTemp) And vbDirectory) <> 0 Then
                    colFolders.Add varTemp
                End If
            End If
            varTemp = Dir
        Loop

        'Call RecursiveDir for each subfolder in colFolders
        For Each varFolder In colFolders
            Call RecursiveDir(pcolFiles, pstrFolder & varFolder, pstrFileSpec, True)
        Next varFolder
    End If

ExitProcedure:
    On Error Resume Next
    
ErrTrap:
    Select Case Err.Number
        Case Is <> 0
            Call DisplayErrorMessage("RecursiveDir", "modMain", Err.Number, Err.Description)
            Resume ExitProcedure
        Case Else
            Resume ExitProcedure
    End Select
    
End Function

Public Function TrailingSlash(ByVal folderDirectory As String) As String
'--------------------------------------------------------------------------------------------------------------------
' Purpose: handles the backslash on directory path
'--------------------------------------------------------------------------------------------------------------------
On Error GoTo ErrTrap

    If Len(folderDirectory) > 0 Then
        If Right(folderDirectory, 1) = "\" Then
            TrailingSlash = folderDirectory
        Else
            TrailingSlash = folderDirectory & "\"
        End If
    End If
    
ExitProcedure:
    On Error Resume Next
    
ErrTrap:
    Select Case Err.Number
        Case Is <> 0
            Call DisplayErrorMessage("TrailingSlash", "modMain", Err.Number, Err.Description)
            Resume ExitProcedure
        Case Else
            Resume ExitProcedure
    End Select
    
End Function

Public Function LoadDvb(projectName As String, _
Optional isLoad As Boolean = True, _
Optional macroName As String = "")
On Error GoTo ErrTrap
'--------------------------------------------------------------------------------------------------------------------
' Purpose:              To load and/or unload projects, macros
' Parameters:
'                       projectName = Project file (*.dvb) path and name
'                       isLoad      = True if you want to load the project / False to unload the project
'                       macroName   = Subroutine Name to run as the project loads.
'--------------------------------------------------------------------------------------------------------------------
Dim ACADApp As AcadApplication
Set ACADApp = GetObject(, "AutoCAD.Application")

    If isLoad Then
        If IsLoaded(projectName) = False Then   ' Is the project already loaded?
            ACADApp.LoadDvb projectName         ' Then load the project
            If macroName <> "" Then             ' Macro will run at startup if passed in
                ACADApp.RunMacro macroName      ' Then run macro
            End If
        End If
    Else
        ACADApp.UnloadDVB projectName           ' Then unload project
    End If

ExitProcedure:
    On Error Resume Next
    Set ACADApp = Nothing
    Exit Function

ErrTrap:
    Select Case Err.Number
        Case Is = -2145320886   'project already loaded.
            MsgBox "DVB file did not load properly." & vbCrLf & "To use this Tool, try restarting AutoCAD.", vbCritical, "Load Failure!"
            Resume ExitProcedure
        Case Is <> 0
            Call DisplayErrorMessage("LoadDvb", "modMain", Err.Number, Err.Description)
            Resume ExitProcedure
        Case Else
            Resume ExitProcedure
    End Select
    
End Function

Public Function IsLoaded(projectPath As String) As Boolean
'--------------------------------------------------------------------------------------------------------------------
' Purpose: Check to see if the project is loaded yet.
'--------------------------------------------------------------------------------------------------------------------
On Error GoTo ErrTrap
Dim objIDE      As Object       ' code window
Dim projectName As String       ' project name for Loop
Dim loopCount   As Integer
Set objIDE = Application.VBE    ' code window for this application

    For loopCount = 1 To objIDE.VBProjects.Count   ' total number of projects
    projectName = objIDE.VBProjects(loopCount).BuildFileName ' name of project via index
        If StrComp(projectPath, projectName, vbTextCompare) = 0 Then ' compare names
            IsLoaded = True 'the project is loaded.
            Resume ExitProcedure
        End If
    Next loopCount
    IsLoaded = False    'the project is NOT loaded.

ExitProcedure:
    On Error Resume Next
    objIDE = Nothing
    Exit Function

ErrTrap:
    Select Case Err.Number
        Case Is <> 0
            Call DisplayErrorMessage("IsLoaded", "modMain", Err.Number, Err.Description)
            Resume ExitProcedure
        Case Else
            Resume ExitProcedure
    End Select

End Function

Public Sub DisplayErrorMessage( _
ByVal procedureName As String, _
ByVal moduleName As String, _
errorNumber As Double, _
errorDescription As String, _
Optional ByVal errorLine As Variant = 0, _
Optional ByVal msgTitle As String = "Unexpected Error")
'--------------------------------------------------------------------------------------------------------------------
' Purpose: Global error message for all procedures
'--------------------------------------------------------------------------------------------------------------------
On Error Resume Next
Dim msg As String

    msg = "Contact your system administrator."
    msg = msg & vbCrLf & "Module: " & moduleName
    msg = msg & vbCrLf & "Procedure: " & procedureName
    msg = msg & IIf(errorLine = 0, "", vbCrLf & "Error Line: " & errorLine)
    msg = msg & vbCrLf & "Error #: " & errorNumber
    msg = msg & vbCrLf & "Error Description: " & errorDescription
    MsgBox msg, vbCritical, msgTitle

End Sub
