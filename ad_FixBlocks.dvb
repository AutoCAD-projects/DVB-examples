Attribute VB_Name = "Module1"
'
'  ad_FixBlocks
'
'  This routine demonstrates the selective updating of particular
'     block attributes in a drawing.
'  It was developed in AutoCAD 2000.
'  Demand load:  -vbarun;ad_FixBlocks.dvb!ad_FixBlocks;
'
'  version 1.00
'  5/17/2001
'
'  Copyright©2001 ActiveDwg.com
'
'  This routine is provided for demonstration purposes only and must
'    not be used for critical applications without your verification
'    that this routine will perform as you intended.
'  This routine may be freely utilized for your own personal use so long
'    as the entire contents of this header remain intact.
'  This routine is provided "as-is" and no declaration, written or implied,
'    is made as to its reliability for any particular task. Any use of this
'    routine is solely at your own risk.
'
Option Explicit

Sub ad_FixBlocks()
  Dim adSS As AcadSelectionSet
  Dim adBlocktoFix As String
  Dim fType(0 To 1) As Integer, fData(0 To 1)
  Dim adDwgBlock As AcadBlockReference
  Dim adBlockAttributes As Variant
  Dim i As Integer
  On Error Resume Next
  adBlocktoFix = "Piece_Mark"  '<-- Your block name goes here
  Set adSS = objSelCol.Add("adSS")
  If Err Then Set adSS = ThisDrawing.SelectionSets.Add("adSS")
  adSS.Clear
  fType(0) = 0: fData(0) = "INSERT": fType(1) = 2: fData(1) = adBlocktoFix
  adSS.Select acSelectionSetAll, , , fType, fData
  i = 0
  For Each adDwgBlock In adSS
    If adDwgBlock.Name = adBlocktoFix Then
      adBlockAttributes = adDwgBlock.GetAttributes
      If adBlockAttributes(0).TextString = "W-28" Then  '<-- This is the search criteria
        adBlockAttributes(1).TextString = "250.00"      '<-- This is the update
        adBlockAttributes(2).TextString = "137.62"      '<-- This is the update
        i = i + 1
      ElseIf adBlockAttributes(0).TextString = "W-32" Then  '<-- This is the search criteria
        adBlockAttributes(1).TextString = "200.30"      '<-- This is the update
        adBlockAttributes(2).TextString = "105.65"      '<-- This is the update
        i = i + 1
      End If
    End If
  Next
  ThisDrawing.Application.Update
  MsgBox i & " blocks updated."
End Sub
