Attribute VB_Name = "ThisDrawing"
Attribute VB_Base = "0{8E75D913-3D21-11D2-85C4-080009A0C626}"
Attribute VB_Creatable = False
Attribute VB_PredeclaredId = True
Attribute VB_Exposed = True
Attribute VB_TemplateDerived = False
Attribute VB_Customizable = True
'      AutoCAD 2000
'
'      Events Example Code ActiveX Automation.
'
'      Copyright (C) 1999 by Autodesk, Inc.
'
'      Permission to use, copy, modify, and distribute this software
'      for any purpose and without fee is hereby granted, provided
'      that the above copyright notice appears in all copies and
'      that both that copyright notice and the limited warranty and
'      restricted rights notice below appear in all supporting
'      documentation.
'
'      AUTODESK PROVIDES THIS PROGRAM "AS IS" AND WITH ALL FAULTS.
'      AUTODESK SPECIFICALLY DISCLAIMS ANY IMPLIED WARRANTY OF
'      MERCHANTABILITY OR FITNESS FOR A PARTICULAR USE.  AUTODESK, INC.
'      DOES NOT WARRANT THAT THE OPERATION OF THE PROGRAM WILL BE
'      UNINTERRUPTED OR ERROR FREE.
'
'      Use, duplication, or disclosure by the U.S. Government is subject to
'      restrictions set forth in FAR 52.227-19 (Commercial Computer
'      Software - Restricted Rights) and DFAR 252.227-7013(c)(1)(ii)
'      (Rights in Technical Data and Computer Software), as applicable.
'
Option Explicit

Public WithEvents PLine As AcadLWPolyline       ' Use with Modified Event Example

Public WithEvents ACADApp As AcadApplication    ' Use with Application Event Examples


'------------------------------------------------------------------
' Document Events
'------------------------------------------------------------------
Private Sub AcadDocument_Activate()
    ' This example intercepts a drawing Activate event.
    '
    ' This event is triggered when a drawing window becomes active.
    '
    ' To trigger this example event: Either open a new drawing or switch from
    ' one drawing window to another

    MsgBox "You have just activated a drawing!"
End Sub

Private Sub AcadDocument_BeginClose()
    ' This example intercepts a drawing BeginClose event.
    '
    ' This event is triggered when a drawing receives a request to close.
    '
    ' To trigger this example event: Close an open drawing

    MsgBox "A drawing has just been closed!"
End Sub

Private Sub AcadDocument_BeginCommand(ByVal CommandName As String)
    ' This example intercepts a drawing BeginCommand event.
    '
    ' This event is triggered when a drawing receives
    ' any command compatible with this event.
    '
    ' To trigger this example event: Issue any command to an open drawing from
    ' either the command line, VBA, the ACAD menus, the ACAD toolbars, or LISP.

    ' Use the "CommandName" variable to determine which command was started
    MsgBox "A drawing has just been issued a " & CommandName & " command."
End Sub

Private Sub AcadDocument_BeginDoubleClick(ByVal PickPoint As Variant)
    ' This example intercepts a drawing BeginDoubleClick event.
    '
    ' This event is triggered when a drawing receives
    ' a double mouse click in its working area.
    '
    ' To trigger this example event: Position the mouse over the working area of
    ' a drawing window and double-click the left mouse button

    ' Use the "PickPoint" variable to determine where on the drawing the user clicked
    MsgBox "A drawing has just been double-clicked at:" & vbCrLf & _
            PickPoint(0) & vbCrLf & _
            PickPoint(1) & vbCrLf & _
            PickPoint(2)
End Sub

Private Sub AcadDocument_BeginLisp(ByVal FirstLine As String)
    ' This example intercepts a drawing BeginLisp event.
    '
    ' This event is triggered when a drawing receives
    ' a request to evaluate a LISP expression.
    '
    ' To trigger this example event: Start the evaluation of a LISP expression

    ' Use the "FirstLine" variable to help the user determine which LISP expression is running
    MsgBox "A LISP expression has just started to be evaluated.  The first line of the expression is: " & FirstLine

End Sub

Private Sub AcadDocument_BeginPlot(ByVal DrawingName As String)
    ' This example intercepts a drawing BeginPlot event.
    '
    ' This event is triggered when a drawing receives a plot request.
    '
    ' To trigger this example event: Plot an open drawing

    ' Use the "DrawingName" variable to determine which drawing is about to plot
    MsgBox "A drawing has just received a request to plot for: " & DrawingName

End Sub

Private Sub AcadDocument_BeginRightClick(ByVal PickPoint As Variant)
    ' This example intercepts a drawing BeginRightClick event.
    '
    ' This event is triggered when a drawing receives
    ' a right mouse click in its working area.
    '
    ' To trigger this example event: Position the mouse over the working area of
    ' a drawing window and click the right mouse

    ' Use the "PickPoint" variable to determine where on the drawing the user clicked
    MsgBox "A drawing has just been right-clicked at:" & vbCrLf & _
            PickPoint(0) & vbCrLf & _
            PickPoint(1) & vbCrLf & _
            PickPoint(2)

End Sub

Private Sub AcadDocument_BeginSave(ByVal FileName As String)
    ' This example intercepts a drawing BeginSave event.
    '
    ' This event is triggered when a drawing receives a request to be saved.
    '
    ' To trigger this example event: Save an open drawing

    ' Use the "FileName" variable to determine where the drawing file is being saved
    MsgBox "A drawing is about to be saved to: " & FileName
End Sub


Private Sub AcadDocument_BeginShortcutMenuCommand(ShortcutMenu As AutoCAD.IAcadPopupMenu, ByVal Command As String)
    ' This example intercepts a shortcut menu start while you are in the command mode.
    '
    MsgBox "You have just initiated a shortcut menu in command mode!"

End Sub

Private Sub AcadDocument_BeginShortcutMenuDefault(ShortcutMenu As AutoCAD.IAcadPopupMenu)
    ' This example intercepts a shortcut menu start while you are in the default mode.
    '
    MsgBox "You have just initiated a shortcut menu in default mode!"
End Sub

Private Sub AcadDocument_BeginShortcutMenuEdit(ShortcutMenu As AutoCAD.IAcadPopupMenu, SelectionSet As AutoCAD.IAcadSelectionSet)
    ' This example intercepts a shortcut menu start while you are in the edit mode.
    '
    MsgBox "You have just initiated a shortcut menu in edit mode!"
End Sub
Private Sub AcadDocument_BeginShortcutMenuGrip(ShortcutMenu As AutoCAD.IAcadPopupMenu)
    ' This example intercepts a shortcut menu start while you are in the grip mode.
    '
    MsgBox "You have just initiated a shortcut menu in grip mode!"
End Sub
Private Sub AcadDocument_BeginShortcutMenuOSnap(ShortcutMenu As AutoCAD.IAcadPopupMenu)
    ' This example intercepts a shortcut menu start while you are in the osnap mode.
    '
    MsgBox "You have just initiated a shortcut menu in osnap mode!"
End Sub
Private Sub AcadDocument_Deactivate()
    ' This example intercepts a drawing DeActivate event.
    '
    ' This event is triggered when a drawing window looses focus.
    '
    ' To trigger this example event: Open two drawings and switch from
    ' one drawing window to another

    MsgBox "You have just deactivated a drawing!"
End Sub

Private Sub AcadDocument_EndCommand(ByVal CommandName As String)
    ' This example intercepts a drawing EndCommand event.
    '
    ' This event is triggered when a drawing receives
    ' any command compatible with this event.
    '
    ' To trigger this example event: Issue any command to an open drawing from
    ' either the command line, VBA, the ACAD menus, the ACAD toolbars, or LISP.
    ' When the command is finished this event will trigger.

    ' Use the "CommandName" variable to determine which command just finished
    MsgBox "A drawing has just finished a " & CommandName & " command."

End Sub

Private Sub AcadDocument_EndLisp()
    ' This example intercepts a drawing BeginLisp event.
    '
    ' This event is triggered when a drawing finishes
    ' a the evaluation of a LISP expression.
    '
    ' To trigger this example event: Start the evaluation of a LISP expression
    ' wait for it to finish being evaluated

    MsgBox "A LISP expression has just finished being evaluated!"

End Sub

Private Sub AcadDocument_EndPlot(ByVal DrawingName As String)
    ' This example intercepts a drawing EndPlot event.
    '
    ' This event is triggered when a drawing finishes a plot request.
    '
    ' To trigger this example event: Plot an open drawing and wait for the plot to finish

    ' Use the "DrawingName" variable to determine which drawing just finished plotting
    MsgBox "A drawing has just finished a plot request!"
End Sub

Private Sub AcadDocument_EndSave(ByVal FileName As String)
    ' This example intercepts a drawing EndSave event.
    '
    ' This event is triggered when a drawing finishes a save request.
    '
    ' To trigger this example event: Save an open drawing and wait for the save to complete

    ' Use the "FileName" variable to determine where the drawing file was saved
    MsgBox "A drawing has just been saved to: " & FileName
End Sub

Private Sub AcadDocument_EndShortcutMenu(ShortcutMenu As AutoCAD.IAcadPopupMenu)
    ' This example intercepts a drawing EndShortcutMenu event.
    '
    ' This event is triggered when the user closes a drawing shortcut menu.
    '
    ' To trigger this example event: Right click the mouse in the working area of a drawing,
    ' wait for the shortcut menu to be displayed and then dismiss the shortcut menu

    MsgBox "A shortcut menu was just closed!"
End Sub

Private Sub AcadDocument_LayoutSwitched(ByVal LayoutName As String)
    ' This example intercepts a drawing LayoutSwitched event.
    '
    ' This event is triggered when the user switches to a different
    ' drawing layout view.
    '
    ' To trigger this example event: Open a drawing and change its layout view
    '
    ' For example: Switch the drawing from Model view to Layout1 view

    ' Use the "LayoutName" variable to determine the which layout view we changed to
    MsgBox "The drawing layout was just changed to: " & LayoutName
End Sub

Private Sub AcadDocument_LispCancelled()
    ' This example intercepts a drawing LispCancelled event.
    '
    ' This event is triggered when the evaluation of a LISP expression is cancelled.
    '
    ' To trigger this example event: Run a LISP expression and
    ' cancel the LISP evaluation before it finishes

    MsgBox "A LISP evaluation was just cancelled."
End Sub


Private Sub AcadDocument_ObjectAdded(ByVal Object As Object)
    ' This example intercepts a drawing ObjectAdded event.
    '
    ' This event is triggered when an object is added to a drawing.
    '
    ' To trigger this example event: Add an object to an open drawing

    ' Use the "Object" variable to determine the type of object added
    MsgBox "A " & TypeName(Object) & " was just added to the drawing!"
End Sub

Private Sub AcadDocument_ObjectErased(ByVal ObjectID As Long)
    ' This example intercepts a drawing ObjectErased event.
    '
    ' This event is triggered when an object is removed from a drawing.
    '
    ' To trigger this example event: Delete (Cut) an existing object from an open drawing

    ' Use the "Object" variable to determine the type of object removed
    MsgBox "The ID of the object deleted is: " & ObjectID

End Sub

Private Sub AcadDocument_ObjectModified(ByVal Object As Object)
    ' This example intercepts a drawing ObjectModified event.
    '
    ' This event is triggered when an object in a drawing is modified.
    '
    ' To trigger this example event: Modify an object in any open drawing

    ' Use the "Object" variable to determine the type of object modified
    MsgBox "A " & TypeName(Object) & " was just modified!"
End Sub

Private Sub AcadDocument_SelectionChanged()
    ' This example intercepts a drawing SelectionChanged event.
    '
    ' This event is triggered when the current selection set in a drawing is modified.
    '
    ' To trigger this example event: Select or deselect objects in any open drawing

    MsgBox "The selection set in a drawing was just changed!"
End Sub

Private Sub AcadDocument_WindowChanged(ByVal WindowState As Long)
    ' This example intercepts a drawing WindowChanged event.
    '
    ' This event is triggered when the window state of the
    ' current drawing window is changed.
    '
    ' To trigger this example event: Change the window state of the drawing window
    '
    ' For example: Minimize or maximize the drawing window

    Dim CurrentState As String

    ' Use the "WindowState" variable to determine the new drawing window state
    Select Case WindowState
        Case acMin: CurrentState = "Minimized"
        Case acMax: CurrentState = "Maximized"
        Case acNorm: CurrentState = "Normal Size"
    End Select

    MsgBox "The drawing window is now: " & CurrentState
End Sub

Private Sub AcadDocument_WindowMovedOrResized(ByVal HWNDFrame As Long, ByVal bMoved As Boolean)
    ' This example intercepts a drawing WindowMovedOrResized event.
    '
    ' This event is triggered when the drawing window is moved or resized
    '
    ' To trigger this example event: Move or resize the drawing window

    Dim CurrentState As String

    ' Use the "bmoved" variable to determine if we moved or sized the drawing window
    CurrentState = IIf(bMoved, "Moving", "Sizing")

    MsgBox "The drawing window appearance was changed by: " & CurrentState
End Sub









'----------------------------------------------------------------------------
' Application Events
'----------------------------------------------------------------------------

Sub Example_AcadApplication_Events()
    ' This example intializes the public variable (ACADApp) which will be used
    ' to intercept AcadApplication Events
    '
    ' The VBA WithEvents statement makes it possible to intercept an generic object
    ' with the events associated with that object.
    '
    ' Before you will be able to trigger any of the AcadApplication events,
    ' you will first need to run this procedure.
    
    ' We could get the application from the ThisDocument object, but that would
    ' require having a drawing open, so we grab it from the system.
    Set ACADApp = GetObject(, "AutoCAD.Application")
End Sub

Private Sub ACADApp_ARXLoaded(ByVal AppName As String)
    ' This example intercepts an Application ARXLoaded event.
    '
    ' This event is triggered when the AutoCAD loads an ARX application
    '
    ' To trigger this example event:
    '     1) Make sure to run the example that initializes
    '     the public variable (named ACADApp) linked to this event.
    '
    '     2) Load an ARX application into AutoCAD

    ' Use the "AppName" variable to notify the user which ARX application was loaded
      MsgBox "AutoCAD just loaded the ARX application: " & AppName

End Sub

Private Sub ACADApp_AppActivate()
    ' This example intercepts an Application AppActivate event.
    '
    ' This event is triggered when the AutoCAD application receives focus
    '
    ' To trigger this example event:
    '     1) Make sure to run the example that initializes
    '     the public variable (named ACADApp) linked to this event.
    '
    '     2) Switch focus from AutoCAD to another Windows application
    '     and then back again

      MsgBox "AutoCAD was just activated!"
End Sub

Private Sub ACADApp_AppDeactivate()
    ' This example intercepts an Application AppDeactivate event.
    '
    ' This event is triggered when the AutoCAD application looses focus
    '
    ' To trigger this example event:
    '     1) Make sure to run the example that initializes
    '     the public variable (named ACADApp) linked to this event.
    '
    '     2) Switch focus from AutoCAD to another Windows application

      MsgBox "AutoCAD just lost focus!"
End Sub


Private Sub ACADApp_ARXUnloaded(ByVal AppName As String)
    ' This example intercepts an Application ARXUnloaded event.
    '
    ' This event is triggered when the AutoCAD unloads an ARX application
    '
    ' To trigger this example event:
    '     1) Make sure to run the example that initializes
    '     the public variable (named ACADApp) linked to this event.
    '
    '     2) Unload an ARX application that is already loaded into AutoCAD

    ' Use the "AppName" variable to notify the user which ARX application was unloaded
      MsgBox "AutoCAD just unloaded the ARX application: " & AppName

End Sub

Private Sub ACADApp_BeginFileDrop(ByVal FileName As String, Cancel As Boolean)
    ' This example intercepts an Application BeginFileDrop event.
    '
    ' This event is triggered when a drawing file is dragged into AutoCAD.
    '
    ' To trigger this example event:
    '     1) Make sure to run the example that initializes
    '     the public variable (named ACADApp) linked to this event.
    '
    '     2) Drag an AutoCAD drawing file into the AutoCAD application from either
    '     the Windows Desktop or Windows Explorer

    ' Use the "Cancel" variable to stop the loading of the dragged file, and the "FileName"
    ' variable to notifiy the user which file is about to be dragged in.
    If MsgBox("AutoCAD is about to load " & FileName & vbCrLf & "Do you want to continue loading this file?", vbYesNoCancel + vbQuestion) <> vbYes Then
        Cancel = True
    End If
End Sub

Private Sub ACADApp_BeginQuit(Cancel As Boolean)
    ' This example intercepts an Application BeginQuit event.
    '
    ' This event is triggered when AutoCAD receives a request to shut down.
    '
    ' To trigger this example event:
    '     1) Make sure to run the example that initializes
    '     the public variable (named ACADApp) linked to this event.
    '
    '     2) Close the AutoCAD application

    ' Use the "Cancel" variable to stop the shut down of the application
    If MsgBox("AutoCAD is about to shut down.  Do you want to continue with the shutdown?", vbYesNoCancel + vbQuestion) <> vbYes Then
        Cancel = True
    End If
End Sub

Private Sub ACADApp_BeginModal()
    ' This example intercepts an Application BeginModal event.  We use a Beep instead of
    ' a message box to notify the use when the event is triggered, since a message box
    ' is a modal entity and would cause continuous BeginModal/EndModal events to be triggered.
    '
    ' This event is triggered when AutoCAD displays a modal dialog.
    '
    ' To trigger this example event:
    '     1) Make sure to run the example that initializes
    '     the public variable (named ACADApp) linked to this event.
    '
    '     2) Use AutoCAD to begin a modal dialog operation.
    '     For example, use AutoCAD to display a modal file dialog by using File/New

    Beep  ' A modal dialog is about to be displayed!
End Sub

Private Sub ACADApp_BeginOpen(FileName As String)
    ' This example intercepts an Application BeginOpen event.
    '
    ' This event is triggered when a drawing is opened by AutoCAD.
    '
    ' To trigger this example event:
    '     1) Make sure to run the example that initializes
    '     the public variable (named ACADApp) linked to this event.
    '
    '     2) Use AutoCAD to open an existing drawing

    ' Use the "FileName" variable to determine which drawing file is being opened
    MsgBox "A drawing is about to be loaded from: " & FileName
End Sub

Private Sub ACADApp_EndModal()
    ' This example intercepts an Application EndModal event.  We use a Beep instead of
    ' a message box to notify the use when the event is triggered, since a message box
    ' is a modal entity and would cause continuous BeginModal/EndModal events to be triggered.
    '
    ' This event is triggered when AutoCAD finishes displaying a modal dialog.
    '
    ' To trigger this example event:
    '     1) Make sure to run the example that initializes
    '     the public variable (named ACADApp) linked to this event.
    '
    '     2) Use AutoCAD to begin a modal dialog operation and then dismiss the dialog.
    '     For example, use AutoCAD to display a modal file dialog by using File/New and then
    '     close the dialog by selecting Cancel

    Beep  ' The modal dialog was just closed!

End Sub

Private Sub ACADApp_EndOpen(ByVal FileName As String)
    ' This example intercepts an Application EndOpen event.
    '
    ' This event is triggered when AutoCAD finishes opening a drawing.
    '
    ' To trigger this example event:
    '     1) Make sure to run the example that initializes
    '     the public variable (named ACADApp) linked to this event.
    '
    '     2) Use AutoCAD to open an existing drawing and wait until the
    '     operation finishes

    ' Use the "FileName" variable to determine which drawing file is being opened
    MsgBox "A drawing was just loaded from: " & FileName
End Sub

Private Sub ACADApp_NewDrawing()
    ' This example intercepts an Application NewDrawing event.
    '
    ' This event is triggered when a new drawing request is sent to AutoCAD.
    '
    ' To trigger this example event:
    '     1) Make sure to run the example that initializes
    '     the public variable (named ACADApp) linked to this event.
    '
    '     2) Use AutoCAD to create a new drawing using File/New

    MsgBox "A request to start a new drawing was just intercepted!"
End Sub

Private Sub ACADApp_SysVarChanged(ByVal SysvarName As String, ByVal newVal As Variant)
    ' This example intercepts an Application SysVarChanged event.
    '
    ' This event is triggered when the value of a system variable is changed.
    '
    ' To trigger this example event:
    '     1) Make sure to run the example that initializes
    '     the public variable (named ACADApp) linked to this event.
    '
    '     2) Change the value of a system variable in AutoCAD.
    '     For example: Type GRIDMODE on the command line and toggle the grid display on/off

    ' Use the "SysvarName" and "newVal" variables to determine which
    ' system variable has changed and its new value.
    MsgBox "The system variable " & SysvarName & " was just changed to: " & newVal
End Sub









'----------------------------------------------------------------------------
' Modified (PLINE) Event Sample
'----------------------------------------------------------------------------

Sub Example_Modified()
     ' This example creates a light weight polyline in model space and
     ' references the new PolyLine using the public variable (PLine) which
     ' is setup to intercept Modified events.
     '
     ' This example then modifies the new object, triggering the code
     ' in the Modified event.
    
    Dim points(0 To 9) As Double
    
    ' Define the 2D polyline points
    points(0) = 1: points(1) = 1
    points(2) = 1: points(3) = 2
    points(4) = 2: points(5) = 2
    points(6) = 3: points(7) = 2
    points(8) = 4: points(9) = 4
        
    ' Create a light weight Polyline object in model space
    '
    ' * Note: We are returning the new PolyLine object into a Module
    ' level variable.  This allows us to intercept events associated
    ' with that particular object.
    Set PLine = ThisDrawing.ModelSpace.AddLightWeightPolyline(points)
    
    ThisDrawing.Application.ZoomAll
    
    ' Modify object to trigger event.
    '
    ' * Note: The event code for the PolyLine modification will be triggered
    ' before we move forward and refresh the view, so the line will not
    ' appear red when the event message box is displayed
    PLine.Color = acRed

    ThisDrawing.Regen acAllViewports
    
End Sub

Private Sub PLine_Modified(ByVal pObject As AutoCAD.IAcadObject)
    ' This example intercepts an object's Modified event.
    '
    ' This event is triggered when an object supporting this event is modified
    '
    ' To trigger this code: Modifiy an object connected to this event
    ' * Note: By connected, we mean the object setup to intercept events using
    ' the VBA WithEvents statement

    ' Use the "pObject" variable to determine which object was modified
    MsgBox "You just modified an object with an ID of: " & pObject.ObjectID
    
End Sub
