Attribute VB_Name = "basCommand"
Option Explicit

' Structure used by SendMessage to transfer data
' to another window
Type COPYDATASTRUCT
    dwData As Long
    cbData As Long
    lpData As Long
End Type

' SendMessage sends a message to another window
Private Declare Function SendMessage Lib "user32" Alias _
 "SendMessageA" (ByVal hwnd As Long, _
 ByVal wMsg As Long, ByVal wParam As Long, _
 ByRef lParam As COPYDATASTRUCT) As Long

' The particular message we want to send
Private Const WM_COPYDATA = &H4A

' GetActiveWindow and GetParent are used to find
' the AutoCAD window
Private Declare Function GetActiveWindow Lib "user32" () As Long
Private Declare Function GetParent Lib "user32" _
 (ByVal hwnd As Long) As Long


Function FindAcadFrameWnd() As Long
    ' Find the overall AutoCAD window. Since we're running
    ' within AutoCAD, we can do this by finding the hwnd of
    ' the current Window, continue finding the parent until
    ' we hit the desktop, and then come back one window.
    '
    ' Returns the window handle of the main AutoCAD window
    '
    ' WARNING: This function WILL NOT WORK if called from the
    ' Immediate Window or while the VBE is the active window.
    ' You must either run it from a macro from within AutoCAD,
    ' or from a UserForm launched from AutoCAD.
    
    Dim hwndPrev As Long
    Dim hwnd As Long
    hwnd = GetActiveWindow()
    ' The desktop always has the special hwnd of zero
    Do Until hwnd = 0
        hwndPrev = hwnd
        hwnd = GetParent(hwnd)
    Loop
    FindAcadFrameWnd = hwndPrev
End Function

Function SendCmdToAcad(ByVal strCommand As String) As Long
    ' Send the supplied string to the AutoCAD command line.
    '
    Dim cmdMsg As COPYDATASTRUCT
    Dim lngRet As Long
    Dim lngAcadHwnd As Long
    Dim intI As Integer
    Dim abytCommand(0 To 255) As Byte
    
    ' Locate AutoCAD so we can send messages to it
    lngAcadHwnd = FindAcadFrameWnd()
    
    ' The dwData field holds a magic number that tells
    ' AutoCAD that this message is an incoming command
    cmdMsg.dwData = 1#
    
    ' VB strings passed to API calls are always Unicode.
    ' AutoCAD strings are always ANSI. We need to fake out
    ' the API call by converting the VB string to an
    ' equivalent array of bytes. Then we'll zero-terminate
    ' the array, pass its base address, and it will look
    ' just like a string to AutoCAD
    For intI = 1 To Len(strCommand)
        abytCommand(intI - 1) = Asc(Mid(strCommand, intI, 1))
    Next intI
    abytCommand(Len(strCommand)) = 0
    
    ' The cbData field in the message holds the length of the
    ' valid data. We have to be sure we include the null byte
    ' in this length.
    cmdMsg.cbData = Len(strCommand) + 1
    
    ' The lpData field in the message holds a pointer to the
    ' actual buffer. We can use the undocumented VarPtr()
    ' function to retrieve the address of the base element
    ' of the byte array
    cmdMsg.lpData = VarPtr(abytCommand(0))
    
    ' And finally, call SendMessage to toss the message
    ' over to AutoCAD where it can be acted on.
    lngRet = SendMessage(lngAcadHwnd, WM_COPYDATA, _
     vbNull, cmdMsg)
     
End Function

Private Sub Wait()

    Dim sysVarName As String
    Dim varData As Variant
    ' The following example returns AutoCAD version number from current drawing.
    ' Note that the return value returned by getVariable method is Variant,
    ' so you need to extract information depending upon
    ' Vartype of varData.
    sysVarName = "CMDACTIVE"
    ' 0 = No command active
    varData = ThisDrawing.GetVariable(sysVarName)
    While varData <> 0
'        MsgBox sysVarName & " = " & varData, Title:="GetVariable"
        varData = ThisDrawing.GetVariable(sysVarName)
    Wend

End Sub
' Helper procedure that allows us to open the form
' from an AutoCAD macro
Public Sub SendCommand()
    frmCommand.Show
End Sub

Attribute VB_Name = "frmCommand"
Attribute VB_Base = "0{0BBC0135-745B-11D2-99C9-00609761BD90}{0BBC0121-745B-11D2-99C9-00609761BD90}"
Attribute VB_Creatable = False
Attribute VB_PredeclaredId = True
Attribute VB_Exposed = False
Attribute VB_TemplateDerived = False
Attribute VB_Customizable = False
Option Explicit

Private Sub cmdOK_Click()
    Me.hide
    SendCmdToAcad txtCommand & vbCr
    Unload Me
    'Wait
    'Me.Show
'    MsgBox "VBA app ending"
End Sub

Private Sub UserForm_Initialize()
' Jam the sample code into the text box so you only have to select the Run button
' to test it.
    Dim fname As String
    fname = "xdata"
    txtCommand.Text = "(command " & Chr(34) & ".-xref" & Chr(34) & " " & Chr(34) & _
                      "a" & Chr(34) & " " & Chr(34) & fname & Chr(34) & " " & _
                      Chr(34) & "0,0,0" & Chr(34) & " " & Chr(34) & "1" & Chr(34) & _
                      " " & Chr(34) & "1" & Chr(34) & " " & Chr(34) & "0" & Chr(34) & _
                      ")" & "(command " & Chr(34) & ".-vbarun" & Chr(34) & " " & _
                      Chr(34) & "sendcommand" & Chr(34) & ")"

End Sub
