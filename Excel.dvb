Attribute VB_Name = "Module1"
Option Explicit
    'Dim ExL As Object
    'Dim XlWorkBook As Object
    'Dim excelSheet As Object

    Dim ExL As Excel.Application
    Dim XlWorkBook As Excel.Workbook
    Dim excelSheet As Excel.Worksheet


Sub Set_Up_Excel()

  On Error Resume Next
  Set ExL = GetObject("", "Excel.Application")
  ExL.Visible = True
  If (Err.Number <> 0) Then
    Err.Clear
    MsgBox "You must have Excel loaded on your computer!"
    Exit Sub
  End If
  Set XlWorkBook = Workbooks.Open("d:\vba book\bill's chapters\my documents\vba1\EXAMPLE1.XLS")
  Sheets("Sheet1").Select
  Set excelSheet = ExL.ActiveWorkbook.Sheets("Sheet1")
  Call FindCell
  
  XlWorkBook.Close

End Sub

Sub Close_book()
  XlWorkBook.Close
End Sub

Sub FindCell()
    On Error Resume Next
    Dim Fnd As Excel.Range
    Set Fnd = excelSheet.Range("A1:A10").Find("AA-3")
    Dim R$
    Dim Rw
    Dim Resulting_Value
    Dim I As Long
    'R$ = Fnd.Address
    R$ = ""
    For I = 1 To 10
       If excelSheet.Cells(I, 1).Value = "AA-3" Then
        R$ = excelSheet.Cells(I, 2).Value
        I = 11 'break out of the loop
       End If
    Next I
    
    Rw = Val(Mid$(R$, 4))
    Resulting_Value = excelSheet.Cells(Rw, 2).Value
    

End Sub
