Attribute VB_Name = "Module1"
Option Explicit
Public Sub Pass_Undeclared_Array()
    ' an example of passing an undeclared array to a procedure
    ' in this example the array is declared in general as a type here
    ' but no items are declared, they must be declared in the called procedure
    Stop
    Dim Pnt() As Double
    FillArray2 (Pnt)                            ' load the array
    Debug.Print "*** Pnt inside Pass_Undeclared_Array after calling FillArray2 ***"
    Dim i As Long
    On Error GoTo ErrHandler                    ' Pnt never get initiated so an error ocurres
    For i = 0 To UBound(Pnt)
        Debug.Print "Pnt(" & i; ") = " & Pnt(i)
    Next i
ExitSub:
    Exit Sub
ErrHandler:
    If Err.Number = 9 Then
        Err.Clear
        Debug.Print "Error: Tried to use Ubound on the uninitiated array Pnt."
    End If
    GoTo ExitSub
End Sub
Public Function FillArray2(Pnt As Variant) As Variant
    ReDim Pnt(0 To 2) As Double
    Pnt(0) = 1                                  ' load the passed in empty array
    Pnt(1) = 2
    Pnt(2) = 3
    Debug.Print "*** Pnt inside FillArray2 ***"
    Dim i As Long
    For i = 0 To UBound(Pnt)
        Debug.Print "Pnt(" & i; ") = " & Pnt(i)
    Next i
End Function
Public Sub Undeclared_Array()
    ' an example of loading an array from another procedure
    ' The variant variable AltPnt has the array set to it from the other
    ' function and can be treated just as an array in this procedure
    Stop
    Dim AltPnt As Variant      ' declare the array recieved from the called procedure
    AltPnt = FillArray1()      ' load an array from another procedure
    Dim i As Long
    For i = 0 To UBound(AltPnt)
        Debug.Print "AltPnt(" & i; ") = " & AltPnt(i)
    Next i
End Sub
Public Function FillArray1() As Variant
    Dim i As Long
    Dim PntArray(0 To 2) As Double
    PntArray(0) = 1
    PntArray(1) = 2
    PntArray(2) = 3
    FillArray1 = PntArray
End Function
Public Sub Pass_Declared_Arrays()
    ' an example of passing a declared array with a known length to another
    ' procedure for loading
    Stop
    Dim Pnt(0 To 2) As Double               ' declare the arrays
    Dim LoadedPnt(0 To 2) As Double
    LoadedPnt(0) = 4                        ' load one of the arrays
    LoadedPnt(1) = 5
    LoadedPnt(2) = 6
    Dim AltPnt As Variant                   ' declare a variant to recieve an array
    Dim VarPnt As Variant                   ' declare a variant to point to an array
    VarPnt = Pnt                            ' why bother, it doesn't work this way
    AltPnt = FillArray(LoadedPnt, VarPnt)   ' pass a loaded and the variant
                                            ' returns an array
    Debug.Print "*** First Pass ***"
    Debug.Print "*** Passed in LoadPnt and VarPnt ***"
    Debug.Print "*** Pnt, LoadedPnt, and VarPnt are declared in the calling procedure ***"
    Debug.Print "*** Pnt and LoadedPnt as arrays of doubles and VarPnt as a variant set to Pnt ***"
    Debug.Print "*** Notice that Pnt does not get loaded but the VarPnt does ***"
    Dim i As Long
    For i = 0 To UBound(Pnt)
        Debug.Print "Pnt(" & i; ") = " & Pnt(i)
    Next i
    For i = 0 To UBound(AltPnt)
        Debug.Print "AltPnt(" & i; ") = " & AltPnt(i)
    Next i
    For i = 0 To UBound(VarPnt)
        Debug.Print "VarPnt(" & i; ") = " & VarPnt(i)
    Next i
    AltPnt = FillArray(LoadedPnt, Pnt) ' pass a loaded and an empty array
    Debug.Print "*** Second Pass ***"
    Debug.Print "*** Passed in LoadPnt and Pnt ***"
    Debug.Print "*** Notice that Pnt does get loaded by passing the array itself ***"
    For i = 0 To UBound(Pnt)
        Debug.Print "Pnt(" & i; ") = " & Pnt(i)
    Next i
    For i = 0 To UBound(AltPnt)
        Debug.Print "AltPnt(" & i; ") = " & AltPnt(i)
    Next i
    Debug.Print " "
    Debug.Print " In both situations the AltPnt array is returned loaded. "
    
End Sub
Public Function FillArray(LoadedPntArray As Variant, EmptyPntArray As Variant) As Variant
    Dim i As Long
    EmptyPntArray(0) = 1        ' load the passed in empty array
    EmptyPntArray(1) = 2
    EmptyPntArray(2) = 3
    FillArray = EmptyPntArray
End Function
