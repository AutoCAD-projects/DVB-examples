Attribute VB_Name = "Module1"
'
'  ad_LayerRename
'
'  This routine demonstrates the manipulation of drawing layer names.
'  It was developed in AutoCAD 2000.
'
'  version 1.00
'  3/16/2002
'
'  Copyright©2002-2003 ActiveDwg.com
'
'  This routine is provided for demonstration purposes only and must
'    not be used for critical applications without your verification
'    that this routine will perform as you intended.
'  This routine may be freely utilized for your own personal use so long
'    as the entire contents of this header remain intact.
'  This routine is provided "as-is" and no declaration, written or implied,
'    is made as to its reliability for any particular task. Any use of this
'    routine is solely at your own risk.
'
Option Explicit

Sub ad_FormatLayerNames()
'This routine reformats all layer names so that the first
'  character is uppercase and the rest are lowercase.
' Demand load:  -vbarun;ad_LayerRename.dvb!ad_FormatLayerNames;
  Dim DwgLayer As AcadLayer
  Dim HoldChar As String
  Dim HoldStr As String
  Dim StrLen As Integer
  
  For Each DwgLayer In ThisDrawing.Layers
    DwgLayer.Name = LCase(DwgLayer.Name)
    HoldStr = DwgLayer.Name
    HoldChar = UCase(Left(DwgLayer.Name, 1))
    StrLen = Len(DwgLayer.Name) - 1
    HoldStr = HoldChar & Right(DwgLayer.Name, StrLen)
    DwgLayer.Name = HoldStr
  Next DwgLayer
End Sub

Sub ad_LayersLowerCase()
'This routine reformats all layer names to all lowercase.
' Demand load:  -vbarun;ad_LayerRename.dvb!ad_LayersLowerCase;
  Dim DwgLayer As AcadLayer
  
  For Each DwgLayer In ThisDrawing.Layers
    DwgLayer.Name = LCase(DwgLayer.Name)
  Next DwgLayer
End Sub

Sub ad_LayersUpperCase()
'This routine reformats all layer names to all uppercase.
' Demand load:  -vbarun;ad_LayerRename.dvb!ad_LayersUpperCase;
  Dim DwgLayer As AcadLayer
  
  For Each DwgLayer In ThisDrawing.Layers
    DwgLayer.Name = UCase(DwgLayer.Name)
  Next DwgLayer
End Sub
