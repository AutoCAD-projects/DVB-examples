Attribute VB_Name = "basGlobal"
Option Explicit
Public Sub Return_Collection()
    Stop
    Dim result As Collection
    Set result = FillCollection3
End Sub
Public Function FillCollection3() As Variant
    Dim colTemp As New Collection
    colTemp.Add 1
    colTemp.Add 2
    colTemp.Add 3
    FillCollection3 = colTemp
End Function
Public Sub Pass_Declared_Collection()
    ' an example of passing a declared collection to another procedure to be loaded
    ' in this example the collection is declared and set to new in the calling
    ' procedure
    Stop
    Dim colOne As New Collection
    Call FillCollection(colOne)
    Dim i As Long
    For i = 1 To colOne.Count
        Debug.Print "colOne(" & i; ") = " & colOne.Item(i)
    Next i
    
End Sub
Public Sub FillCollection(colOne1 As Collection)
    colOne1.Add 1
    colOne1.Add 2
    colOne1.Add 3
End Sub
Public Sub Pass_Undeclared_Collection()
    ' an example of passing a declared collection to another procedure to be loaded
    ' in this example the collection is declared in the calling procedure but must
    ' be set to a new instance in the called procedure
    Stop
    Dim colOne As Collection
    Call FillCollection1(colOne)
    Dim i As Long
    For i = 1 To colOne.Count
        Debug.Print "colOne(" & i; ") = " & colOne.Item(i)
    Next i
End Sub
Public Function FillCollection1(colTemp As Collection)
    Set colTemp = New Collection
    colTemp.Add 1
    colTemp.Add 2
    colTemp.Add 3
End Function
Public Sub Pass_Collection()
    ' an example of how to keep adding on to a collection from anther porcedure
    Stop
    Dim colOne As New Collection
    Dim i As Long
    For i = 1 To 4
        Call fillcollection2(colOne, i)     ' add the item to the collection
    Next i
    For i = 1 To colOne.Count               ' show the collection in the debug window
        Debug.Print "colOne(" & i; ") = " & colOne.Item(i)
    Next i
End Sub
Public Sub fillcollection2(colTemp As Collection, counter As Long)
    colTemp.Add counter         ' just one line to show how but you
                                ' could add more code in this routine
End Sub
