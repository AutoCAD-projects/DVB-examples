Attribute VB_Name = "Module1"
Public Sub DWGLog()
logform.Show
End Sub

Attribute VB_Name = "ThisDrawing"
Attribute VB_Base = "0{FCE25E01-1282-11D0-89E7-00805FC2FBBA}"
Attribute VB_Creatable = False
Attribute VB_PredeclaredId = True
Attribute VB_Exposed = True
Attribute VB_TemplateDerived = False
Attribute VB_Customizable = True
Private Sub AcadDocument_BeginSave(ByVal FileName As String)

End Sub

Private Sub AcadDocument_EndOpen(ByVal FileName As String)
End Sub

Attribute VB_Name = "logform"
Attribute VB_Base = "0{5157945C-75AB-11D3-824F-006008A3609B}{51579444-75AB-11D3-824F-006008A3609B}"
Attribute VB_Creatable = False
Attribute VB_PredeclaredId = True
Attribute VB_Exposed = False
Attribute VB_TemplateDerived = False
Attribute VB_Customizable = False
Private Sub TextBox1_Change()

End Sub

Private Sub dwgname_Change()

End Sub

Private Sub updatebutton_Click()
Dim excel As Object
Dim excelsheet As Object
Dim exapp As Object
On Error Resume Next
Me.Hide
Set excel = GetObject(, "Excel.application")
If Err <> 0 Then
    Err.Clear
    Set excel = CreateObject("Excel.application")
    If Err <> 0 Then
        MsgBox "Could not load Excel.", vbOKOnly + vbInformation, "Error report"
    End
End If
End If
On Error GoTo 0
excel.Visible = True 'remove this line to run the macro without ever seeing Excel
Set exapp = excel.workbooks.Add
'*****************NOTE*******************************************************************************
'The above line needs to be changed to Set exapp = excel.workbooks.OPEN ("your log path & filename")
'to send each drawing name and date to one spreadsheet. For the sake of simplicity this example
'opens a new spreadsheet each time it is run.
'****************************************************************************************************
dwgname = ThisDrawing.Path
todaysdate = Date
rownum = 2
columnnum = 1
With excel
Set excelsheet = excel.ActiveWorkbook.Sheets("sheet1")
Do Until excelsheet.Cells(rownum, 1).Value = "" Or excelsheet.Cells(rownum, 1).Value = dwgname
    rownum = rownum + 1
Loop
excelsheet.Cells(rownum, 1).Value = dwgname
If excelsheet.Cells(rownum, 1).Value = dwgname Then
    columnnum = columnnum + 1
End If
Do Until excelsheet.Cells(rownum, columnnum).Value = "" Or excelsheet.Cells(rownum, columnnum).Value = todaysdate
    columnnum = columnnum + 1
Loop
excelsheet.Cells(rownum, columnnum).Value = todaysdate
'excel.ActiveWorkbook.Save
'excel.ActiveWorkbook.Close
'excel.Quit
'*********************************NOTE***********************
'Take the quote off the above lines to automatically save the spreadsheet, close it and quit Excel.
'************************************************************
End With
End Sub

Private Sub UserForm_Click()

End Sub

Private Sub UserForm_Initialize()
logform.dwgname.Text = ThisDrawing.Path
logform.today.Text = Date
End Sub
