Attribute VB_Name = "Access_VBA_mod"
Public wksObj As Object     'Workspace
Public dbsObj As Object     'Access
Public tblObj As Object     'Table
Public fldObj As Object     'Fields
Public rstObj As Object     'Memory version of database

Public Sub OpenAccess()
On Error Resume Next
Dim strSQL As String
Dim i, j, btot As Integer
Dim bnam As String
Dim ent As Object

    Set wksObj = DBEngine.Workspaces(0)
    Set dbsObj = wksObj.Opendatabase("AutoCAD.mdb")
        
        For i = 0 To btot - 1
            bnam = ThisDrawing.Blocks.Item(i).Name
            If Not Mid$(bnam, 1, 1) = "*" Then ListBox1.AddItem bnam
        Next i
        
        For i = 0 To ListBox1.ListCount - 1
            bnam = ListBox1.list(i): btot = 0
            For j = 0 To ThisDrawing.ModelSpace.count - 1
                Set ent = ThisDrawing.ModelSpace.Item(j)
                If ent.EntityType = acBlockReference And ent.Name = bnam Then btot = btot + 1
            Next j
            ListBox2.AddItem btot
        Next i
        
End Sub

Attribute VB_Name = "Close_All_mod"
Public Sub ad_CloseAllDwgs()
'  This routine is provided for demonstration purposes only and must
'    not be used for critical applications without your verification
'    that this routine will perform as you intended.
'  This routine may be freely utilized for your own personal use so long
'    as the entire contents of this header remain intact.
'  This routine is provided "as-is" and no declaration, written or implied,
'    is made as to its reliability for any particular task. Any use of this
'    routine is solely at your own risk.

    Dim Drawing As AcadDocument
    Dim StrMsg As String
    Dim StrTitle As String
    Dim Response

'    On Error Resume Next
    If Documents.count = 0 Then
        MsgBox "No drawings to close!"
        Exit Sub
    End If
    StrMsg = "Save all drawings before closing?"
    StrTitle = "Verify Close Mode"
    Response = MsgBox(StrMsg, vbYesNo, StrTitle)
    If Response = vbYes Then
        For Each Drawing In Documents
            Drawing.Save
            Drawing.Close
        Next
    Else
        For Each Drawing In Documents
            Drawing.Close (False)
        Next
    End If
End Sub

Attribute VB_Name = "Dwg_Properties_frm"
Attribute VB_Base = "0{564D419D-98C1-11D5-8640-00C04F948912}{564D40EA-98C1-11D5-8640-00C04F948912}"
Attribute VB_GlobalNameSpace = False
Attribute VB_Creatable = False
Attribute VB_PredeclaredId = True
Attribute VB_Exposed = False
Attribute VB_TemplateDerived = False
Attribute VB_Customizable = False
'Author: Mark Johnston
'Authors Comments:
'This app is a dialog that will give you feedback about the current drawing
'and about the objects in the drawing.
'It 's a quick way to list a drawings layers, linetypes, textstyles,
'dimensions, dimstyles, block definitions, block references and osnap state.
'i 've added each of these features as I found a need for them in various
'projects.

'It can also give some useful information about specific entities in the
'drawing. Just select the "Pick Ent" button and pick an entity. You will
'notice that the information displayed is very simple. This could be
'expanded on as the user finds reasons to see more details.
'It even includes a little sub called "SnapToggle" that will turn your
'Osnaps On or Off exactly like pressing the statusbar button. Just pass it
'True for ON and False for OFF.

Private Sub cmdBlockRefs_Click()
    Dim ABlockRef As AcadBlockReference
    Dim AcadObj As AcadObject
   ' ListBox1.Clear
    'For Each AcadObj In ThisDrawing.ModelSpace
    '    If AcadObj.ObjectName = "AcDbBlockReference" Then
    ''        Select Case AcadObj.Name
    '            Case "AVE_RENDER", "AVE_GLOBAL"
    '            Case Else
    '                ListBox1.AddItem AcadObj.Name
    '        End Select
   '     End If
  '  Next
    'SetLabel cmdBlockRefs
End Sub

Private Sub cmdCancel_Click()
On Error Resume Next

        Unload Me
        Me.Hide
        End

End Sub

Private Sub cmdPickEnt_Click()
    txInfo.Text = ""
    Dim acEnt As AcadEntity
    Dim PPoint As Variant
    Me.Hide
RePick:
    On Error Resume Next
    ThisDrawing.Utility.GetEntity acEnt, PPoint, "Select Something"
    If acEnt Is Nothing Then GoTo RePick
    Dim strInfo As String
    strInfo = strInfo & "Color = " & acEnt.Color & vbCrLf
    strInfo = strInfo & "Object Name = " & acEnt.ObjectName & vbCrLf
    strInfo = strInfo & "Object Layer = " & acEnt.Layer & vbCrLf
    strInfo = strInfo & "Object ID = " & acEnt.ObjectID & vbCrLf
    strInfo = strInfo & "Object Handle = " & acEnt.handle & vbCrLf
    Select Case acEnt.ObjectName
        Case "AcDbRadialDimension"
            strInfo = strInfo & "Arrowhead Block = " & acEnt.ArrowheadBlock & vbCrLf
            strInfo = strInfo & "Arrowhead Type = " & acEnt.ArrowheadType & vbCrLf
        Case "AcDbDiametricDimension", "AcDbRotatedDimension", "AcDbAlignedDimension", "AcDb3PointAngularDimension", "AcDb2LineAngularDimension"
            strInfo = strInfo & "Arrowhead Block = " & vbCrLf '& acEnt.ArrowheadBlock & vbCrLf
            strInfo = strInfo & "Arrowhead 1 Block = " & acEnt.Arrowhead1Block & vbCrLf
            strInfo = strInfo & "Arrowhead 2 Block = " & acEnt.Arrowhead2Block & vbCrLf
            strInfo = strInfo & "Arrowhead 1 Type = " & acEnt.Arrowhead1Type & vbCrLf
            strInfo = strInfo & "Arrowhead 2 Type = " & acEnt.Arrowhead2Type & vbCrLf
        Case "AcDbBlockReference"
            strInfo = strInfo & "Block name = " & acEnt.Name & vbCrLf
            Dim IPnt As Variant
            Dim XDiff As Integer
            Dim YDiff As Integer
            IPnt = acEnt.InsertionPoint
                ' Insertion point X
            strInfo = strInfo & "X = " & IPnt(0) & vbCrLf
                ' Insertion point Y
            strInfo = strInfo & "Y = " & IPnt(1) & vbCrLf
            On Error Resume Next
            Dim dblX As Double
            Dim dblY As Double
            dblX = CDbl(GetXD(acEnt, "CES", "InsX"))
            dblY = CDbl(GetXD(acEnt, "CES", "InsY"))
            XDiff = CInt(dblX - IPnt(0))
            YDiff = CInt(dblY - IPnt(1))
            If XDiff = 0 Then
                strInfo = strInfo & "XData X Matches" & vbCrLf
            Else
                strInfo = strInfo & "XData X is off by " & CStr(XDiff) & vbCrLf
            End If
            If YDiff = 0 Then
                strInfo = strInfo & "XData Y Matches" & vbCrLf
            Else
                strInfo = strInfo & "XData Y is off by " & CStr(YDiff) & vbCrLf
            End If
                ' Tag locations
            Dim XTagOff As Double
            Dim YTagOff As Double
            Dim XTag As Double
            Dim YTag As Double
            Dim XTagDiff As Integer
            Dim YTagDiff As Integer
            XTag = CDbl(GetXD(acEnt, "CES", "TagX"))
            YTag = CDbl(GetXD(acEnt, "CES", "TagY"))
            XTagOff = CDbl(GetXD(acEnt, "CES", "Width")) / 2
            If Left(GetXD(acEnt, "CES", "Model"), 1) = "W" Then
                    ' This is a wall cabinet
                YTagOff = CDbl(53.61122)
            Else
                    ' This is a base or tall cabinet
                YTagOff = CDbl(-4)
            End If
            XTagDiff = CInt((XTag - dblX) - XTagOff)
            YTagDiff = CInt(YTag - dblY - YTagOff)
            If XTagDiff = 0 Then
                strInfo = strInfo & "XData TagX Matches" & vbCrLf
            Else
                strInfo = strInfo & "XData TagX is off by " & CStr(XTagDiff) & vbCrLf
            End If
            If YTagDiff = 0 Then
                strInfo = strInfo & "XData TagY Matches" & vbCrLf
            Else
                strInfo = strInfo & "XData TagY is off by " & CStr(YTagDiff) & vbCrLf
            End If
    
    End Select
    txInfo.Text = strInfo
    Me.Show
    
End Sub

Private Sub PopulateDB(strBlkName As String, objDB As Database)
  Dim NewSS As AcadSelectionSet
  Dim objBlk As AcadBlockReference
  Dim rsAtts As Recordset
  Dim fldAtt As Field
  Dim varAtts As Variant
  Dim varPnt1 As Variant
  Dim varPnt2 As Variant
  Dim VarData(0 To 1) As Variant
  Dim intData(0 To 1) As Integer
  Dim intCnt As Integer
  Set NewSS = vbdPowerSet("data")
  VarData(0) = "INSERT"
  VarData(1) = strBlkName
  intData(0) = 0
  intData(1) = 2
  NewSS.Select Mode:=acSelectionSetAll, FilterType:=intData, FilterData:=VarData
  Set rsAtts = objDB.OpenRecordset(strBlkName)
  For Each objBlk In NewSS
    varAtts = objBlk.GetAttributes
    rsAtts.AddNew
    For intCnt = LBound(varAtts) To UBound(varAtts)
      rsAtts.Fields(intCnt) = varAtts(intCnt).TextString
    Next
    rsAtts.Update
  Next
  rsAtts.Close
End Sub

Private Sub CommandButton2_Click()
On Error Resume Next

        Me.lst_BLK.Clear

    End Sub

Private Sub lst_BLK_Change()
On Error Resume Next

        Call ListAttributes

End Sub

Private Sub lst_DWG_Change()
On Error Resume Next
        
        Me.lst_BLK.Clear
        Me.lst_ATR.Clear
        Call ListBlocks
        
End Sub

Private Sub UserForm_Activate()
On Error Resume Next

        Call ListDrawings
        Call SetBlkLabel
        Call SetAtrLabel
        
End Sub

Public Function SetBlkLabel()
On Error Resume Next

        Me.lbl_BLK.Caption = CStr(Me.lst_BLK.ListCount) + " " + "Blocks"
    
End Function

Public Function SetDwgLabel()
On Error Resume Next

        Me.lbl_DWG.Caption = CStr(Me.lst_DWG.ListCount) + " " + "Drawings"
    
End Function

Public Function SetAtrLabel()
On Error Resume Next

        Me.lbl_ATR.Caption = CStr(Me.lst_ATR.ListCount) + " " + "Attributes"
    
End Function

Public Sub ListDrawings()
On Error Resume Next
Dim adDwg As AcadDocument
Dim adListFile As Integer
Dim adList As String
    adList = ""

        For Each adDwg In Documents
            adList = adList & adDwg.Name & vbCrLf
            Me.lst_DWG.AddItem adDwg.Name
        Next
        
        Call SetDwgLabel

End Sub

Public Sub ListBlocks()
On Error Resume Next
Dim ABlock As AcadBlock
Dim DrawingName As Object
Dim adDwg As AcadDocument
Dim adListFile As Integer
Dim adList As String
    adList = ""

    DrawingName = Me.lst_DWG.Value
    DrawingName.Activate

        'Set adDwg = Me.lst_DWG
        
        For Each ABlock In ThisDrawing.Blocks
            If Left(ABlock.Name, 1) <> "*" Then
                Me.lst_BLK.AddItem ABlock.Name
            End If
        Next
        
        Call SetBlkLabel
        
End Sub

Public Sub ListAttributes()
On Error Resume Next
Dim BlockObj As Object
Dim BlockObjAttributes
Dim i As Integer
Dim DrawingName As String
Dim BlockName As String
Dim BlockMatch As String
Dim count As Integer
Dim ent As Object
Dim sset As Object
Dim handle

        DrawingName = Me.lst_DWG.Value
        Set BlockObj = ThisDrawing.HandleToObject(sset.Item(0).handle)
        BlockName = Me.lst_BLK.Value
        BlockObjAttributes = BlockObj.GetAttributes
        
        For i = LBound(BlockObjAttributes) To UBound(BlockObjAttributes)
            AttributeList.AddItem BlockObjAttributes(i).TextString
            Me.lst_DWG.AddItem NewAttribute.Text
        Next i
        
'-------------------------------------------------------------------
 ' Set BlockObj = ThisDrawing.HandleToObject(sset.Item(0).handle)
 ' BlockName = BlockObj.Name
 ' BlockObjAttributes = BlockObj.GetAttributes
 ' For i = LBound(BlockObjAttributes) To UBound(BlockObjAttributes)
 '    AttributeList.AddItem BlockObjAttributes(i).TextString
 ' Next i
'-------------------------------------------------------------------

        Call SetAtrLabel
        
End Sub

Attribute VB_Name = "Excel_VBA_mod"
'Excel

Public excelApp As Object       'Excel
Public wkbObj As Object         'Workbook
Public shtObj As Object         'Sheet/Page

Public Sub OpenExcel()
On Error Resume Next
'Establish a link to Excel
'The GetObject function assumes that Excel is already running
Set excelApp = GetObject(, "Excel.Application")
If Err <> 0 Then
    Err.Clear
    'The CreateObject function is used because an error (non-zero condition) is generated
    Set excelApp = CreateObject("Excel.Application")
    If Err <> 0 Then 'could not launch Excel
        MsgBox "Could not start Excel!", vbExclamation, "Excel Error"
        End
    End If
End If
excelApp.Visible = True
'To work with an existing spreadsheet file, you can use the code below to set the
'current workbook
'Set wkbobj = Workbooks.Open(filename:="c:\dir\filename.xls")
Set wbkObj = excelApp.workbooks.Add
Set shtObj = excelApp.worksheets(1)
    
End Sub

Public Sub CloseExcel()
On Error Resume Next
'a dialog may ask if you want to save changes to the current workbook
        excelApp.Quit


End Sub

Public Sub GetBlocks()
'cycles through all blocks found in the drawing block collection and adds their names,
'except for those beginning with an asterisk in the listbox.  It then cycles through
'all listbox names, totaling all entities in Modelspace which are both blocks and named
'current listbox value to other listbox.  "Create Excel" button sends the listbox data
'to a new spreadsheet. "Quit" button exits the form.
On Error Resume Next
Dim i, j, btot As Integer
Dim bnam As String
Dim ent As Object
btot = ThisDrawing.Blocks.count
For i = 0 To btot - 1
    bnam = ThisDrawing.Blocks.Item(i).Name
    If Not Mid$(bnam, 1, 1) = "*" Then ListBox1.AddItem bnam
Next i
For i = 0 To ListBox1.ListCount - 1
    bnam = ListBox1.list(i): btot = 0
    For j = 0 To ThisDrawing.ModelSpace.count - 1
        Set ent = ThisDrawing.ModelSpace.Item(j)
        If ent.EntityType = acBlockReference And ent.Name = bnam Then btot = btot + 1
    Next j
    ListBox2.AddItem btot
Next i
End Sub

Public Sub CreateExcel()
On Error Resume Next
Set excelApp = GetObject(, "excel.application")
If Err <> 0 Then
    Err.Clear
    Set excelApp = CreateObject("excel.application")
    If Err <> 0 Then
        MsgBox "Could not start Excel!", vbExclamation, "Excel Error"
        End
    End If
End If
excelApp.Visible = True
Set wkbObj = excelApp.workbooks.Add
Set shtObj = wkbObj.worksheets(1)
shtObj.Name = "Block Count"
Dim bnam As String
j = 1
For i = 0 To ListBox1.ListCount - 1
    bnam = ListBox1.list(i)
    btot = ListBox2.list(i)
    shtObj.Cells(j, 1).Value = bnam
    shtObj.Cells(j, 2).Value = btot
    j = j + 1
Next i

End Sub

Attribute VB_Name = "Get_Blocks_frm"
Attribute VB_Base = "0{564D417E-98C1-11D5-8640-00C04F948912}{564D40E2-98C1-11D5-8640-00C04F948912}"
Attribute VB_GlobalNameSpace = False
Attribute VB_Creatable = False
Attribute VB_PredeclaredId = True
Attribute VB_Exposed = False
Attribute VB_TemplateDerived = False
Attribute VB_Customizable = False
Public wksObj As Object     'Workspace
Public dbsObj As Object     'Access
Public tblObj As Object     'Table
Public fldObj As Object     'Fields
Public rstObj As Object     'Memory version of database

Private Sub cmd_CRE_TBL_Click()
'On Error Resume Next
    'Set wksObj = DBEngine.Workspaces(0)
    'Set dbsObj = wksObj.Opendatabase("AutoCAD.mdb")
        Call CreateDB("AutoCAD")

End Sub

Private Sub cmd_Get_BLK_NME_Click()
On Error Resume Next

        'Call OpenAccess

End Sub

Private Sub cmd_QUIT_Click()
On Error Resume Next

        'AutoCAD.AcadApplication.Quit
        Me.Hide
        End
        
End Sub

Public Sub ListBlocks()
Dim i, j, btot As Integer
Dim bnam As String
Dim ent As Object
On Error Resume Next
        
        For i = 0 To btot - 1
            bnam = ThisDrawing.Blocks.Item(i).Name
            If Not Mid$(bnam, 1, 1) = "*" Then ListBox1.AddItem bnam
        Next i
        
        For i = 0 To ListBox1.ListCount - 1
            bnam = ListBox1.list(i): btot = 0
            For j = 0 To ThisDrawing.ModelSpace.count - 1
                Set ent = ThisDrawing.ModelSpace.Item(j)
                If ent.EntityType = acBlockReference And ent.Name = bnam Then btot = btot + 1
            Next j
            ListBox2.AddItem btot
        Next i
        
End Sub

Public Function CreateDB(strName As String) As Database
  Dim objDBBlks As Database             'Access Database
  Dim objTbl As TableDef                'Table Definitions
  Dim objFld As Field                   'Fields
  Dim objBlk As AcadBlockReference      'Blocks in AutoCAD
  Dim varAtts As Variant                'Block Attributes
  Dim varPnt As Variant                 '
  Dim intCnt As Integer                 'Count Attributes
  Dim strPrmpt As String                'Message string
  Dim strDwgNme As String               'Drawing Name
  strPrmpt = "Select a block: "         'Message value
  On Error GoTo Error_Control
  ThisDrawing.Utility.GetEntity objBlk, varPnt, strPrmpt
  If objBlk.HasAttributes Then
    varAtts = objBlk.GetAttributes      'function to get the attributes
    Set objDBBlks = CreateDatabase(strName, dbLangGeneral)
    Set objTbl = objDBBlks.CreateTableDef(objBlk.Name)
      For intCnt = LBound(varAtts) To UBound(varAtts)
        Set objFld = objTbl.CreateField(varAtts(intCnt).TagString, dbText)
        objTbl.Fields.Append objFld
      Next
      strDwgNme = "Drawing Name"
        Set objFld = objTbl.CreateField(strDwgNme, dbText)
        objTbl.Fields.Append objFld
        objDBBlks.TableDefs.Append objTbl
        PopulateDB objBlk.Name, objDBBlks
        Set CreateDB = objDBBlks
  Else
    MsgBox "The selected block did not have any attributes"
  End If
  Exit Function
Error_Control:
'For example just dump out
  MsgBox "unbelievable fatal error, your not even allowed to have this error!"
'This will of course leave the calling function open to an error, so there had
'better be a test to make sure that this returned something (Not Nothing)
End Function


Public Sub testit()
  Dim myBase As Database
  Dim allTables As TableDefs
  Dim allFields As Fields
  Dim myTable As TableDef
  Dim myField As Field
  Set myBase = CreateDB("C:\mydata.mdb")
  Set allTables = myBase.TableDefs
  For Each myTable In allTables
    Set allFields = myTable.Fields
    For Each myField In allFields
      MsgBox myField.Name
    Next
  Next
  myBase.Close
End Sub

Private Sub PopulateDB(strBlkName As String, objDB As Database)
  Dim NewSS As AcadSelectionSet
  Dim objBlk As AcadBlockReference
  Dim rsAtts As Recordset
  Dim fldAtt As Field
  Dim varAtts As Variant
  Dim varPnt1 As Variant
  Dim varPnt2 As Variant
  Dim VarData(0 To 1) As Variant
  Dim intData(0 To 1) As Integer
  Dim intCnt As Integer
  Dim strDwgNme As String
      strDwgNme = ThisDrawing.Name
  Set NewSS = vbdPowerSet("data")
  VarData(0) = "INSERT"
  VarData(1) = strBlkName
  intData(0) = 0
  intData(1) = 2
  NewSS.Select Mode:=acSelectionSetAll, FilterType:=intData, FilterData:=VarData
  Set rsAtts = objDB.OpenRecordset(strBlkName)
  For Each objBlk In NewSS
    varAtts = objBlk.GetAttributes
    rsAtts.AddNew
    For intCnt = LBound(varAtts) To UBound(varAtts)
      rsAtts.Fields(intCnt) = varAtts(intCnt).TextString
      
    Next
    rsAtts.Update
  Next
  rsAtts.Close
End Sub
Public Function vbdPowerSet(strName As String) As AcadSelectionSet
  Dim objSelSet As AcadSelectionSet
  Dim objSelCol As AcadSelectionSets
  Set objSelCol = ThisDrawing.SelectionSets
    For Each objSelSet In objSelCol
      If objSelSet.Name = strName Then
        ThisDrawing.SelectionSets.Item(strName).Delete
        Exit For
      End If
    Next
  Set objSelSet = ThisDrawing.SelectionSets.Add(strName)
  Set vbdPowerSet = objSelSet
End Function

Attribute VB_Name = "Integrate_mod"
'Integrating Microsoft Excel and Access with AutoCAD VBA

'Essential Preparations for Connecting AutoCAD with Excel and Access
'Obviously, to take advantage of AutoCAD's VBA, we need to launch AutoCAD and use a command
'like VBAMAN or VBAIDE to bring up the VBA interface within AutoCAD.  By default, AutoCAD
'VBA does not recognize Excel and Access objects, so you need to use the VBA Tools/References
'pulldown menu function and select a Microsoft Excel Object Library and/or a Microsoft
'DAO (Data Access Objects) Library to use Excel and/or Access Objects and their properties.

Attribute VB_Name = "Module1"
Option Explicit

Public Function CreateDB(strName As String) As Database
  Dim objDBBlks As Database
  Dim objTbl As TableDef
  Dim objFld As Field
  Dim objBlk As AcadBlockReference
  Dim varAtts As Variant
  Dim varPnt As Variant
  Dim intCnt As Integer
  Dim strPrmpt As String
  strPrmpt = "Select a block: "
  On Error GoTo Error_Control
  ThisDrawing.Utility.GetEntity objBlk, varPnt, strPrmpt
  If objBlk.HasAttributes Then
    varAtts = objBlk.GetAttributes
    Set objDBBlks = CreateDatabase(strName, dbLangGeneral)
    Set objTbl = objDBBlks.CreateTableDef(objBlk.Name)
      For intCnt = LBound(varAtts) To UBound(varAtts)
        Set objFld = objTbl.CreateField(varAtts(intCnt).TagString, dbText)
        objTbl.Fields.Append objFld
      Next
        objDBBlks.TableDefs.Append objTbl
        PopulateDB objBlk.Name, objDBBlks
        Set CreateDB = objDBBlks
  Else
    MsgBox "The selected block did not have any attributes"
  End If
  Exit Function
Error_Control:
'For example just dump out
  MsgBox "unbelievable fatal error, your not even allowed to have this error!"
'This will of course leave the calling function open to an error, so there had
'better be a test to make sure that this returned something (Not Nothing)
End Function


Public Sub testit()
  Dim myBase As Database
  Dim allTables As TableDefs
  Dim allFields As Fields
  Dim myTable As TableDef
  Dim myField As Field
  Set myBase = CreateDB("C:\mydata.mdb")
  Set allTables = myBase.TableDefs
  For Each myTable In allTables
    Set allFields = myTable.Fields
    For Each myField In allFields
      MsgBox myField.Name
    Next
  Next
  myBase.Close
End Sub

Private Sub PopulateDB(strBlkName As String, objDB As Database)
  Dim NewSS As AcadSelectionSet
  Dim objBlk As AcadBlockReference
  Dim rsAtts As Recordset
  Dim fldAtt As Field
  Dim varAtts As Variant
  Dim varPnt1 As Variant
  Dim varPnt2 As Variant
  Dim VarData(0 To 1) As Variant
  Dim intData(0 To 1) As Integer
  Dim intCnt As Integer
  Set NewSS = vbdPowerSet("data")
  VarData(0) = "INSERT"
  VarData(1) = strBlkName
  intData(0) = 0
  intData(1) = 2
  NewSS.Select Mode:=acSelectionSetAll, FilterType:=intData, FilterData:=VarData
  Set rsAtts = objDB.OpenRecordset(strBlkName)
  For Each objBlk In NewSS
    varAtts = objBlk.GetAttributes
    rsAtts.AddNew
    For intCnt = LBound(varAtts) To UBound(varAtts)
      rsAtts.Fields(intCnt) = varAtts(intCnt).TextString
    Next
    rsAtts.Update
  Next
  rsAtts.Close
End Sub
Public Function vbdPowerSet(strName As String) As AcadSelectionSet
  Dim objSelSet As AcadSelectionSet
  Dim objSelCol As AcadSelectionSets
  Set objSelCol = ThisDrawing.SelectionSets
    For Each objSelSet In objSelCol
      If objSelSet.Name = strName Then
        ThisDrawing.SelectionSets.Item(strName).Delete
        Exit For
      End If
    Next
  Set objSelSet = ThisDrawing.SelectionSets.Add(strName)
  Set vbdPowerSet = objSelSet
End Function

Attribute VB_Name = "Module2"
'To call the form include a module with the following macro name "DWGlog".

Sub DWGlog()

        logform.Show

End Sub

'Double-click on the form and enter the code that does the work:

Private Sub updatebutton_Click()
Dim excel As Object
Dim excelsheet As Object
Dim exapp As Object

'The four lines above create variables containing the Excel application, the workbook to be used and the sheet to be used. We then hide the form and check to see if Excel is running. If it is not we start it (the "On Error Resume Next" line prevents the macro from stopping if Excel is not yet open)...

On Error Resume Next
Me.Hide
Set excel = GetObject(, "Excel.application")
If Err <> 0 Then
Err.Clear
Set excel = CreateObject("Excel.application")
If Err <> 0 Then
MsgBox "Could not load Excel.", vbOKOnly + vbInformation, "Error report"
End
End If
End If

'We then make Excel visible and open a specific workbook called Drawinglog (if you want the log to be updated without ever seeing Excel set Excel.visible to false)...

On Error GoTo 0
excel.Visible = True
Set exapp = excel.workbooks.Open("c:\vba\Drawinglog.xls")

'We then save the current drawing name (using the Thisdrawing.name property) and the date (using the VB date command) to variables and set the starting column number and row number in Excel (row number 1 contains a heading so we start at 2)...

DWGNAME = ThisDrawing.Name
todaysdate = Date
rownum = 2
columnnum = 1

'We need to set the active sheet in Excel to send the data to and make it active...

Set excelsheet = excel.ActiveWorkbook.Sheets("sheet1")
excel.Sheets("sheet1").Select

'We then scan down column A using a "Do...until" loop by incrementing the rownum counter until we encounter an empty cell or a cell containing the current drawing name...

With exapp
Do Until excelsheet.Cells(rownum, 1).Value = "" Or excelsheet.Cells(rownum, 1).Value = DWGNAME
rownum = rownum + 1
Loop

'We then enter our drawing name (saved in the variable DWGNAME) into the cell and move one column to the right to place the date...

excelsheet.Cells(rownum, 1).Value = DWGNAME
If excelsheet.Cells(rownum, 1).Value = DWGNAME Then
columnnum = columnnum + 1
End If

'We need to scan to the right holding rownum constant and incrementing columnnum using another "Do..Until" loop, until we find an empty cell or one that matches today's date. In this example we don't want to muddy the spreadsheet by adding duplicate dates. When we find a match or an empty cell put the date (stored in the variable todaysdate) in the cell...

Do Until (excelsheet.Cells(rownum, columnnum).Value = "" Or excelsheet.Cells(rownum, columnnum).Value = todaysdate)
columnnum = columnnum + 1
Loop
excelsheet.Cells(rownum, columnnum).Value = todaysdate

'All that remains is to save the workbook, close it and close Excel...

excel.ActiveWorkbook.Save
excel.ActiveWorkbook.Close
excel.Quit
End With
End Sub

Attribute VB_Name = "Module3"
Function GetFileNames(strDirPath As String, Optional strExt As String = "*.dwg", _
                     Optional strDelim As String = ",") As String
    'Returns a delimeted string of all files in a directory that
    'match the extension you provide. Bt default it returns AutoCAD
    'Drawings. You can change the delimiting character. To get file names from
    'this string use the ParseString function
    Dim strFileList     As String
    Dim strFileNames    As String
    Dim strTemp         As String
    If Right$(strDirPath, 1) <> "\" Then
        strDirPath = strDirPath & "\"
    End If
    strFileNames = strDirPath & strExt
    strTemp = Dir$(strFileNames)
    Do While Len(strTemp) <> 0
        strFileList = strFileList & strTemp & strDelim
        strTemp = Dir$()
    Loop
    If Len(strFileList) > 1 Then
        GetFileNames = Left(strFileList, Len(strFileList) - 1)
    Else
        GetFileNames = ""
    End If
End Function

Attribute VB_Name = "View_Dwg_Properties_mod"
Sub View_Dwg_Properties_frm()
On Error Resume Next

        Dwg_Properties_frm.Show

End Sub
