Attribute VB_Name = "frmBlockReport"
Attribute VB_Base = "0{EAB75E31-678D-11D2-ADD4-0080488509BF}{EAB75E09-678D-11D2-ADD4-0080488509BF}"
Attribute VB_Creatable = False
Attribute VB_PredeclaredId = True
Attribute VB_Exposed = False
Attribute VB_TemplateDerived = False
Attribute VB_Customizable = False
Option Explicit

    Dim intColBlock As Integer
    Dim intColCount As Integer
    

Private Sub cmdExit_Click()
Unload Me
End Sub

Private Sub cmdFindBlocks_Click()
' Finds all blocks in a Drawing an puts found drawings into the
' Block Report FlexGrid

    Dim objAcad As Object
    Dim objDoc As Object
    Dim objnewss As Object
    Dim dblPt1(0 To 2) As Double
    Dim dblPt2(0 To 2) As Double
    Dim intGpCode(0) As Integer
    Dim GpData(0) As Variant
    Dim objEntity As Object
    Dim intCounter As Integer
    Dim intRowLocation As Integer
    Dim intRowCounter As Integer
    
    dblPt1(0) = 1: dblPt1(1) = 1: dblPt1(2) = 0
    dblPt2(0) = 2: dblPt2(1) = 2: dblPt2(2) = 0
    intGpCode(0) = 0: GpData(0) = "INSERT"
    Set objAcad = GetObject(, "AutoCAD.Application")
    Set objDoc = objAcad.ActiveDocument
    ' create a selection set
    Set objnewss = objDoc.SelectionSets.Add("ONLYBLOCKS")
    
    ' Make the FlexGrid Invisible for faster processing
    lstResults.Visible = False
    
    ' Change the Status Text
    txtStatus.Caption = "Selecting Blocks"
    
   ' Repaint the Form
   frmBlockReport.Repaint
    
    ' Set up the type of selection set with the filter Insert
    objnewss.Select acSelectionSetAll, dblPt1, dblPt2, intGpCode, GpData
    
    ' Clear the block list box
    lstResults.Clear
   
   ' Set up the column titles in the Block Results FlexGrid
   lstResults.Rows = 1              ' Set the number of initial Rows
   lstResults.Cols = 2              ' Set the number of initial Colums
   lstResults.Row = 0               ' Set the Row to Row 0
   lstResults.Col = intColBlock     ' Set the Colum to the Block Colum
   lstResults.Text = "Block Name"   ' Set the Text in the Block Colum to "Block Name"
   lstResults.Col = intColCount     ' Change the Colum to Count
   lstResults.Text = "Count"        ' Set the Text in the Count Colum to "Count"
    

    
   ' set the row location to the first row
   intRowLocation = 0
          
   ' Change the Status Text
   txtStatus.Caption = "Processing Blocks"
   ' Repaint the Form
   frmBlockReport.Repaint
   
   ' Process each block in the selection Set objnewss
   For Each objEntity In objnewss

      For intRowCounter = 0 To lstResults.Rows - 1
        
        'Set the Row to the Counter
        lstResults.Row = intRowCounter
        
        ' Set the Colum to block name
        lstResults.Col = 0
        
        ' check for a match of the Block name and the text Value in the grid
        If objEntity.Name = lstResults.Text Then
                    
          ' set the Column to Count
          lstResults.Col = 1
          
          ' add one to the Quantity in the Count Column
          lstResults.Text = CDbl(lstResults.Text) + 1
          GoTo ExitProcessing
        End If
        
        
      Next
      
        ' addition of New block to the Flex grid
        ' set the rowlocation to the number of current rows..
        '(0 = 1 in grid world)
        intRowLocation = lstResults.Rows
        ' add a row to the Results FlexGrid
        lstResults.Rows = lstResults.Rows + 1
        lstResults.Row = intRowLocation     ' Setup the Row location
        lstResults.Col = intColBlock        ' Set the Column to the Block colum
        lstResults.Text = objEntity.Name    ' Place the Block text name into the FlexGrid
        lstResults.Col = intColCount        ' Set the Column to the Count column
        lstResults.Text = "1"               ' Place "1" into the FlexGrid in the count column

        
ExitProcessing:
       
        
 ' end of for
  Next
  
  
  
  ' sort the FlexGrid on the block column
  lstResults.Col = intColBlock
  lstResults.Sort = flexSortGenericAscending ' Sort the FlexGrid Assending
    
  ' Make the FlexGrid Visible
  lstResults.Visible = True
   
    ' make the Remove button and Place button enabled or disabled
    If lstResults.Rows <= 1 Then
       cmdRemove.Enabled = False
       cmdMtextPlace.Enabled = False
       Else
       cmdRemove.Enabled = True
       cmdMtextPlace.Enabled = True
    End If
   

End Sub


Private Sub cmdMtextPlace_Click()
' Place an MText object in to the drawing containing the block names and the count
    Dim objAcad As Object
    Dim objDoc As Object
    Dim objUtil As Object
    Dim strDrawingName As String
    Dim intCounter As Integer
    Dim strMTextOutPut As String
    Dim MtextWidth As Double
    Dim objNewMtextReport As Object
    Dim Pt1 As Variant
    Dim dblXscale As Double
    Dim dblYscale As Double
    Dim dblRotAngle As Double
    Dim strSetting As String
    Dim strOUT1  As String
    Dim Qt As String
    
    ' set Qt to equal chr(34)
    ' this is the ASCII character "
    Qt = Chr(34)
    
    ' set the string length to the largest number by setting the flexGrid Sort on the highest number
    ' sort the FlexGrid on the Count column
    lstResults.Col = intColBlock
    lstResults.Sort = flexSortNumericDescending   ' Sort the FlexGrid decending
    lstResults.Col = intColCount
    lstResults.Row = 1
    'The string length
    strSetting = Qt + lstResults.Text & Qt
    
    
    ' sort the FlexGrid on the block column
    lstResults.Col = intColBlock
    lstResults.Sort = flexSortGenericAscending ' Sort the FlexGrid Assending
    
    ' Width of the Mtext object
    MtextWidth = 525
    
    Set objAcad = GetObject(, "AutoCAD.Application")
    Set objDoc = objAcad.ActiveDocument
    Set objUtil = objDoc.Utility
      
    strMTextOutPut = "\fArial|b0|i0|c0|p34;Block Report: \P\LQty.    Block\Fmonotxt.shx;\l "
    
    ' Process every row in the Block results FlexGrid
    For intCounter = 1 To lstResults.Rows - 1
       strOUT1 = strSetting             ' set the lenght of the string for the QTY or Count Field.
       lstResults.Col = intColCount     ' set the FlexGrid colum to the Count column
       lstResults.Row = intCounter      ' set the FlexGrid row to the row being processed.
       RSet strOUT1 = lstResults.Text   ' Get the text from the flexgrid at this location
                                        ' and right set the text from this location.
       strMTextOutPut = strMTextOutPut & "\P" & strOUT1 ' add this text to the mtext out string
       lstResults.Col = intColBlock     ' set the FlexGrid colum to the Block column
       lstResults.Row = intCounter      ' set the FlexGrid row to the row being processed.
       strMTextOutPut = strMTextOutPut & Space(1) & lstResults.Text ' add this text to the mtext out string
    Next intCounter     ' Process the next intCounter
           
    ' Hide the Block Report form
    frmBlockReport.hide
    
    ' Select the Block Report location on screen.
    Pt1 = objUtil.GetPoint(, "Select Block Report location:")
    dblXscale = 1
    dblYscale = 1
    dblRotAngle = 0
    
    If ThisDrawing.GetVariable("tilemode") = 1 Then
        Set objNewMtextReport = objDoc.ModelSpace.AddMText(Pt1, MtextWidth, strMTextOutPut)
        Else
        Set objNewMtextReport = objDoc.PaperSpace.AddMText(Pt1, MtextWidth, strMTextOutPut)
    End If
    
    ' Redraw refresh or otherwise update the mtext just placed in the drawing.
    objNewMtextReport.Update
    
    ' Show the block report form
    frmBlockReport.Show
    
End Sub

Private Sub cmdRemove_Click()
' used to delete a selected row in the FlexGrid

On Error GoTo ClearForm

lstResults.RemoveItem lstResults.RowSel


Exit Sub
ClearForm:
Call UserForm_Initialize
Exit Sub


End Sub



Private Sub UserForm_Initialize()
   ' setup global varialbes
    intColBlock = 0
    intColCount = 1
   
   ' Clear the lstResults Flex Grid
   lstResults.Clear
   
   ' Set the number of rows
   lstResults.Rows = 1
   ' Set the column titles in the results grid
   lstResults.Row = intColBlock
   lstResults.Col = intColBlock
   lstResults.Text = "Block Name"
   lstResults.ColWidth(intColBlock) = 3000
   lstResults.Col = intColCount
   lstResults.Text = "Count"
   lstResults.ColWidth(intColCount) = 600
   
    ' make the Remove button and Place button enabled or disabled
    If lstResults.Rows <= 1 Then
       cmdRemove.Enabled = False
       cmdMtextPlace.Enabled = False
       Else
       cmdRemove.Enabled = True
       cmdMtextPlace.Enabled = True
       
    End If
   
End Sub
