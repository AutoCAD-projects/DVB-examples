Attribute VB_Name = "basGlobal"
Public Sub ShowForm()
    frmTabs.Show
End Sub
Public Sub Tabs(Form As UserForm, Ctrl As Control)
' this subroutine demonstrates some different attributes of the multipage control
' it also demonstrates the technique of building a control name on the fly, based
' upon the page number it is on, and using it.

    Const strTxtBox As String = "TextBox"         ' first part of control name
    Static Message As String                      ' use static to build the message with each pass
    
    ' show how to get the name and active page from the multipage control
    ' note: Intellisense does not work on the passed in control.
    '       This means that you must know the propertities of the object
    '       instead of depending on the Intellisense feature.
    MsgBox "The active page name is " & Ctrl.SelectedItem.Name & vbCrLf & _
           "and its index number is " & CStr(Ctrl.SelectedItem.Index), , "Tabs"
    
    Dim ctrlName As String                        ' holds the control's name
    Dim txtbox As TextBox                         ' a textbox object
    Dim lngIdx As Long                            ' counter for the For loop
    Dim lngCnt As Long                            ' holds the number of pages on the multipage control
    lngCnt = Ctrl.Count                           ' how many pages on the multipage?
    For lngIdx = 1 To lngCnt                      ' process each textbox control (one per page)
        ctrlName = strTxtBox & CStr(lngIdx)       ' create its name and store it
        Dim MyControl As Control                  ' a control object
        For Each MyControl In Form.Controls       ' search each control on the form
            If MyControl.Name = ctrlName Then     ' check the controls name against the built name
                Set txtbox = MyControl            ' grab the control into a textbox object
                ' build the output message of what was found using the textbox object
                Message = Message & "textbox" & CStr(lngIdx) & " = " & _
                                    txtbox.Text & vbCrLf
            End If
        Next
    Next lngIdx
    MsgBox Message, , "Tabs"                      ' display the message
    Message = ""                                  ' clear the message
End Sub

Public Function DoesControlExist(Form As UserForm, ctrlName As String) As Boolean
' this function takes the userform and the suspected control name and verifies
' whether or not the control is present on the form
' True is returned when it is found and false when it is not found
' The control name is case sensitive normally so ucase is used to illiminate the
' problem
        Dim MyControl As Control
        Dim Result As Boolean
        Result = False
        For Each MyControl In Form.Controls
            If UCase(MyControl.Name) = UCase(ctrlName) Then
                Result = True
                Exit For
            End If
        Next
        DoesControlExist = Result
End Function

Attribute VB_Name = "frmTabs"
Attribute VB_Base = "0{C53739B4-07DC-11D2-99E5-00609761BD90}{C53739A0-07DC-11D2-99E5-00609761BD90}"
Attribute VB_Creatable = False
Attribute VB_PredeclaredId = True
Attribute VB_Exposed = False
Attribute VB_TemplateDerived = False
Attribute VB_Customizable = False
Private Sub btnShowText_Click()
    MsgBox "The active page name is " & Me.MultiPage1.SelectedItem.Name & vbCrLf & _
           "and its index number is " & CStr(Me.MultiPage1.SelectedItem.Index), , "btnShowText"
    Stop
    Tabs Me, Me.MultiPage1                ' call the routine to show the text fields

End Sub

Private Sub UserForm_Initialize()
    ' set default values
    If DoesControlExist(Me, "TextBox1") Then
        TextBox1.Text = "Text Box 1"
    End If
    If DoesControlExist(Me, "TextBox2") Then
        TextBox2.Text = "Text Box 2"
    End If
    If DoesControlExist(Me, "TextBox3") Then
        TextBox3.Text = "Text Box 3"
    End If
    If DoesControlExist(Me, "TextBox4") Then
        TextBox4.Text = "Text Box 4"
    End If
    ' default page is the first (0)
    Me.MultiPage1.Value = 0
    
End Sub
Private Sub btnOK_Click()
    
    End
End Sub

Private Sub btnShowPageCnt_Click()
    Dim lngCnt As Long
    lngCnt = Me.MultiPage1.Count
    
    MsgBox "There are " & CStr(lngCnt) & " pages on the form.", , "Tabs"
    Stop
End Sub
