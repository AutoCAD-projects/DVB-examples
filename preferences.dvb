Attribute VB_Name = "Module1"
Public acadApp As AcadApplication
Public acadDOC As AcadDocument
'


Sub Preferences()

    Dim prefs As AcadPreferences
    Set prefs = ThisDrawing.Application.Preferences
    If prefs.Display.DisplayScreenMenu Then
       MsgBox "Why do you have screen menus on?"
    End If

End Sub

Sub GetApp()

    On Error Resume Next
    Set acadApp = GetObject(, "AutoCAD.Application")
    
    If Err Then
       MsgBox "AutoCAD not running"
       Err.Clear
       'your program should launch AutoCAD now or simply terminate
      Else
       'AutoCAD is running
       'Variable acadDOC is an object dimensioned in a global module
       Set acadDOC = acadApp.ActiveDocument 'same as ThisDrawing
    End If

End Sub

Sub DocAccess()

    Dim DWGS As AcadDocuments
    Set DWGS = ThisDrawing.Application.Documents
    Dim ADWG As AcadDocument
    On Error Resume Next
    Err.Clear
    Set ADWG = DWGS.Item(DrawingName)
    If Err.Number <> 0 Then
      'drawing name not in collection
     Else
      If ADWG.Active = False Then ADWG.Activate
    End If

End Sub

Sub MultipleDocs()

    Dim APS As AcadPreferences
    Dim Nam As String
    Nam = "ATT.DWG"
    Set APS = ThisDrawing.Application.Preferences
    If APS.System.SingleDocumentMode = False Then
          Dim DWG As AcadDocument
          Set DWG = ThisDrawing.Application.ActiveDocument
          ThisDrawing.Application.Documents.Open ("d:\AT&T\" & Nam)
          ThisDrawing.Application.ActiveDocument = DWG
    End If

End Sub
Sub GetReal()

    Dim myVal As Double
    myVal = ThisDrawing.Utility.GetReal("Enter a real number: ")

End Sub

Sub GetMore()

    With ThisDrawing.Utility
        Dim myVal As Double
        myVal = .GetReal("Enter a real number")
        Dim MyStr As String
        MyStr = .GetString(1, "Enter a string")
        Dim MyInt As Integer
        MyInt = .GetInteger("Enter an integer")
    End With
End Sub

Sub ShowPoint()

    MyInputForm.Hide
    Dim Pnt As Variant
    Pnt = ThisDrawing.Utility.GetPoint(, "Select a point")
    MyInputForm.PtX.Value = Pnt(0)
    MyInputForm.PtY.Value = Pnt(1)
    MyInputForm.Show

End Sub

Sub LayerCollection()

    Dim MyLayer As AcadLayer
    Set MyLayer = ThisDrawing.Layers.Add("MyLayer")
    MyLayer.Color = acBlue
    MyLayer.Linetype = "DASHED"

End Sub

Sub CreateLine()

    Dim Obj As AcadLine
    Dim P1(0 To 2) As Double
    Dim P2(0 To 2) As Double
    P1(0) = 1#: P1(1) = 1#: P1(2) = 0#
    P2(0) = 5#: P1(1) = 1#: P1(2) = 0#
    Set Obj = ThisDrawing.ModelSpace.AddLine(P1, P2)
    'Variable (Obj) now contains line object.

End Sub

Sub GetEntity()

    Dim Obj As Object
    Set Obj = ThisDrawing.ModelSpace.Item(0)

End Sub

Sub PickEntity()

    Dim Uobj As Object
    Dim Pnt(0 To 2) As Double
    On Error Resume Next
    ThisDrawing.Utility.GetEntity Uobj, Pnt, "Pick an object: "
    If Err.Number <> 0 Then
       Err.Clear
       MsgBox "Entity not selected."
     Else
       'Entity object now in variable (Uobj).
    End If
    If (Uobj.EntityType = acArc) Then
        Uobj.Radius = 1.5
        Uobj.Update
    End If
    Dim Vobj As Object
    Dim Pnt2(0 To 2) As Double
    On Error Resume Next
    ThisDrawing.Utility.GetEntity Vobj, Pnt2, "Select another object: "
    If Err <> 0 Then
       Err.Clear
       MsgBox "You didn't pick an object!"
    Else
       Dim Pnts As Variant
       Pnts = Vobj.IntersectWith(Uobj, acExtendNone)
       If VarType(Pnts) <> vbEmpty Then
         Dim I As Integer
         For I = LBound(Pnts) To UBound(Pnts)
            S$ = Pnts(I) & ", " & Pnts(I + 1) & ", " & Pnts(I + 2)
            MsgBox "Found intersection at " & S$
            I = I + 2
         Next I
       Else
         MsgBox "No intersections found"
       End If
    End If
End Sub

Sub CreateLWPolyline()

    Dim Obj As AcadLWPolyline
    Dim P1(0 To 7) As Double
    P1(0) = 1#: P1(1) = 1# 'Vertex 0
    P1(2) = 1#: P1(3) = 5# 'Vertex 1
    P1(4) = 4#: P1(5) = 1# 'Vertex 2
    P1(6) = 2.5: P1(7) = 0.75 'Vertex 3
    Set Obj = ThisDrawing.ModelSpace.AddLightWeightPolyline(P1)
    Obj.Closed = True
    'add 35 degree included angle at 2nd to last segment
    Obj.SetBulge 2, 0.15
    'add 45 degree included angle at closing segment
    Obj.SetBulge 3, 0.2

End Sub

Sub CreateObj()

    Dim Atext As AcadText
    S$ = ThisDrawing.FullName & "  " & Now
    Dim Pt(2) As Double
    Pt(0) = 1#: Pt(1) = 1#: Pt(2) = 0#
    Dim Ht As Double
    Ht = 0.2
    Set Atext = ThisDrawing.ModelSpace.AddText(S$, Pt, Ht)
    Atext.Layer = "TEMP"

End Sub

Sub CreateLine2()

    'Draw a line from the point (2, 3, 0) to the point (5, 2, 1).
    'Use BASIC Dim statement to declare variables.
    Dim P1(0 To 2) As Double 'Define array of double precision.
    Dim P2(0 To 2) As Double 'Array of numbers for point 2.
    Dim Obj As AcadLine 'Define line object variable.
    P1(0) = 2#: P1(1) = 3#: P1(2) = 0#  'Set the value of point 1.
    P2(0) = 5#: P2(1) = 2#: P2(2) = 1# 'Set the value of point 2.
    
    'The next statement creates the line object from P1 to P2
    Set Obj = ThisDrawing.ModelSpace.AddLine(P1, P2) 'Create the new line


End Sub

Attribute VB_Name = "ThisDrawing"
Attribute VB_Base = "0{8E75D913-3D21-11D2-85C4-080009A0C626}"
Attribute VB_Creatable = False
Attribute VB_PredeclaredId = True
Attribute VB_Exposed = True
Attribute VB_TemplateDerived = False
Attribute VB_Customizable = True

Dim Time_Start
Dim Dwg_Name As String

Private Sub AcadDocument_Activate()
  Time_Start = Timer
  Dwg_Name = ThisDrawing.FullName
End Sub
'
Private Sub AcadDocument_Deactivate()
  MsgBox "Time Spent in " & Dwg_Name & " was " & Timer - Time_Start
End Sub
