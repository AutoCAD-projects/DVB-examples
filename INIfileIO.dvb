Attribute VB_Name = "BasMisc"

Option Explicit

'   Paladin
'   Copyright (C) 1998 by Paladin.  All rights reserved.

'   Permission to use or modify this software is hereby granted to the
'   licensee, provided that the above copyright notice appears in all
'   copies and that both that copyright notice and this permission
'   notice appear in all supporting documentation.

'   Permission is hereby granted to use this routine on the condition that
'   this header remains with the routine. No warrantity is implied or
'   expressed.

'   Original version   2-4-98  John Gibb
'            revised    -  -


Public Arguments() As Variant
Const delimiter = ","
' Argument 1 determines the showing of the form (ShowForm) or command line processing (NoForm)
'          2 is the project number
'          3 is the Work order number
'          4 is the users name
'          5 is the status of the document
'          6 is the drawing name
Public FormVisibility As String
Public ProjectNumber As String
Public WorkOrder As String
Public UserName As String
Public DocStatus As String
Public DwgName As String

Public Sub Get_Arguments(ArgStr As String)
    Dim i, cnt As Long
    cnt = count_occurances(ArgStr, delimiter)
    If Not (cnt >= 0 And Len(ArgStr) > 0) Then          ' if not at least one argument - abort
        MsgBox "No arguments passed to the program. Aborting.", vbOKOnly
        End
    End If
    For i = 0 To cnt                                    ' Loop through the argument string getting the arguments
        ReDim Preserve Arguments(i)                     ' Allocate a new element.
        Arguments(i) = parse(ArgStr, delimiter, i + 1)  ' add the argument to the array
    Next i

End Sub

Public Function count_occurances(line As String, delimit As String) As Long

    Dim i, cnt As Long
    cnt = 0
    For i = 1 To Len(line)
        If delimit = Mid(line, i, Len(delimit)) Then
            cnt = cnt + 1
        End If
    Next i
    
    count_occurances = cnt

End Function

Public Function parse(parse_string As String, delimit As String, position As Long) As String
    Dim c As Long
    Dim Lpipe As Long
    Dim Rpipe As Long
    Dim mark As Long
    Dim tempvar As String
    Dim start As Long
    Dim datalen As Long
    Dim cnt As Long
    c = 1
    Lpipe = 0
    mark = 1
    tempvar = ""
    For cnt = 1 To position
        Do While Mid(parse_string, c, 1) <> delimit And Len(parse_string) >= c
            c = c + 1
        Loop
        Rpipe = c
        If mark = position - 1 Then
            Lpipe = c
        End If
        c = c + 1
        mark = mark + 1
    Next cnt
    start = Lpipe + 1
    datalen = (Rpipe - Lpipe) - 1
    parse = Mid(parse_string, start, datalen)
End Function

Public Function chk_plural(var As Long, mode As Long)
    Dim plural As Boolean
    If var = 0 Or var > 1 Then plural = True
    
    Select Case mode
        Case 1
            If plural = True Then
                chk_plural = "s"
            Else
                chk_plural = ""
            End If
        Case 2
            If plural = True Then
                chk_plural = "are"
            Else
                chk_plural = "is"
            End If
        Case 3
            If plural = True Then
                chk_plural = "were"
            Else
                chk_plural = "was"
            End If
        Case Else
            plural = ""
    End Select

End Function

Public Function Token(tmp As String, search As String) As String
    Dim X As Variant
    X = InStr(1, tmp, search)
    If X Then
       Token = Mid(tmp, 1, X - 1)
       tmp = Mid(tmp, X + 1)
    Else
       Token = tmp
       tmp = ""
    End If
End Function
Public Function RightToken(tmp As String, search As String) As String
    Dim X As Variant
    X = InStr(1, tmp, search)
    If X Then
       RightToken = Mid(tmp, X, Len(tmp))
'       tmp = Mid(tmp, X + 1)
    Else
       RightToken = tmp
       tmp = ""
    End If
End Function

Attribute VB_Name = "basGlobal"
Option Explicit
Declare Function GetPrivateProfileString Lib "kernel32" Alias "GetPrivateProfileStringA" (ByVal lpApplicationName As String, ByVal lpKeyName As Any, ByVal lpDefault As String, ByVal lpReturnedString As String, ByVal nSize As Long, ByVal lpFileName As String) As Long
Declare Function WritePrivateProfileString Lib "kernel32" Alias "WritePrivateProfileStringA" (ByVal lpApplicationName As String, ByVal lpKeyName As Any, ByVal lpString As Any, ByVal lpFileName As String) As Long
Public Const gintMAX_SIZE As Integer = 50
Global Const gstrNULL$ = ""                             'Empty string
Public Sub INIExample()
    frmInput.Show
End Sub
'-----------------------------------------------------------
' FUNCTION: ReadIniFile
'
' Reads a value from the specified section/key of the
' specified .INI file
'
' IN: [strIniFile] - name of .INI file to read
'     [strSection] - section where key is found
'     [strKey] - name of key to get the value of
'     [KeyMode] - whether to read and return all keys
'                 or just the one supplied and return its item
'
' Returns: non-zero terminated value of .INI file key
'-----------------------------------------------------------
'
Public Function ReadIniFile(ByVal strIniFile As String, ByVal strSection As String, ByVal strKey As String, KeyMode As Boolean) As String
'    Stop
    'Dim strBuffer As String     ' declare the buffer seperately because otherwise
                                ' it will not store returned data properly
                                ' This might be because of the Space function used
                                ' to inititate it. (Not sure)
    Dim strBuffer As String
    Dim strResult As String
    Dim intPos As Integer

    strBuffer = Space$(gintMAX_SIZE)    ' initiate buffer (a must!!!)
    If KeyMode Then                     ' true when wants all keys
        intPos = GetPrivateProfileString(strSection, vbNullString, "default", strBuffer, gintMAX_SIZE, strIniFile)
    Else                                ' just wants one key's item
        intPos = GetPrivateProfileString(strSection, strKey, "default", strBuffer, gintMAX_SIZE, strIniFile)
    End If
    If intPos > 0 Then
        ReadIniFile = Mid(strBuffer, 1, intPos) ' strip off extra chars in buffer as it is sent back
    Else
        ReadIniFile = gstrNULL                  ' return nothing on failure
    End If
End Function
Public Function WriteIniFile(ByVal strIniFile As String, ByVal strSection As String, ByVal strKey As String, ByVal strItem As String) As String
'    Stop
    Dim strResult As String
    Dim intPos As Integer
    
    intPos = WritePrivateProfileString&(strSection, strKey, strItem, strIniFile)
    If intPos > 0 Then                  ' if successful - tell them
        MsgBox frmInput.txtItem & " was sucessfully written to the Key " & frmInput.txtKey & "."
    Else
        Debug.Print "failure"
    End If
End Function

Attribute VB_Name = "frmInput"
Attribute VB_Base = "0{3E7B3F67-222F-11D2-99EE-00609761BD90}{3E7B3E81-222F-11D2-99EE-00609761BD90}"
Attribute VB_Creatable = False
Attribute VB_PredeclaredId = True
Attribute VB_Exposed = False
Attribute VB_TemplateDerived = False
Attribute VB_Customizable = False
Option Explicit

Private Sub btnDone_Click()
    End
End Sub

Private Sub btnGetFile_Click()
    Dim strMessage As String
    strMessage = "Please select the INI file APICALLS.INI in your VBA book's support directory."
    MsgBox strMessage, , "APICalls"
    Me.Hide
    cmdInput.ShowOpen
'    Stop
    If Len(cmdInput.Filename) > 0 Then
        txtFileName.Text = cmdInput.Filename
    Else
        MsgBox "Nothing selected."
    End If
    Me.Show
    
End Sub

Private Sub btnReadINI_Click()
    Dim strIniFile, strSection, strKey, strResult As String
    strIniFile = txtFileName.Text
    strSection = "General Support"                      ' hard code a section header
    strKey = "Delimiter"                                ' hard code a key
    ' send off and get the information
    strResult = ReadIniFile(ByVal strIniFile, ByVal strSection, ByVal strKey, frmInput.rdKeySearch.Value)
    ' show the results
    txtSection.Text = strSection                        ' show the section header
    txtKey.Text = strKey                                ' and the key
    If InStr(1, strResult, Chr$(0), vbTextCompare) Then ' see if they got back a list of section headers
        Dim lngCnt, lngIdx As Long
        Dim strTemp As String
        lngCnt = count_occurances(strResult, Chr$(0))   ' find out how many
        For lngIdx = 1 To lngCnt                        ' replace the Null chras in the line with a comma
            strTemp = strTemp & parse(strResult, Chr$(0), lngIdx) & ","
        Next lngIdx
        strTemp = Left(strTemp, Len(strTemp) - 1)       ' remove the extra comma at the end
        ' show the results
        MsgBox "Found multiple keys." & vbCrLf & _
               " List is: " & strTemp, , "Key Search Results"
    Else
        txtItem.Text = strResult                            ' show the item
    End If
    
End Sub

Private Sub btnWriteINI_Click()
    Dim strResult As String
    If Len(Dir(txtFileName.Text)) > 0 Then                  ' make sure there is a file to write to
        ' make sure all fields are filled out
        If Len(txtSection.Text) > 0 And _
           Len(txtKey.Text) > 0 And _
           Len(txtItem.Text) > 0 Then
           ' send it off to be written
           strResult = WriteIniFile(ByVal txtFileName.Text, ByVal txtSection.Text, ByVal txtKey.Text, ByVal txtItem.Text)
        Else
            MsgBox "The Section, Key and Item text boxes must be filled out to continue."
        End If
    Else
        MsgBox txtFileName.Text & " not found.", , "Error"
    End If
End Sub


Private Sub UserForm_Initialize()
    rdItemSearch.Value = True
End Sub
