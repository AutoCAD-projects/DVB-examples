Attribute VB_Name = "TestModules"
Option Explicit
Public Sub TestSetXdata()
    Dim Pnt As Variant
    Dim Ent As Object
    Call GetEnt(Ent, Pnt)
' now process the entity
    If Len(Ent.Handle & "") > 0 Then
        Dim xdataobj As New Xdata
        Dim EntityObj As Object
        If xdataobj.GetXdata(Ent, "") Then
            Debug.Print "Found Xdata on the object"
                Dim lstbox As ListBox
                Set lstbox = frmXdataView.lstXdata
                xdataobj.List "d"
                Dim XdataValueTemp As Variant
                ' get original xdatavalue array to build fake input array
                XdataValueTemp = xdataobj.XdataValue
                ' replace an item in the array
                XdataValueTemp(1) = "John Wayne"
                ' put the replacement array into a new xdata object
                Dim newXdataObj As New Xdata
                ' transfer the same xdata type array to the new object
                newXdataObj.XdataType = xdataobj.XdataType
                ' jam the replacement array into the new object
                newXdataObj.XdataValue = XdataValueTemp
                newXdataObj.StoreAppNames
                ' XdataObj.XdataValue = newXdataObj.XdataValue
                xdataobj.SetXdata Ent, newXdataObj, "ANOTHER_TEST_APPLICATION"
                
        Else
            Debug.Print "No Xdata on the object"
        End If
    Else
       MsgBox "No entity selected to process.", , "Aborting"
    End If

End Sub
Public Sub TestListXdata()
    Dim Pnt As Variant
    Dim Ent As Object
    Call GetEnt(Ent, Pnt)
' now process the entity
    If Len(Ent.Handle & "") > 0 Then
        Dim xdataobj As New Xdata
        Dim EntityObj As Object
        If xdataobj.GetXdata(Ent, "") Then
            Debug.Print "Found Xdata on the object"
            Dim lstbox As ListBox
            Set lstbox = frmXdataView.lstXdata
            If xdataobj.AppExist("APP1") Then
                Debug.Print "Found App1 Xdata on the object"
            Else
                Debug.Print "No App1 Xdata on the object"
            End If
            Dim strTemp As String
            strTemp = xdataobj.AppNames(1)          ' get the first app
            Set xdataobj = Nothing
            ' alternate way of getting the data without checking the results
            'xdataobj.GetXdata Ent, strTemp         ' just one app
            xdataobj.GetXdata Ent, ""               ' all apps
            If xdataobj.AppNames.Count > 0 Then
                Debug.Print "Found Xdata for " & strTemp & " on the object"
                ' both the listmode and the form's listbox
                ' are optional, the default is default is debug print
                xdataobj.List           ' or XdataObj.List "d"
                xdataobj.List "d"
                xdataobj.List "m"
                xdataobj.List "l", lstbox
                frmXdataView.Show
            Else
                Debug.Print "No Xdata on the object"
            End If
        Else
            Debug.Print "No Xdata on the object"
        End If
    Else
       MsgBox "No entity selected to process.", , "Aborting"
    End If

End Sub
Public Sub TestSplitXdata()
    Dim Pnt As Variant
    Dim Ent As Object
    Call GetEnt(Ent, Pnt)
' now process the entity
    If Len(Ent.Handle & "") > 0 Then
        Dim xdataobj As New Xdata
        Dim EntityObj As Object
        If xdataobj.GetXdata(Ent, "") Then
            Debug.Print "Found Xdata on the object"
            If xdataobj.AppNames.Count > 0 Then
                ' both the listmode and the form's listbox
                ' are optional, the default is default is debug print
                xdataobj.List           ' load the 2d array
                xdataobj.Split          ' unload it into xdatatype & xdatavalue
            Else
                Debug.Print "No Xdata on the object"
            End If
        Else
            Debug.Print "No Xdata on the object"
        End If
    Else
       MsgBox "No entity selected to process.", , "Aborting"
    End If

End Sub

Public Sub GetEnt(Ent As Object, Pnt As Variant)
' This subroutine waits for input from user
    On Error Resume Next
   
    ' The following example
Retry:
'    Dim Ent As Object
    
    ThisDrawing.Utility.GetEntity Ent, Pnt, "Select an object: "
    
    If Err <> 0 Then
        Err.Clear
        MsgBox "You need to select an existing object"
        GoTo Retry
    End If
    
End Sub

Attribute VB_Name = "Xdata"
Attribute VB_Base = "0{FCFB3D2A-A0FA-1068-A738-08002B3371B5}"
Attribute VB_Creatable = True
Attribute VB_PredeclaredId = False
Attribute VB_Exposed = False
Attribute VB_TemplateDerived = False
Attribute VB_Customizable = False
Option Explicit

Public XdataType As Variant
Public XdataValue As Variant
Public AppNames As New Collection
Public ItemsCount As Long
Public aryXdata As Variant
Public EntityType As Long
Public Sub Split()
' take the two dimensional array used for listboxes and split it into
' the XdataType And XdataValue
    If Not IsEmpty(aryXdata) Then
        XdataType = Empty             ' clear the arrays
        XdataValue = Empty
        Dim holdXdataType() As Variant, holdXdataValue() As Variant
        Dim LngI As Long
        Dim strTemp As String
        Dim arrayData(0 To 2) As Variant
        For LngI = LBound(aryXdata) To UBound(aryXdata)
            ReDim Preserve holdXdataType(LngI)
            ReDim Preserve holdXdataValue(LngI)
            holdXdataType(LngI) = aryXdata(LngI, 0)
            If (aryXdata(LngI, 0) = 1010) Or (aryXdata(LngI, 0) = 1011) Or (aryXdata(LngI, 0) = 1012) Or (aryXdata(LngI, 0) = 1013) Then
                strTemp = aryXdata(LngI, 1)
                arrayData(0) = parse(strTemp, ",", 1)
                arrayData(1) = parse(strTemp, ",", 2)
                arrayData(2) = parse(strTemp, ",", 3)
                holdXdataValue(LngI) = arrayData
            Else
                holdXdataValue(LngI) = aryXdata(LngI, 1)
            End If
        Next LngI
        XdataType = holdXdataType
        XdataValue = holdXdataValue
    Else
        MsgBox "No data in aryXdata to split.", , "Error"
    End If
    
End Sub
Public Sub List(Optional Listmode As String, Optional frmList As ListBox)
' fill the objects property called aryXdata
'(2 dimensional array) and set up for display
' possible display list modes are:   "D" for debug.print (default)
'                                    "M" for message box
'                                    "L" for list box
    If Not IsEmpty(XdataType) Then
        ' put the two seperate array's data into a two dimensional array
        Dim inti, intj As Integer
        inti = UBound(XdataType)
        ReDim aryXdata(inti, 2)
        Dim i As Integer
        Dim arrayData As Variant
        For i = 0 To inti
            aryXdata(i, 0) = XdataType(i)
        Next i
        For i = 0 To inti
            If (XdataType(i) = 1010) Or (XdataType(i) = 1011) Or (XdataType(i) = 1012) Or (XdataType(i) = 1013) Then
                arrayData = XdataValue(i)
                aryXdata(i, 1) = arrayData(0) & "," & arrayData(1) & "," & arrayData(2)
            Else
                aryXdata(i, 1) = XdataValue(i)
            End If
        Next i
        Dim LngI As Long
        Select Case UCase(Listmode)
            Case "L"
                ' load the list control passed in
                frmList.Clear
                frmList.List = aryXdata
            Case "M"
                Dim strMsg As String
                strMsg = ""
                For LngI = LBound(aryXdata) To UBound(aryXdata)
                    strMsg = strMsg & aryXdata(LngI, 0) & ": " & aryXdata(LngI, 1) & vbCrLf
                Next LngI
                MsgBox strMsg, , "Xdata List"
            Case Else
                For LngI = LBound(aryXdata) To UBound(aryXdata)
                    Debug.Print aryXdata(LngI, 0) & ": " & aryXdata(LngI, 1)
                Next LngI
        End Select
    End If
End Sub

Public Function AppExist(Appname) As Boolean
' See if the appname is present in the xdata
' using the appnames collection of the object
    Dim result As Boolean
    On Error Resume Next
    Debug.Print AppNames.Item(Appname)
    If Err.Number > 0 Then
        Err.Clear
    Else
        result = True
    End If
    AppExist = result
End Function
Public Function SetXdata(OriginalObject As Object, MasterObject As Xdata, Appname) As Boolean
' Exposed function to user on the object for setting the xdata onto the entity or group
' The OriginalObject is the entity or group
' the MasterObject is the new xdata for placement
' the Appname is the application name to update ("" means update all apps on the entity)
    Dim result As Boolean
    Dim lngEtype As Long
    On Error Resume Next
    lngEtype = OriginalObject.EntityType
    If Err.Number > 0 Or lngEtype = 0 Then          ' is it a legal object (lngetype = 0 is an Xdata object)
        MsgBox "Invalid Object type passed in.", , "Error"
        Err.Clear
    Else
        Dim TempOrigObj As New Xdata
        TempOrigObj.GetXdata OriginalObject, ""         ' store the entity or group
        Dim LngI As Long
        If Not IsEmpty(TempOrigObj.XdataType) Then      ' do we have xdata to work with on the original object?
            ' now process the xdata - if any
            If Not IsEmpty(MasterObject.XdataType) Then ' any new xdata loaded on the masterobject?
                RegisterApps MasterObject               ' register all apps
                If Appname = "" Then                    ' replace all apps?
                    PlaceXdata OriginalObject, MasterObject
                    result = True
                Else                                    ' just replace one app
                    Dim TempXdataObj As New Xdata
                    Dim TargetXdataType() As Variant, TargetXdataValue() As Variant
                    If MasterObject.AppExist(Appname) Then
                        ' first find the application in the masterobject that was requested
                        ' and place it into an xdata object by itself
                        TempXdataObj.GetXdata MasterObject, Appname
                        ' next spin through the original object's xdata and place each into
                        ' a temp xdata object (except the requested app name data)
                        Dim lngK As Long
                        Dim ChildTempOrigObj As New Xdata
                        For LngI = 1 To TempOrigObj.AppNames.Count
                            ' next put all of the temp xdata into a target array
                            Set ChildTempOrigObj = Nothing      ' clear it each time
                            If TempOrigObj.AppNames(LngI) = Appname Then
                            Else
                                ChildTempOrigObj.GetXdata TempOrigObj, TempOrigObj.AppNames(LngI)
                                AddArrays TargetXdataType, ChildTempOrigObj.XdataType
                                AddArrays TargetXdataValue, ChildTempOrigObj.XdataValue
                            End If
                        Next LngI
                        ' when the target arrays are built (both type and value)
                        ' add the masterobject xdata type & value arrays to
                        ' the target arrays
                        AddArrays TargetXdataType, TempXdataObj.XdataType
                        AddArrays TargetXdataValue, TempXdataObj.XdataValue
                        Dim NewMasterObj As New Xdata
                        NewMasterObj.XdataType = TargetXdataType
                        NewMasterObj.XdataValue = TargetXdataValue
                        ' Now set the xdata on the entity using the target arrays
                        PlaceXdata OriginalObject, NewMasterObj
                        result = True
                    Else
                        MsgBox "Could not find " & Appname & " application in the MasterObject." & _
                               "No Xdata set.", , "Error"
                    End If
                End If
            Else
                MsgBox "No Xdata in the MasterObject for placement.", , "Error"
            End If
        Else
            ' no xdata on the original object so just add the new xdata
            RegisterApps MasterObject                   ' always register the apps first
            PlaceXdata OriginalObject, MasterObject     ' set the xdata on the object
            result = True
        End If
    End If
    SetXdata = result
End Function
Public Function GetXdata(object As Object, Appname) As Boolean
' This method is exposed to the user and is used to take
' the entity or group object and the appname
' and retrieves (and loads) the xdata from the object into the xdata object
' when appname = "" then all applications are retrieved and loaded from the object
    Dim result As Boolean
    Dim lngEtype As Long
    On Error Resume Next
    lngEtype = object.EntityType
    If Err.Number > 0 Then
        MsgBox "Invalid Object type passed in.", , "Error"
        Err.Clear
    Else
        RetrieveXdata object, Appname           ' go get the data
        ' now process the xdata - if any
        If Not IsEmpty(XdataType) Then          ' any xdata loaded?
            result = True                       ' return xdata found flag
            StoreAppNames Appname               ' stores the appname in the xdata objects appnames collection
            ItemsCount = UBound(XdataValue)     ' store the number of items in the xdata in the xdata objects itemscount property
            List                                ' builds the two dimensional array (aryxdata) property from the xdata in the object and optionally lists it out
        End If
    End If
    GetXdata = result
End Function
Public Sub StoreAppNames(Optional Appname As Variant)
' now that the xdata is loaded into the xdatatype
' extract application names into the names collection
    If IsMissing(Appname) Then
        Appname = ""
    End If
    If Appname = "" Then
        Dim LngI As Long
        On Error Resume Next
        LngI = LBound(XdataType)
        If Err.Number = 0 Then
            For LngI = LBound(XdataType) To UBound(XdataType)
                Select Case XdataType(LngI)
                    Case 1001
                        AppNames.Add XdataValue(LngI), XdataValue(LngI)
                    Case Else
                End Select
            Next LngI
        Else
            MsgBox "Unsucessful. Xdata not present.", , "Error"
        End If
    Else                    ' just requested one app so store it
        AppNames.Add Appname, Appname
    End If
End Sub
Private Sub RegisterApps(MasterObject As Xdata)
' toolbox function to register all apps in the xdata object
    Dim LngI As Long
    ' make sure all appnames in the master object are registered
    ' if not, register them before proceeding
    For LngI = 1 To MasterObject.AppNames.Count
        On Error Resume Next
        With ThisDrawing
            .RegisteredApplications.Item (MasterObject.AppNames.Item(LngI))
            If Err.Number > 0 Then      ' wasn't there so add it
                .RegisteredApplications.Add MasterObject.AppNames.Item(LngI)
                Err.Clear
            End If
        End With
    Next LngI
End Sub
Private Sub PlaceXdata(OriginalObject As Object, MasterObject As Xdata)
' put the xdata onto the entity or group
    On Error GoTo errorhandler
    Dim aryXdataType() As Integer, aryXdataValue() As Variant
    Dim lngX As Long
    ' load the arrays from the masterobject
    For lngX = LBound(MasterObject.XdataType) To UBound(MasterObject.XdataType)
        ReDim Preserve aryXdataType(lngX)
        ReDim Preserve aryXdataValue(lngX)
        aryXdataType(lngX) = CInt(MasterObject.XdataType(lngX))
        aryXdataValue(lngX) = MasterObject.XdataValue(lngX)
    Next lngX
    Select Case OriginalObject.EntityType
        Case acArc
            Dim cadArc As New AcadArc
            Set cadArc = OriginalObject
            cadArc.SetXdata MasterObject.XdataType, MasterObject.XdataValue
        Case acCircle
            Dim cadCircle As New AcadCircle
            Set cadCircle = OriginalObject
            cadCircle.SetXdata MasterObject.XdataType, MasterObject.XdataValue
        Case acEllipse
            Dim cadEllipse As New AcadEllipse
            Set cadEllipse = OriginalObject
            cadEllipse.SetXdata MasterObject.XdataType, MasterObject.XdataValue
        Case acLine
            Dim cadLine As New AcadLine
            Set cadLine = OriginalObject
            cadLine.SetXdata MasterObject.XdataType, MasterObject.XdataValue
        Case acPoint
            Dim cadPoint As New AcadPoint
            Set cadPoint = OriginalObject
            cadPoint.SetXdata MasterObject.XdataType, MasterObject.XdataValue
        Case acRay
            Dim cadray As New AcadRay
            Set cadray = OriginalObject
            cadray.SetXdata MasterObject.XdataType, MasterObject.XdataValue
        Case ac3dFace
            Dim cad3dface As New Acad3DFace
            Set cad3dface = OriginalObject
            cad3dface.SetXdata MasterObject.XdataType, MasterObject.XdataValue
        Case ac3dPolyline
            Dim cad3dpolyline As New Acad3DPolyline
            Set cad3dpolyline = OriginalObject
            cad3dpolyline.SetXdata MasterObject.XdataType, MasterObject.XdataValue
        Case ac3dSolid
            Dim cad3dsolid As New Acad3DSolid
            Set cad3dsolid = OriginalObject
            cad3dsolid.SetXdata MasterObject.XdataType, MasterObject.XdataValue
        Case acAttribute
            Dim cadAttribute As New AcadAttribute
            Set cadAttribute = OriginalObject
            cadAttribute.SetXdata MasterObject.XdataType, MasterObject.XdataValue
        Case acDimAligned
            Dim cadDimAligned As New AcadDimAligned
            Set cadDimAligned = OriginalObject
            cadDimAligned.SetXdata MasterObject.XdataType, MasterObject.XdataValue
        Case acDimAngular
            Dim cadDimAngular As New AcadDimAngular
            Set cadDimAngular = OriginalObject
            cadDimAngular.SetXdata MasterObject.XdataType, MasterObject.XdataValue
        Case acDimDiametric
            Dim cadDimDiametric As New AcadDimDiametric
            Set cadDimDiametric = OriginalObject
            cadDimDiametric.SetXdata MasterObject.XdataType, MasterObject.XdataValue
        Case acDimOrdinate
            Dim cadDimOrdinate As New AcadDimOrdinate
            Set cadDimOrdinate = OriginalObject
            cadDimOrdinate.SetXdata MasterObject.XdataType, MasterObject.XdataValue
        Case acDimRadial
            Dim cadDimRadial As New AcadDimRadial
            Set cadDimRadial = OriginalObject
            cadDimRadial.SetXdata MasterObject.XdataType, MasterObject.XdataValue
        Case acDimRotated
            Dim cadDimRotated As New AcadDimRotated
            Set cadDimRotated = OriginalObject
            cadDimRotated.SetXdata MasterObject.XdataType, MasterObject.XdataValue
        Case acGroup
            Dim cadGroup As New AcadGroup
            Set cadGroup = OriginalObject
            cadGroup.SetXdata MasterObject.XdataType, MasterObject.XdataValue
        Case acHatch
            Dim cadHatch As New AcadHatch
            Set cadHatch = OriginalObject
            cadHatch.SetXdata MasterObject.XdataType, MasterObject.XdataValue
        Case acLeader
            Dim cadLeader As New AcadLeader
            Set cadLeader = OriginalObject
            cadLeader.SetXdata MasterObject.XdataType, MasterObject.XdataValue
        Case acMtext
            Dim cadMtext As New AcadMtext
            Set cadMtext = OriginalObject
            cadMtext.SetXdata MasterObject.XdataType, MasterObject.XdataValue
        Case acPolyline
            Dim cadPolyline As New AcadPolyline
            Set cadPolyline = OriginalObject
            cadPolyline.SetXdata MasterObject.XdataType, MasterObject.XdataValue
        Case acPolylineLight
            Dim cadPoly As New AcadLWPolyline
            Set cadPoly = OriginalObject
            cadPoly.SetXdata aryXdataType, aryXdataValue
        Case acPolymesh
            Dim cadPolyMesh As New AcadPolygonMesh
            Set cadPolyMesh = OriginalObject
            cadPolyMesh.SetXdata MasterObject.XdataType, MasterObject.XdataValue
        Case acRaster
            Dim cadRaster As New AcadRasterImage
            Set cadRaster = OriginalObject
            cadRaster.SetXdata MasterObject.XdataType, MasterObject.XdataValue
        Case acRegion
            Dim cadRegion As New AcadRegion
            Set cadRegion = OriginalObject
            cadRegion.SetXdata MasterObject.XdataType, MasterObject.XdataValue
        Case acShape
            Dim cadShape As New AcadShape
            Set cadShape = OriginalObject
            cadShape.SetXdata MasterObject.XdataType, MasterObject.XdataValue
        Case acSolid
            Dim cadSolid As New AcadSolid
            Set cadSolid = OriginalObject
            cadSolid.SetXdata MasterObject.XdataType, MasterObject.XdataValue
        Case acSpline
            Dim cadSpline As New AcadSpline
            Set cadSpline = OriginalObject
            cadSpline.SetXdata MasterObject.XdataType, MasterObject.XdataValue
        Case acText
            Dim cadText As New AcadText
            Set cadText = OriginalObject
            cadText.SetXdata MasterObject.XdataType, MasterObject.XdataValue
        Case acTolerance
            Dim cadTolerance As New AcadTolerance
            Set cadTolerance = OriginalObject
            cadTolerance.SetXdata MasterObject.XdataType, MasterObject.XdataValue
        Case acTrace
            Dim cadTrace As New AcadTrace
            Set cadTrace = OriginalObject
            cadTrace.SetXdata MasterObject.XdataType, MasterObject.XdataValue
        Case acXline
            Dim cadXline As New AcadXline
            Set cadXline = OriginalObject
            cadXline.SetXdata MasterObject.XdataType, MasterObject.XdataValue
    End Select
exitsub:
    Exit Sub
errorhandler:
    MsgBox Err.Number & vbTab & Err.Description & " in PlaceXdata", , "Error"
End Sub
Private Sub Retrievedata(Xobject As Xdata, LngI As Long)
    Dim lngK As Long, cnt As Long
    Dim tempXdataType() As Variant, tempXdataValue() As Variant
    With Xobject
        lngK = LngI
        cnt = 0
        On Error GoTo errorhandler
        Dim Trigger As Boolean
        Trigger = True
        Do While Trigger
            ReDim Preserve tempXdataType(cnt)
            ReDim Preserve tempXdataValue(cnt)
            tempXdataType(cnt) = .XdataType(lngK)
            tempXdataValue(cnt) = .XdataValue(lngK)
            cnt = cnt + 1
            lngK = lngK + 1
            On Error Resume Next
            Dim lngCode As Long
            lngCode = .XdataType(lngK)
            If Err.Number > 0 Then
                Trigger = False
                Err.Clear
            Else
                If lngCode = 1001 Then
                    Trigger = False
                End If
            End If
            'Debug.Print tempXdataValue(cnt - 1)
        Loop
    End With
    XdataType = tempXdataType
    XdataValue = tempXdataValue

exitsub:
    Exit Sub
errorhandler:
    MsgBox Err.Number & vbTab & Err.Description & " in RetrieveXdata", , "Error"
End Sub

Private Sub RetrieveXdata(object As Object, Appname, Optional Mode As Boolean)
     Select Case object.EntityType
        Case acArc
            Dim cadArc As New AcadArc
            Set cadArc = object
            cadArc.GetXdata Appname, XdataType, XdataValue
        Case acCircle
            Dim cadCircle As New AcadCircle
            Set cadCircle = object
            cadCircle.GetXdata Appname, XdataType, XdataValue
        Case acEllipse
            Dim cadEllipse As New AcadEllipse
            Set cadEllipse = object
            cadEllipse.GetXdata Appname, XdataType, XdataValue
        Case acLine
            Dim cadLine As New AcadLine
            Set cadLine = object
            cadLine.GetXdata Appname, XdataType, XdataValue
        Case acPoint
            Dim cadPoint As New AcadPoint
            Set cadPoint = object
            cadPoint.GetXdata Appname, XdataType, XdataValue
        Case acRay
            Dim cadray As New AcadRay
            Set cadray = object
            cadray.GetXdata Appname, XdataType, XdataValue
        Case ac3dFace
            Dim cad3dface As New Acad3DFace
            Set cad3dface = object
            cad3dface.GetXdata Appname, XdataType, XdataValue
        Case ac3dPolyline
            Dim cad3dpolyline As New Acad3DPolyline
            Set cad3dpolyline = object
            cad3dpolyline.GetXdata Appname, XdataType, XdataValue
        Case ac3dSolid
            Dim cad3dsolid As New Acad3DSolid
            Set cad3dsolid = object
            cad3dsolid.GetXdata Appname, XdataType, XdataValue
        Case acAttribute
            Dim cadAttribute As New AcadAttribute
            Set cadAttribute = object
            cadAttribute.GetXdata Appname, XdataType, XdataValue
        Case acDimAligned
            Dim cadDimAligned As New AcadDimAligned
            Set cadDimAligned = object
            cadDimAligned.GetXdata Appname, XdataType, XdataValue
        Case acDimAngular
            Dim cadDimAngular As New AcadDimAngular
            Set cadDimAngular = object
            cadDimAngular.GetXdata Appname, XdataType, XdataValue
        Case acDimDiametric
            Dim cadDimDiametric As New AcadDimDiametric
            Set cadDimDiametric = object
            cadDimDiametric.GetXdata Appname, XdataType, XdataValue
        Case acDimOrdinate
            Dim cadDimOrdinate As New AcadDimOrdinate
            Set cadDimOrdinate = object
            cadDimOrdinate.GetXdata Appname, XdataType, XdataValue
        Case acDimRadial
            Dim cadDimRadial As New AcadDimRadial
            Set cadDimRadial = object
            cadDimRadial.GetXdata Appname, XdataType, XdataValue
        Case acDimRotated
            Dim cadDimRotated As New AcadDimRotated
            Set cadDimRotated = object
            cadDimRotated.GetXdata Appname, XdataType, XdataValue
        Case acGroup
            Dim cadGroup As New AcadGroup
            Set cadGroup = object
            cadGroup.GetXdata Appname, XdataType, XdataValue
        Case acHatch
            Dim cadHatch As New AcadHatch
            Set cadHatch = object
            cadHatch.GetXdata Appname, XdataType, XdataValue
        Case acLeader
            Dim cadLeader As New AcadLeader
            Set cadLeader = object
            cadLeader.GetXdata Appname, XdataType, XdataValue
        Case acMtext
            Dim cadMtext As New AcadMtext
            Set cadMtext = object
            cadMtext.GetXdata Appname, XdataType, XdataValue
        Case acPolyline
            Dim cadPolyline As New AcadPolyline
            Set cadPolyline = object
            cadPolyline.GetXdata Appname, XdataType, XdataValue
        Case acPolylineLight
            Dim cadPoly As New AcadLWPolyline
            Set cadPoly = object
            cadPoly.GetXdata Appname, XdataType, XdataValue
        Case acPolymesh
            Dim cadPolyMesh As New AcadPolygonMesh
            Set cadPolyMesh = object
            cadPolyMesh.GetXdata Appname, XdataType, XdataValue
        Case acRaster
            Dim cadRaster As New AcadRasterImage
            Set cadRaster = object
            cadRaster.GetXdata Appname, XdataType, XdataValue
        Case acRegion
            Dim cadRegion As New AcadRegion
            Set cadRegion = object
            cadRegion.GetXdata Appname, XdataType, XdataValue
        Case acShape
            Dim cadShape As New AcadShape
            Set cadShape = object
            cadShape.GetXdata Appname, XdataType, XdataValue
        Case acSolid
            Dim cadSolid As New AcadSolid
            Set cadSolid = object
            cadSolid.GetXdata Appname, XdataType, XdataValue
        Case acSpline
            Dim cadSpline As New AcadSpline
            Set cadSpline = object
            cadSpline.GetXdata Appname, XdataType, XdataValue
        Case acText
            Dim cadText As New AcadText
            Set cadText = object
            cadText.GetXdata Appname, XdataType, XdataValue
        Case acTolerance
            Dim cadTolerance As New AcadTolerance
            Set cadTolerance = object
            cadTolerance.GetXdata Appname, XdataType, XdataValue
        Case acTrace
            Dim cadTrace As New AcadTrace
            Set cadTrace = object
            cadTrace.GetXdata Appname, XdataType, XdataValue
        Case acXline
            Dim cadXline As New AcadXline
            Set cadXline = object
            cadXline.GetXdata Appname, XdataType, XdataValue
        Case Else
            ' must be an xdata object since no matching acad entitytype
            Dim newXdataObj As New Xdata
            Set newXdataObj = object
            With newXdataObj
                Dim LngI As Long
                For LngI = LBound(.XdataType) To UBound(.XdataType)
                    ' first find the requested application xdata
                    On Error GoTo errorhandler
                    If .XdataType(LngI) = 1001 Then
                        If IsMissing(Mode) Then
                            If .XdataValue(LngI) = Appname Then
                            Else                                ' all apps except the requested one
                                Retrievedata newXdataObj, LngI
                                Exit For
                            End If
                        Else
                            If .XdataValue(LngI) = Appname Then
                                Retrievedata newXdataObj, LngI    ' only the requested app
                                Exit For
                            End If
                        End If
                    End If
                Next LngI
            End With
    End Select
    
exitsub:
    Exit Sub
errorhandler:
    MsgBox Err.Number & vbTab & Err.Description & " in RetrieveXdata", , "Error"
End Sub
Private Function parse(strLine As String, strDelimit As String, lngPosition As Long) As String
' this function takes the
'                                    position    position   position
'                                       1            2         3
' strLine holds the string  ie. "All good | men are | leaving the boat."
'                                              ^
'                                           boundary
' strdelimit is a one character string containing the delimiter to be used
' tempvar is returned
' lngPosition is what information position in the string you want
' Lpipe and Rpipe are the boundaries around the data

    Dim c As Long
    Dim Lpipe As Long
    Dim Rpipe As Long
    Dim mark As Long
    Dim tempvar As String
    Dim start As Long
    Dim datalen As Long
    Dim cnt As Long
    c = 1
    Lpipe = 0
    mark = 1
    tempvar = ""
    For cnt = 1 To lngPosition
        Do While Mid(strLine, c, 1) <> strDelimit And Len(strLine) >= c
            c = c + 1
        Loop
        Rpipe = c
        If mark = lngPosition - 1 Then
            Lpipe = c
        End If
        c = c + 1
        mark = mark + 1
    Next cnt
    start = Lpipe + 1
    datalen = (Rpipe - Lpipe) - 1
    parse = Mid(strLine, start, datalen)
End Function
Private Sub AddArrays(OriginalArray As Variant, AdditionalArray As Variant)
' toolbox function takes and adds the additionalarray to the original array
    Dim cnt As Long, LngI As Long
    On Error Resume Next
    cnt = UBound(OriginalArray) + 1
    If Err.Number > 0 Then
        cnt = 0
    End If
    For LngI = 0 To UBound(AdditionalArray)
        ReDim Preserve OriginalArray(cnt)
        OriginalArray(cnt) = AdditionalArray(LngI)
        cnt = cnt + 1
    Next LngI
End Sub

Attribute VB_Name = "frmXdataView"
Attribute VB_Base = "0{B6697DEB-C448-11D2-99DA-BE2967000000}{B6697DE1-C448-11D2-99DA-BE2967000000}"
Attribute VB_Creatable = False
Attribute VB_PredeclaredId = True
Attribute VB_Exposed = False
Attribute VB_TemplateDerived = False
Attribute VB_Customizable = False
Option Explicit

Private Sub btnDone_Click()
    Unload Me
    End
End Sub

Private Sub rdCode_Click()
    lstXdata.ColumnWidths = "40pt,40pt"
End Sub

Private Sub rdData_Click()
    lstXdata.ColumnWidths = "0pt,1pt"
End Sub


Private Sub UserForm_Initialize()
    Me.rdCode = True
End Sub
