Attribute VB_Name = "SaveAsR12"
Attribute VB_Base = "0{D7440334-C869-11D2-89E9-00805F88D716}{D7440322-C869-11D2-89E9-00805F88D716}"
Attribute VB_Creatable = False
Attribute VB_PredeclaredId = True
Attribute VB_Exposed = False
Attribute VB_TemplateDerived = False
Attribute VB_Customizable = False
'      AutoCAD 2000
'
'      SaveASR12 VBA sample Using Migration Assistance Convert Program
'      ActiveX Automation and VBA Samples.
'
'      Copyright (C) 1999 by Autodesk, Inc.
'
'      Permission to use, copy, modify, and distribute this software
'      for any purpose and without fee is hereby granted, provided
'      that the above copyright notice appears in all copies and
'      that both that copyright notice and the limited warranty and
'      restricted rights notice below appear in all supporting
'      documentation.
'
'      AUTODESK PROVIDES THIS PROGRAM "AS IS" AND WITH ALL FAULTS.
'      AUTODESK SPECIFICALLY DISCLAIMS ANY IMPLIED WARRANTY OF
'      MERCHANTABILITY OR FITNESS FOR A PARTICULAR USE.  AUTODESK, INC.
'      DOES NOT WARRANT THAT THE OPERATION OF THE PROGRAM WILL BE
'      UNINTERRUPTED OR ERROR FREE.
'
'      Use, duplication, or disclosure by the U.S. Government is subject to
'      restrictions set forth in FAR 52.227-19 (Commercial Computer
'      Software - Restricted Rights) and DFAR 252.227-7013(c)(1)(ii)
'      (Rights in Technical Data and Computer Software), as applicable.
'
Option Compare Text
Option Explicit
Dim OemAppObj As Object
Dim DirName As String
Dim DestDirName As String
Dim Flag As Boolean

Private Sub CmdBatch_Click()

End Sub

Private Sub CmdBrowse_Click()
Dim StrFile As String
On Error Resume Next
LstFiles.Clear
DirName = CStr(Trim(TxtDir.Text))
If DirName = "" Then Exit Sub
If Right(DirName, 1) <> "\" Then
    DirName = DirName & "\"
End If
Dir DirName & "*.dwg"
StrFile = Dir
If StrFile = "" Then
    Exit Sub
End If
Do
LstFiles.AddItem StrFile
StrFile = Dir
Loop While StrFile <> ""
End Sub

Private Sub CmdClose_Click()
OemAppObj.Quit
Unload SaveAsR12
End
End Sub

Private Sub CmdSave_Click()
Dim i As Integer
Dim FileName As String
Dim TempFiles() As String

If TxtDest.Text = "" Then
    MsgBox "Enter the Destination Directory", vbOKOnly, "SaveAsR12"
    Exit Sub
Else
    DestDirName = TxtDest.Text
End If
If Right(DestDirName, 1) <> "\" Then
    DestDirName = DestDirName & "\"
End If
SaveAsR12.MousePointer = fmMousePointerHourGlass
    If Not Flag Then
        AcadApplication.Documents.Add ""
        AcadApplication.ActiveDocument.SaveAs DestDirName & "TempSaveAsR14", acR14_dwg
        AcadApplication.ActiveDocument.Close False
        Flag = True
    End If
For i = 0 To LstFiles.ListCount - 1
    If LstFiles.Selected(i) = True Then
        FileName = DestDirName & LstFiles.List(i)
        FileName = Mid(FileName, 1, Len(FileName) - 4)
        AcadApplication.Documents.Open DirName & LstFiles.List(i), True
        AcadApplication.ActiveDocument.SaveAs FileName & "14", acR14_dwg
        AcadApplication.ActiveDocument.Close False
        OemAppObj.ShutProxyDialog True
        OemAppObj.SetQAFLAGS 6
        OemAppObj.Open FileName & "14.dwg"
        OemAppObj.SaveAsR12 FileName
        OemAppObj.Open DestDirName & "TempSaveAsR14.dwg"
        Kill FileName & "14.dwg"
    End If
Next i
SaveAsR12.MousePointer = fmMousePointerDefault
End Sub

Private Sub UserForm_Initialize()
On Error Resume Next

Set OemAppObj = GetObject(, "convert.application")
If OemAppObj Is Nothing Then
    Err.Clear
    On Error GoTo NoOEM
    Set OemAppObj = CreateObject("convert.application")
End If

On Error Resume Next

OemAppObj.Visible = True
AppActivate ("AutoCAD")
Flag = False
Call CheckFonts

Dim strRtn As String

strRtn = Left$(ThisDrawing.Application.FullName, Len(ThisDrawing.Application.FullName) - 8)
SaveAsR12.TxtDir.Text = strRtn & "Sample"

Exit Sub

NoOEM:
MsgBox "The Convert Application needed for SaveAsR12 to work was not Installed," & Chr(13) & Chr(10) & "Please Refer to the ReadME file, and Install Migration Assistance for SaveAsR12 to run correctly.", vbCritical
OemAppObj.Quit
Unload SaveAsR12

End Sub

Private Sub UserForm_QueryClose(Cancel As Integer, CloseMode As Integer)
On Error Resume Next
OemAppObj.Quit
Kill DestDirName & "TempSaveAsR14.dwg"
End Sub

Private Sub CheckFonts()

Dim strFontName As String
Dim strConvertDir As String
Dim strRtn As String

Dim vR14Fonts As Variant

vR14Fonts = Array("bigfont.shx", "complex.shx", "gothice.shx", "gothicg.shx", _
                  "gothici.shx", "greekc.shx", "greeks.shx", "gdt.shx", "isocp.shx", _
                  "isocp2.shx", "isocp3.shx", "isoct.shx", "isoct2.shx", "isoct3.shx", _
                  "italic.shx", "italicc.shx", "italict.shx", "ltypeshp.shx", "monotxt.shx", _
                  "romanc.shx", "romand.shx", "romans.shx", "romant.shx", "scriptc.shx", _
                  "scripts.shx", "simplex.shx", "syastro.shx", "symap.shx", "symath.shx", _
                  "symeteo.shx", "symusic.shx", "txt.shx")
                  
strRtn = Left$(ThisDrawing.Application.FullName, Len(ThisDrawing.Application.FullName) - 8)
strConvertDir = strRtn & "Migration\Convert\Support\"

Dim i As Integer
Dim j As Integer
j = 0
For i = LBound(vR14Fonts) To UBound(vR14Fonts)

   strFontName = strConvertDir & vR14Fonts(i)

   strRtn = Dir(strFontName)
   
   If (StrComp(strRtn, "") = 0) And (j < 5) Then
      MsgBox "R14 Font: " & StrConv(vR14Fonts(i), vbUpperCase) & Chr(13) & Chr(10) & " was NOT found in the Convert Application Support Directory," & Chr(13) & Chr(10) & " Please place a copy there, for Convert To Function Properly.", vbCritical
      j = j + 1
   End If
   
   If j > 4 Then
      MsgBox "Exiting SaveAsR12, more than 5 R14 fonts were not found in the .\Migration\Convert\Support Directory" & Chr(13) & Chr(10) & " Please check the Convert.Txt ReadMe file, and copy ALL R14 SHX fonts to the Convert Support Directory " & Chr(13) & Chr(10) & " for SaveAsR12 to function correctly.", vbCritical
      OemAppObj.Quit
      Unload SaveAsR12
      End
   End If
 Next

End Sub

Attribute VB_Name = "ThisDrawing"
Attribute VB_Base = "0{8E75D913-3D21-11D2-85C4-080009A0C626}"
Attribute VB_Creatable = False
Attribute VB_PredeclaredId = True
Attribute VB_Exposed = True
Attribute VB_TemplateDerived = False
Attribute VB_Customizable = True
'      AutoCAD 2000
'
'      SaveASR12 VBA sample Using Migration Assistance Convert Program
'      ActiveX Automation and VBA Samples.
'
'      Copyright (C) 1999 by Autodesk, Inc.
'
'      Permission to use, copy, modify, and distribute this software
'      for any purpose and without fee is hereby granted, provided
'      that the above copyright notice appears in all copies and
'      that both that copyright notice and the limited warranty and
'      restricted rights notice below appear in all supporting
'      documentation.
'
'      AUTODESK PROVIDES THIS PROGRAM "AS IS" AND WITH ALL FAULTS.
'      AUTODESK SPECIFICALLY DISCLAIMS ANY IMPLIED WARRANTY OF
'      MERCHANTABILITY OR FITNESS FOR A PARTICULAR USE.  AUTODESK, INC.
'      DOES NOT WARRANT THAT THE OPERATION OF THE PROGRAM WILL BE
'      UNINTERRUPTED OR ERROR FREE.
'
'      Use, duplication, or disclosure by the U.S. Government is subject to
'      restrictions set forth in FAR 52.227-19 (Commercial Computer
'      Software - Restricted Rights) and DFAR 252.227-7013(c)(1)(ii)
'      (Rights in Technical Data and Computer Software), as applicable.
'
Option Explicit

Sub Sample_SaveAsR12()
SaveAsR12.Show
End Sub
