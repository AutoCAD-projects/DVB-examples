Attribute VB_Name = "Module1"
Option Explicit

Public Sub ShowEmp(name As String, age As Integer, bdate As Date, Optional height As Integer)

    Stop
    Debug.Print name & vbCr & age & vbCr & bdate & vbCr & height

End Sub
' ShowEmp "My Name", 22, #2/3/76#
' Call ShowEmp (bDate:=#2/3/76#, Name:="My Name", Age:=22)
' Call ShowEmp ("My Name", 22, #2/3/76#, 72)
