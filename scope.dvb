Attribute VB_Name = "Module1"
Option Explicit
Public D
Private A
Private C

Public Sub Three()
    Stop
    A = 4
    'B = 8
    C = 6
    D = 11

End Sub
Public Sub four()
    Static A
    Stop
    A = A + 12
    'B = 55

End Sub

Attribute VB_Name = "Scope"
Attribute VB_Base = "0{598BC850-C74C-11D1-99CA-00609761BD90}{598BC6BD-C74C-11D1-99CA-00609761BD90}"
Attribute VB_Creatable = False
Attribute VB_PredeclaredId = True
Attribute VB_Exposed = False
Attribute VB_TemplateDerived = False
Attribute VB_Customizable = False
Option Explicit
Public A
Private B
Private Const D = 33

Private Sub btnCancel_Click()
    Unload Me
End Sub

Private Sub btnOK_Click()
    Unload Me
End Sub

Private Sub UserForm_Initialize()
End Sub

Private Sub btnOne_Click()
    Stop
    A = 3
    B = 4

End Sub
Private Sub btnTwo_Click()
    Stop
    A = 20
    B = 7
    C = 5
    D = 6


End Sub

Private Sub btnThree_Click()
    Three
    
End Sub
Private Sub btnFour_Click()
    
    four
    
End Sub
