Attribute VB_Name = "Module1"
'
'  ad_DwgDate
'
'  This routine inserts the current system date into the 'ad_DwgDate'
'    block on each layout of the current drawing. It uses the form
'    mm/dd/yy and is setup for paperspace.
'  Demand load:  -vbarun;ad_DwgDate.dvb!ad_DwgDate;
'
'  version 1.00
'  7/22/2000
'
'  Copyright©2000 ActiveDwg.com
'
'  This routine is provided for demonstration purposes only and must
'    not be used for critical applications without your verification
'    that this routine will perform as you intended.
'  This routine may be freely utilized for your own personal use so long
'    as the entire contents of this header remain intact.
'  This routine is provided "as-is" and no declaration, written or implied,
'    is made as to its reliability for any particular task. Any use of this
'    routine is solely at your own risk.
'
Option Explicit

Public Sub ad_DwgDate()
    Dim DwgDate As Variant
    Dim DwgStr As Variant
    Dim PlotLayout As AcadLayout
    Dim CurrLayout As AcadLayout
    Dim PlotLayouts As AcadLayouts
    Dim ent As Object
    Dim BlockObjAttributes As Variant
    
    DwgDate = Date
    DwgStr = Format(DwgDate, "SHORT DATE")
    Set PlotLayouts = ThisDrawing.Layouts
    Set CurrLayout = ThisDrawing.ActiveLayout
    For Each PlotLayout In PlotLayouts
        ThisDrawing.ActiveLayout = PlotLayout
        If ThisDrawing.ActiveSpace = acPaperSpace Then
            For Each ent In ThisDrawing.PaperSpace
              If ent.EntityName = "AcDbBlockReference" Then
                If ent.Name = "ad_DwgDate" Then
                    BlockObjAttributes = ent.GetAttributes
                    BlockObjAttributes(0).TextString = DwgStr
                End If
              End If
            Next ent
        End If
    Next PlotLayout
    ThisDrawing.ActiveLayout = CurrLayout
End Sub
