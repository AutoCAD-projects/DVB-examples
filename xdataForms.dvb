Attribute VB_Name = "Module1"
Option Explicit

Public Ent As Object

Public Sub GetEnt(Ent As Object, Pnt As Variant)
' This subroutine waits for input from user
    On Error Resume Next
   
    ' The following example
Retry:
'    Dim Ent As Object
    
    ThisDrawing.Utility.GetEntity Ent, Pnt, "Select an object: "
    
    If Err <> 0 Then
        Err.Clear
        MsgBox "You need to select an existing object"
        GoTo Retry
    End If
    
End Sub
Public Sub Blink(cnt As Long, FrmCtrl As Control, message As String)
    If cnt > 0 Then
        Dim x As Long
        Dim y As Long
        For x = 1 To cnt
            FrmCtrl.Caption = message
            For y = 1 To 1000
                DoEvents
                FrmCtrl.Caption = CStr(y)
            Next y
        Next x
    End If
End Sub

Attribute VB_Name = "frmGroupNames"
Attribute VB_Base = "0{9BA4C514-D7EF-11D1-99D7-00609761BD90}{9BA4C508-D7EF-11D1-99D7-00609761BD90}"
Attribute VB_Creatable = False
Attribute VB_PredeclaredId = True
Attribute VB_Exposed = False
Attribute VB_TemplateDerived = False
Attribute VB_Customizable = False
Option Explicit

Private Sub btnCancel_Click()
    Unload Me
End Sub

Private Sub btnOK_Click()
    Me.Hide
End Sub

Attribute VB_Name = "frmXdata"
Attribute VB_Base = "0{9BA4C57C-D7EF-11D1-99D7-00609761BD90}{9BA4C500-D7EF-11D1-99D7-00609761BD90}"
Attribute VB_Creatable = False
Attribute VB_PredeclaredId = True
Attribute VB_Exposed = False
Attribute VB_TemplateDerived = False
Attribute VB_Customizable = False
Option Explicit



Private Sub btnExecute_Click()
    If Len(edAppName.Text) > 0 Then
        Dim regApp As AcadRegisteredApplication
        Set regApp = ThisDrawing.RegisteredApplications.Add(edAppName)
        If Len(edData.Text) > 0 Then
            ' check radio buttons here for data types (rdstring etc)
            Dim dType As Integer
            dType = 1000             ' hard line for testing
            dType = UCase(dType)
            Select Case dType
                Case dType = 1000
                    dType = 1000
                Case Else
                    dType = 1000       ' default type is string
            End Select
            ' attached it
            Dim dataType(0 To 1) As Integer
            Dim data(0 To 1) As Variant
'            Dim reals3(0 To 2) As Double
'            Dim worldPos(0 To 2) As Double
            ' Initialize all the xdata value. Note that first data in the list should be
            ' application name and first datatype code should be 1001
            dataType(0) = 1001: data(0) = edAppName
            dataType(1) = 1000: data(1) = edData.Text

            'dataType(2) = 1003: data(2) = "0"               ' layer
            '    dataType(3) = 1040: data(3) = 1.23479137438413E+40          ' real
            '    dataType(4) = 1041: data(4) = 1237324938            ' distance
            '   dataType(5) = 1070: data(5) = 32767                 ' 16 bit Integer
            '   dataType(6) = 1071: data(6) = 32767                 ' 32 bit Integer
            '   dataType(7) = 1042: data(7) = 10                ' scaleFactor

            'reals3(0) = -2.95: reals3(1) = 100: reals3(2) = -20
            '    dataType(8) = 1010: data(8) = reals3                ' real
            '    worldPos(0) = 4: worldPos(1) = 400.99999999: worldPos(2) = 2.798989
            '    dataType(9) = 1011: data(9) = worldPos          ' world space position
            ' The following code attaches xdata to an object
            Ent.SetXData dataType, data

        Else
            MsgBox "No data to store."
        End If
    Else
        MsgBox "Application name must be filled out"
    End If
End Sub

Private Sub btnOK_Click()
    End
End Sub

Private Sub btnSelectGroup_Click()
    lbMessage.Caption = ""
    ' are there any groups in the drawing?
    If ThisDrawing.groups.Count <> 0 Then
        ' get all of their names into a collection for processing
        Dim GroupNames As New Collection
        
        Dim group As AcadGroup
        Dim x As Long
        For x = 0 To ThisDrawing.groups.Count - 1
            Set group = ThisDrawing.groups.Item(x)
            GroupNames.Add group.Name
        Next x
        
        ' now show the group names and get the one they want to use
        Call Show_Group_names(GroupNames)
        frmGroupNames.Show
        Dim groupname As Variant
        groupname = frmGroupNames.lstGroupNames.Value
        ' check if the groupname is null or has no text
        ' this bit of code is a little unusal but it works because the '&' takes a variant
        ' and a zero length string and adds them together to get a zero length string
        ' but if the variant has anything in it, that is added and the length is
        ' greater than zero.
        If Len(groupname & "") > 0 Then
            Set_Group_Name (groupname)
            ' now get any xdata attached to the requested group
' gather Xdata information from the object
            Dim appname As String
            Dim xdataType As Variant, xdataValue As Variant
            appname = ""
                    Set group = ThisDrawing.groups.Item(groupname)
            group.GetXData appname, xdataType, xdataValue  ' get the xdata from the object
            Dim lbnd As Integer, ubnd As Integer
            Dim i As Integer
            Dim arrayData As Variant
            Dim resultString As String
            If VarType(xdataType) > vbNull Then
                lbnd = LBound(xdataType)
                ubnd = UBound(xdataType)
                For i = lbnd To ubnd
                    If (xdataType(i) = 1010) Or (xdataType(i) = 1011) Or (xdataType(i) = 1012) Or (xdataType(i) = 1013) Then
                        arrayData = xdataValue(i)
                        resultString = resultString & "XData Type: " & xdataType(i) & "  Xdata Value: " & arrayData(0) & "," & arrayData(1) & "," & arrayData(2) & vbCr
                        lstEditData.AddItem arrayData(0)
                        lstEditData.AddItem arrayData(1)
                        lstEditData.AddItem arrayData(2)
                        
                    Else
                        resultString = resultString & "XData Type: " & xdataType(i) & "  Xdata Value: " & xdataValue(i) & vbCr
                        If xdataType(i) <> "1001" Then
                            lstEditData.AddItem xdataValue(i)
                        End If
                    End If
                Next
                MsgBox resultString
        ' now gather all of the application names in the xdata of the selected object
        '        Dim x As Long
                Dim cnt As Long
                cnt = 0
                Dim AppNames() As Variant
                For x = 0 To UBound(xdataType)
                    If xdataType(x) = "1001" Then
                        ReDim Preserve AppNames(cnt)
                        AppNames(cnt) = xdataValue(x)
                        cnt = cnt + 1
                    End If
                Next x
        ' now show the xdata application names in the approperiate fields
                Dim ArrayPointer As Variant
                ArrayPointer = AppNames
                Show_xdata (ArrayPointer)
            Else
                Clear_Fields
                ' no xdata found
        '        MsgBox "The selected object has no xdata attached."
                lbMessage.Caption = "The selected object has no xdata attached."
            End If
        Else
            Turn_off_object_fields
            'MsgBox "Groupname = " & groupname
        End If
'        Dim ArrayPointer As Variant
'        ArrayPointer = GroupNames
'        Show_xdata (ArrayPointer)
    Else
        MsgBox "No Groups present in this drawing."
    End If
    
End Sub
Private Sub btnSelectObject_Click()
    
    lbMessage.Caption = ""
    Me.Hide
    Dim Pnt As Variant
    Dim Ent As Object
    Call GetEnt(Ent, Pnt)
' now process the entity
    'Dim PntPointer As Variant   ' setup a variant pointer to the array to pass
    'PntPointer = Pnt
    'call show_xdata_msgbox(Ent, PntPointer)
    If Len(Ent.Handle & "") > 0 Then
        Set_Object_Name (Ent.Handle)
        ' now get any xdata attached to the requested group
    Else
        Turn_off_object_fields
        'MsgBox "Groupname = " & groupname
    End If
    ' check if the object has any xdata
' gather Xdata information from the object
    Dim appname As String
    Dim xdataType As Variant, xdataValue As Variant
    Ent.GetXData appname, xdataType, xdataValue  ' get the xdata from the object
    Dim aryXdata() As Variant
    ' put the two seperate array's data into a two dimensional array
    Dim inti, intj As Integer
    inti = UBound(xdataType)
    ReDim aryXdata(inti, 2)
    Dim i As Integer
    Dim arrayData As Variant
    For i = 0 To inti
        aryXdata(i, 0) = xdataType(i)
    Next i
    For i = 0 To inti
        If (xdataType(i) = 1010) Or (xdataType(i) = 1011) Or (xdataType(i) = 1012) Or (xdataType(i) = 1013) Then
            arrayData = xdataValue(i)
            aryXdata(i, 1) = arrayData(0) & "," & arrayData(1) & "," & arrayData(2)
        Else
            aryXdata(i, 1) = xdataValue(i)
        End If
    Next i
    Dim lbnd As Integer, ubnd As Integer
    Dim resultString As String
    lstEditData.List = aryXdata
    If VarType(xdataType) > vbNull Then
        lbnd = LBound(xdataType)
        ubnd = UBound(xdataType)
        For i = lbnd To ubnd
            If (xdataType(i) = 1010) Or (xdataType(i) = 1011) Or (xdataType(i) = 1012) Or (xdataType(i) = 1013) Then
                arrayData = xdataValue(i)
                resultString = resultString & "XData Type: " & xdataType(i) & "  Xdata Value: " & arrayData(0) & "," & arrayData(1) & "," & arrayData(2) & vbCr
'                lstEditData.AddItem arrayData(0)
'                lstEditData.AddItem arrayData(1)
'                lstEditData.AddItem arrayData(2)
            Else
                resultString = resultString & "XData Type: " & xdataType(i) & "  Xdata Value: " & xdataValue(i) & vbCr
'                If xdataType(i) <> "1001" Then
'                    lstEditData.AddItem xdataValue(i)
'                End If
            End If
        Next
       MsgBox resultString
' now gather all of the application names in the xdata of the selected object
        Dim x As Long
        Dim cnt As Long
        cnt = 0
        Dim AppNames() As Variant
        For x = 0 To UBound(xdataType)
            If xdataType(x) = "1001" Then
                ReDim Preserve AppNames(cnt)
                AppNames(cnt) = xdataValue(x)
                cnt = cnt + 1
            End If
        Next x
' now show the xdata application names in the approperiate fields
        Dim ArrayPointer As Variant
        ArrayPointer = AppNames
        Show_xdata (ArrayPointer)
    Else
        Clear_Fields
        ' no xdata found
'        MsgBox "The selected object has no xdata attached."
        lbMessage.Caption = "The selected object has no xdata attached."
    End If
    
    Me.Show
    
End Sub


Private Sub CommandButton2_Click()
            Dim dType As Integer
            dType = 1000             ' hard line for testing
            dType = UCase(dType)
            Select Case dType
                Case dType = 1000
                    dType = 1000
                Case Else
                    dType = 1000       ' default type is string
            End Select
            ' attached it
            Dim dataType(0 To 1) As Integer
            Dim data(0 To 1) As Variant
            Dim reals3(0 To 2) As Double
            Dim worldPos(0 To 2) As Double
            ' Initialize all the xdata value. Note that first data in the list should be
            ' application name and first datatype code should be 1001
            dataType(0) = 1001: data(0) = "test app"
            dataType(1) = 1000: data(1) = "a stinr"

            'dataType(2) = 1003: data(2) = "0"               ' layer
            '    dataType(3) = 1040: data(3) = 1.23479137438413E+40          ' real
            '    dataType(4) = 1041: data(4) = 1237324938            ' distance
            '   dataType(5) = 1070: data(5) = 32767                 ' 16 bit Integer
            '   dataType(6) = 1071: data(6) = 32767                 ' 32 bit Integer
            '   dataType(7) = 1042: data(7) = 10                ' scaleFactor

            reals3(0) = -2.95: reals3(1) = 100: reals3(2) = -20
            '    dataType(8) = 1010: data(8) = reals3                ' real
                worldPos(0) = 4: worldPos(1) = 400.99999999: worldPos(2) = 2.798989
            '    dataType(9) = 1011: data(9) = worldPos          ' world space position
            ' The following code attaches xdata to an object
    Me.Hide
    Dim Pnt As Variant
    Dim Ent As Object
    Call GetEnt(Ent, Pnt)
    Ent.SetXData dataType, data

End Sub

Private Sub frType_Click()
    lbMessage.Caption = ""

End Sub

Private Sub MultiPage1_Change()
    lbMessage.Caption = ""
End Sub

Private Sub UserForm_Initialize()
    rdString.Value = True
    Turn_off_object_fields

End Sub
Private Sub btnGetXData_Click()
' Creates a group named "TEST" in current drawing
    Dim group As AcadGroup
    Set group = ThisDrawing.groups.Add("TEST")  'create the group named TEST
  
    Dim anObj(1) As AcadLine
    Dim xdataType As Variant, xdataValue As Variant
    Dim appname As String
    ' The following code retrieves all the xdata of attached on an object
    ' Initialize anObj variable to any object that supports
    ' setxdata method.  This example creates 2 lines that are then added to a group
    Dim startpt(0 To 2) As Double, endpt(0 To 2) As Double
    startpt(0) = 0#: startpt(1) = 0#: startpt(2) = 0#
    endpt(0) = 5#: endpt(1) = 5#: endpt(2) = 0#
    Set anObj(0) = ThisDrawing.ModelSpace.AddLine(startpt, endpt)
    startpt(0) = 5#: startpt(1) = 0#: startpt(2) = 0#
    endpt(0) = 0#: endpt(1) = 5#: endpt(2) = 0#
    Set anObj(1) = ThisDrawing.ModelSpace.AddLine(startpt, endpt)
    
    group.AppendItems (anObj)  ' add the lines to the group TEST
    
Dim dataType(0 To 9) As Integer
    Dim data(0 To 9) As Variant
    Dim reals3(0 To 2) As Double
    Dim worldPos(0 To 2) As Double
    ' Initialize all the xdata value. Note that first data in the list should be
    ' application name and first datatype code should be 1001
    dataType(0) = 1001: data(0) = "TEST_APP"
    dataType(1) = 1000: data(1) = "This is a test for xdata"

dataType(2) = 1003: data(2) = "0"               ' layer
    dataType(3) = 1040: data(3) = 1.23479137438413E+40          ' real
    dataType(4) = 1041: data(4) = 1237324938            ' distance
    dataType(5) = 1070: data(5) = 32767                 ' 16 bit Integer
    dataType(6) = 1071: data(6) = 32767                 ' 32 bit Integer
    dataType(7) = 1042: data(7) = 10                ' scaleFactor

reals3(0) = -2.95: reals3(1) = 100: reals3(2) = -20
    dataType(8) = 1010: data(8) = reals3                ' real
    worldPos(0) = 4: worldPos(1) = 400.99999999: worldPos(2) = 2.798989
    dataType(9) = 1011: data(9) = worldPos          ' world space position
' The following code attaches xdata to an object
    group.SetXData dataType, data
' The following code shows how to retrive information from XData
    appname = "TEST_APP"
    group.GetXData appname, xdataType, xdataValue  ' get the xdata from the group

    Dim lbnd As Integer, ubnd As Integer
    Dim i As Integer
    Dim arrayData As Variant
    Dim resultString As String
    If VarType(xdataType) > vbNull Then
        lbnd = LBound(xdataType)
        ubnd = UBound(xdataType)
        For i = lbnd To ubnd

            If (xdataType(i) = 1010) Or (xdataType(i) = 1011) Or (xdataType(i) = 1012) Or (xdataType(i) = 1013) Then
                arrayData = xdataValue(i)
                resultString = "XData Type: " & xdataType(i) & "  Xdata Value: " & arrayData(0) & "," & arrayData(1) & "," & arrayData(2)
            Else
                resultString = "XData Type: " & xdataType(i) & "  Xdata Value: " & xdataValue(i)
End If
Debug.Print resultString   ' print all the xdata in the immedate window
        Next
    End If
End Sub

Private Sub CommandButton1_Click()
    Dim anObj As AcadLine
    ' Initialize anObj variable to any object that supports
    ' setxdata method.  This example creates a line for that
    ' purpose
    Dim startpt(0 To 2) As Double, endpt(0 To 2) As Double
    startpt(0) = 0#: startpt(1) = 0#: startpt(2) = 0#
    endpt(0) = 5#: endpt(1) = 5#: endpt(2) = 0#
    Set anObj = ThisDrawing.ModelSpace.AddLine(startpt, endpt)

Dim dataType(0 To 9) As Integer
    Dim data(0 To 9) As Variant
    Dim reals3(0 To 2) As Double
    Dim worldPos(0 To 2) As Double
    ' Initialize all the xdata value. Note that first data in the list should be
    ' application name and first datatype code should be 1001
    dataType(0) = 1001: data(0) = "Another_Test_Application"
    dataType(1) = 1000: data(1) = "This is a test for xdata"

dataType(2) = 1003: data(2) = "0"               ' layer
    dataType(3) = 1040: data(3) = 1.23479137438413E+40          ' real
    dataType(4) = 1041: data(4) = 1237324938            ' distance
    dataType(5) = 1070: data(5) = 32767                 ' 16 bit Integer
    dataType(6) = 1071: data(6) = 32767                 ' 32 bit Integer
    dataType(7) = 1042: data(7) = 10                ' scaleFactor

reals3(0) = -2.95: reals3(1) = 100: reals3(2) = -20
    dataType(8) = 1010: data(8) = reals3                ' real
    worldPos(0) = 4: worldPos(1) = 400.99999999: worldPos(2) = 2.798989
    dataType(9) = 1011: data(9) = worldPos          ' world space position
    ' The following code attaches xdata to an object
    anObj.SetXData dataType, data
End Sub
Public Sub Show_Group_names(GroupNames As Collection)
    frmGroupNames.lstGroupNames.Clear
    Dim x As Long
    For x = 1 To GroupNames.Count
        frmGroupNames.lstGroupNames.AddItem GroupNames.Item(x)
    Next x
End Sub
Public Sub Show_xdata(AppNames As Variant)
    ' now figure out which page is active on the form and populate the
    ' approperiate field(s)
    lstAppNamePlace.Clear
    lstAppNameEdit.Clear
    lstAppNameRemove.Clear
    lstAppNames.Clear
    Dim appnamevalue As String
    Dim x As Long
    appnamevalue = MultiPage1.Value
    Select Case appnamevalue
        Case 0                                          ' place xdata
            For x = 0 To UBound(AppNames)
                lstAppNamePlace.AddItem AppNames(x)
                lstAppNameEdit.AddItem AppNames(x)
                lstAppNameRemove.AddItem AppNames(x)
                lstAppNames.AddItem AppNames(x)
            Next x
            lstAppNamePlace.ListIndex = 0              'Set combo box to first entry
        Case 1                                          ' edit xdata
            For x = 0 To UBound(AppNames)
                lstAppNamePlace.AddItem AppNames(x)
                lstAppNameEdit.AddItem AppNames(x)
                lstAppNameRemove.AddItem AppNames(x)
                lstAppNames.AddItem AppNames(x)
            Next x
            lstAppNamePlace.ListIndex = 0              'Set combo box to first entry
        Case 2                                          ' remove xdata
            For x = 0 To UBound(AppNames)
                lstAppNamePlace.AddItem AppNames(x)
                lstAppNameEdit.AddItem AppNames(x)
                lstAppNameRemove.AddItem AppNames(x)
                lstAppNames.AddItem AppNames(x)
            Next x
            lstAppNamePlace.ListIndex = 0              'Set combo box to first entry
        Case 3                                          ' application names
            For x = 0 To UBound(AppNames)
                lstAppNamePlace.AddItem AppNames(x)
                lstAppNameEdit.AddItem AppNames(x)
                lstAppNameRemove.AddItem AppNames(x)
                lstAppNames.AddItem AppNames(x)
            Next x
            lstAppNamePlace.ListIndex = 0              'Set combo box to first entry
    End Select

End Sub

Public Sub show_xdata_msgbox(Ent As Object, Pnt As Variant)
' show that we got the entity and the point selected
    Dim x As Long
    Dim msg As String
    msg = "Ent name is " & Ent.EntityName & vbCr
    msg = msg & "Pnt is" & vbCr
    For x = 0 To 2
        msg = msg & " " & Pnt(x) & vbCr
    Next x
    MsgBox msg

End Sub
Private Sub Clear_Fields()
    
    lstAppNamePlace.Clear
    lstAppNameEdit.Clear
    lstAppNameRemove.Clear
    lstAppNames.Clear

End Sub
Private Sub Set_Group_Name(groupname As String)
    
    lbObjectPlace.Visible = True
    edObjectPlace.Visible = True
    lbObjectPlace.Caption = "Group Name"
    edObjectPlace.Text = groupname
    lbObjectEdit.Visible = True
    edObjectEdit.Visible = True
    lbObjectEdit.Caption = "Group Name"
    edObjectEdit.Text = groupname
    lbObjectRemove.Visible = True
    edObjectRemove.Visible = True
    lbObjectRemove.Caption = "Group Name"
    edObjectRemove.Text = groupname

End Sub
Private Sub Set_Object_Name(objecthandle As String)
    
    lbObjectPlace.Visible = True
    edObjectPlace.Visible = True
    lbObjectPlace.Caption = "Object Handle"
    edObjectPlace.Text = objecthandle
    lbObjectEdit.Visible = True
    edObjectEdit.Visible = True
    lbObjectEdit.Caption = "Object Handle"
    edObjectEdit.Text = objecthandle
    lbObjectRemove.Visible = True
    edObjectRemove.Visible = True
    lbObjectRemove.Caption = "Object Handle"
    edObjectRemove.Text = objecthandle

End Sub
Private Sub Turn_off_object_fields()
    
    lbObjectPlace.Visible = False
    edObjectPlace.Visible = False
    lbObjectEdit.Visible = False
    edObjectEdit.Visible = False
    lbObjectRemove.Visible = False
    edObjectRemove.Visible = False

End Sub
