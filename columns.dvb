Attribute VB_Name = "Module1"
Option Explicit
Public Sub ColumnSamples()
    frmColumns.Show
End Sub

Attribute VB_Name = "frmColumns"
Attribute VB_Base = "0{6FE80A84-D7A5-11D1-99D7-00609761BD90}{6FE80A50-D7A5-11D1-99D7-00609761BD90}"
Attribute VB_Creatable = False
Attribute VB_PredeclaredId = True
Attribute VB_Exposed = False
Attribute VB_TemplateDerived = False
Attribute VB_Customizable = False
Option Explicit
Private SampleArray(5, 2) As Variant
Private OtherSampleArray(5, 2) As Variant
Private ColText As String
Private Column As String

Private Sub btnClear_Click()
    lstColumnWindow.Clear
    lstListWindow.Clear
    lstItemWindow.Clear
End Sub

Private Sub btnLoad_Click()

    lstColumnWindow.Column = SampleArray                   ' load using column property
    lstListWindow.List = SampleArray                       ' load using list property

    Dim intI As Integer
    With lstItemWindow                                     ' load using additem method
        For intI = 0 To UBound(SampleArray)
            .AddItem SampleArray(intI, 0)
            .Column(1, .ListCount - 1) = SampleArray(intI, 1)
        Next intI
    End With


End Sub

Private Sub btnOK_Click()
    End
End Sub

Private Sub btnOtherLoad_Click()
    lstColumnWindow.Column = OtherSampleArray                   ' load using column property
    lstListWindow.List = OtherSampleArray                       ' load using list property

    Dim intI As Integer
    With lstItemWindow                                     ' load using additem method
        For intI = 0 To UBound(OtherSampleArray)
            .AddItem OtherSampleArray(intI, 0)
            .Column(1, .ListCount - 1) = OtherSampleArray(intI, 1)
        Next intI
    End With

End Sub

Private Sub lstColumnWindow_Click()

    edView.Text = lstColumnWindow.Value

End Sub

Private Sub lstItemWindow_Click()
    
    edView.Text = lstItemWindow.Value

End Sub

Private Sub lstListWindow_Click()
    
    edView.Text = lstListWindow.Value

End Sub

Private Sub rdColumn1_Click()
    lstColumnWindow.BoundColumn = 1
    lstListWindow.BoundColumn = 1
    lstItemWindow.BoundColumn = 1
End Sub
Private Sub rdColumn2_Click()
    lstColumnWindow.BoundColumn = 2
    lstListWindow.BoundColumn = 2
    lstItemWindow.BoundColumn = 2
End Sub

Private Sub UserForm_Initialize()
    SampleArray(0, 0) = "Row 1"
    SampleArray(1, 0) = "Row 2"
    SampleArray(2, 0) = "Row 3"
    SampleArray(3, 0) = "Row 4"
    SampleArray(4, 0) = "Row 5"
    SampleArray(0, 1) = "is 0"
    SampleArray(1, 1) = "is 1"
    SampleArray(2, 1) = "is 2"
    SampleArray(3, 1) = "is 3"
    SampleArray(4, 1) = "is 4"
    
    OtherSampleArray(0, 0) = "1"
    OtherSampleArray(0, 1) = "2"
    OtherSampleArray(1, 0) = "3"
    OtherSampleArray(1, 1) = "4"
    OtherSampleArray(2, 0) = "5"
    OtherSampleArray(2, 1) = "6"
    OtherSampleArray(3, 0) = "7"
    OtherSampleArray(3, 1) = "8"
    OtherSampleArray(4, 0) = "9"
    OtherSampleArray(4, 1) = "10"
    
    rdColumn1.Value = "1"
    
End Sub
