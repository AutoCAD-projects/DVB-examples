Attribute VB_Name = "Employee"
Attribute VB_Base = "0{FCFB3D2A-A0FA-1068-A738-08002B3371B5}"
Attribute VB_Creatable = True
Attribute VB_PredeclaredId = False
Attribute VB_Exposed = False
Attribute VB_TemplateDerived = False
Attribute VB_Customizable = False
Option Explicit

Public Age As Integer
Public Name As String


Public Sub Speak()
    Dim strSpeak As String
        strSpeak = strSpeak & "My age is " & Me.Age
    ' And display it
    MsgBox strSpeak, , Me.Name
End Sub

Private Sub Class_Initialize()
    ' MsgBox "New Employee"
End Sub

Private Sub Class_Terminate()
    ' MsgBox "Employee gone!"
End Sub

Attribute VB_Name = "basEmployee"
Option Explicit


Public Sub TestEmp()
    Dim Emp As Employee
    
    ' Make the object variable point to a real object.
    Set Emp = New Employee
    
    ' Set properties of the new object.
    With Emp
        .Age = 29
        .Name = "Bill Kramer"
    End With
    ' Retrieve the properties.
    Debug.Print Emp.Name & " "
    Emp.Speak

    ' Destroy the object.
    Set Emp = Nothing
End Sub
