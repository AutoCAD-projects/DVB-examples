Attribute VB_Name = "Form1"
Attribute VB_Base = "0{A103F745-B640-11D2-A614-00805F0C2A0F}{A103F73B-B640-11D2-A614-00805F0C2A0F}"
Attribute VB_Creatable = False
Attribute VB_PredeclaredId = True
Attribute VB_Exposed = False
Attribute VB_TemplateDerived = False
Attribute VB_Customizable = False

'       Text Height Change Sample for AutoCAD 2000
'
'      Copyright (C) 1996 1997 1999 by Autodesk, Inc.
'
'      Permission to use, copy, modify, and distribute this software
'      for any purpose and without fee is hereby granted, provided
'      that the above copyright notice appears in all copies and
'      that both that copyright notice and the limited warranty and
'      restricted rights notice below appear in all supporting
'      documentation.
'
'      AUTODESK PROVIDES THIS PROGRAM "AS IS" AND WITH ALL FAULTS.
'      AUTODESK SPECIFICALLY DISCLAIMS ANY IMPLIED WARRANTY OF
'      MERCHANTABILITY OR FITNESS FOR A PARTICULAR USE.  AUTODESK, INC.
'      DOES NOT WARRANT THAT THE OPERATION OF THE PROGRAM WILL BE
'      UNINTERRUPTED OR ERROR FREE.
'
'      Use, duplication, or disclosure by the U.S. Government is subject to
'      restrictions set forth in FAR 52.227-19 (Commercial Computer
'      Software - Restricted Rights) and DFAR 252.227-7013(c)(1)(ii)
'      (Rights in Technical Data and Computer Software), as applicable.


Option Explicit

Private Sub cmdApply_Click()
    Dim elem As Object
    Dim TextHeight As Double
    Dim found As Boolean
    TextHeight = TextBox1.Text
    
    ' Cycle through the entities in the ModelSpace
    For Each elem In ThisDrawing.ModelSpace
        With elem
            If (.EntityName = "AcDbText") Or (.EntityName = "AcDbMText") Then
                ' Change the height of the text entity
                .Height = TextHeight
                .Update
                found = True
            End If
        End With
        Set elem = Nothing
    Next elem
    
    ' If we didn't find text, notify user
    If Not found Then
        MsgBox "No text found in ModelSpace.", vbInformation
    End If
    
End Sub

Private Sub cmdCancel_Click()
    ' Terminate on 'Done'
    End
End Sub

Private Sub cmdHelp_Click()
    ' Display help message
    MsgBox "Changes the height of all text in the ModelSpace." _
    + Chr(13) + Chr(10) + "First draw text using the TEXT Command."
End Sub

Private Sub SpinButton1_Change()
    ' Change text height in textbox as spin button changes
    TextBox1.Text = SpinButton1.Value / 10
End Sub

Private Sub UserForm_Initialize()
    ' Put initial value in text height box
    TextBox1.Text = SpinButton1.Value / 10
End Sub

Attribute VB_Name = "Module1"
'       Text Height Change Sample for AutoCAD 2000
'
'      Copyright (C) 1996 1997 1999 by Autodesk, Inc.
'
'      Permission to use, copy, modify, and distribute this software
'      for any purpose and without fee is hereby granted, provided
'      that the above copyright notice appears in all copies and
'      that both that copyright notice and the limited warranty and
'      restricted rights notice below appear in all supporting
'      documentation.
'
'      AUTODESK PROVIDES THIS PROGRAM "AS IS" AND WITH ALL FAULTS.
'      AUTODESK SPECIFICALLY DISCLAIMS ANY IMPLIED WARRANTY OF
'      MERCHANTABILITY OR FITNESS FOR A PARTICULAR USE.  AUTODESK, INC.
'      DOES NOT WARRANT THAT THE OPERATION OF THE PROGRAM WILL BE
'      UNINTERRUPTED OR ERROR FREE.
'
'      Use, duplication, or disclosure by the U.S. Government is subject to
'      restrictions set forth in FAR 52.227-19 (Commercial Computer
'      Software - Restricted Rights) and DFAR 252.227-7013(c)(1)(ii)
'      (Rights in Technical Data and Computer Software), as applicable.

Sub TextHeight()
    Form1.Show
End Sub
