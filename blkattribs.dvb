Attribute VB_Name = "basGlobal"
Option Explicit

Public Function GetAttrib1(BlkName As String, AttrName As String) As String
' getting all entities in the drawing and sorting out the desired block and attribute
' take the requested block name and attribute name and return the attributes contents
' This function only passes back the last attribute contents found
' therefore it is built expection to see only one block
' We could just as easily create a string of all tags contents found
' (for multiple blocks) and pass that back.
' A zero length string is returned when no attribute or block is found
  Dim obj As Object                             ' generic object
  Dim varAttributeArray As Variant              ' attribute array
  Dim objAttribRef As AcadAttributeReference    ' attribute occurance
  Dim objModelSpace As AcadModelSpace           ' model space
  Dim intI, intJ, intK, intL As Integer         ' subscripts
  Dim strMessage, TagContents As String         ' attribute text to return
  
  Set objModelSpace = ThisDrawing.ModelSpace    ' get the entity space to work with
  intI = objModelSpace.Count - 1                ' set counter to one less than entities
  For intJ = 0 To intI                          ' spin through entities
    Set obj = objModelSpace.Item(intJ)          ' get an entity
    If obj.EntityType = acBlockReference Then   ' is it a block
       varAttributeArray = obj.GetAttributes    ' get its attributes
       intJ = UBound(varAttributeArray) + 1     ' get attribute count +1
       If intJ > 0 Then                         ' got the block
          strMessage = "Found block - " & obj.Name & _
               " - with " & Str$(intJ) & " attributes { "
          For intL = 0 To intJ - 1              ' spin through block's attributes
             Set objAttribRef = varAttributeArray(intL) ' get an attribute
             ' check its tag name
             If UCase(objAttribRef.TagString) = UCase(AttrName) Then
                TagContents = objAttribRef.TextString   ' load the contents
                strMessage = strMessage + objAttribRef.TagString & "/" & objAttribRef.TextString & " "
             End If
          Next intL
          strMessage = strMessage & "}"
          MsgBox strMessage
       End If
    End If
  Next intJ
  GetAttrib = TagContents
End Function
Public Function GetAttrib(BlkName As String, AttrName As String) As String
' getting the block with a selection set and getting the requested attribute
' take the requested block name and attribute name and returns the attributes contents
' This function only passes back the last attribute contents found
' therefore it is built with the expection to see only one block
' We could just as easily create a string of all tags contents found
' (for multiple blocks) and pass that back.
' A zero length string is returned when no attribute or block is found

  Dim obj As Object                             ' generic object
  Dim varAttributeArray As Variant              ' attribute array
  Dim objAttribRef As AcadAttributeReference    ' attribute occurance
  Dim intJ, intK, intL As Integer               ' subscripts
  Dim strMessage, TagContents As String         ' attribute text to return
  Dim sset As AcadSelectionSet                  ' collection of selection sets
  
  Set sset = ThisDrawing.SelectionSets.Add("SS1") ' create a new set
  sset.Clear                                    ' clear it to be safe
  
  Dim gpCode(0 To 3) As Integer                 ' DXF code (code . value)
  ' <and (0 . "INSERT")(2 . blockname)and>
  Dim dataValue(0 To 3) As Variant              ' DXF Value
  gpCode(0) = -4                                ' open an and modifier
  dataValue(0) = "<and"                         ' and value
  gpCode(1) = 0                                 ' Object type
  dataValue(1) = "INSERT"                       ' a block
  gpCode(2) = 2                                 ' block name type
  dataValue(2) = UCase(BlkName)                 ' block name
  gpCode(3) = -4                                ' close the and code
  dataValue(3) = "and>"                         ' close code
    
  Dim groupCode As Variant, dataCode As Variant ' set arrays to pass
  groupCode = gpCode                            ' load the arrays
  dataCode = dataValue
  
  ' get all blocks in the drawing with the requested block name
  sset.Select acSelectionSetAll, , , groupCode, dataCode
  
  For intJ = 0 To sset.Count - 1             ' spin through selection set
    Set obj = sset.Item(intJ)                ' get a block object
    varAttributeArray = obj.GetAttributes    ' get its attributes
    intJ = UBound(varAttributeArray) + 1     ' get attribute count +1
    If intJ > 0 Then                         ' got the block
       strMessage = "Found block - " & obj.Name & _
            " - with " & Str$(intJ) & " attributes { "
       For intL = 0 To intJ - 1              ' spin through block's attributes
          Set objAttribRef = varAttributeArray(intL) ' get an attribute
          ' check its tag name
          If UCase(objAttribRef.TagString) = UCase(AttrName) Then
             TagContents = objAttribRef.TextString   ' load the contents
             strMessage = strMessage + objAttribRef.TagString & "/" & objAttribRef.TextString & " "
          End If
       Next intL
       strMessage = strMessage & "}"
       'MsgBox strMessage
    End If
  Next intJ
  GetAttrib = TagContents
End Function

Public Sub test()
    ' use F8 to step through the called function to see how it
    ' works
    Stop
    Dim strAttrContents As String
    ' call the attribute getter (highly technical jargon used here at all times!)
    ' and get the contents back
    strAttrContents = GetAttrib("$SHT_SZ", "shtsz")
    ' show the results
    If Len(strAttrContents) > 0 Then
        MsgBox "Attribute contents were: " & strAttrContents, , "Got it!"
    Else
        MsgBox "Attribute or block not found.", , "Missed it!"
    End If
End Sub
