Attribute VB_Name = "Module2"
'
'  ad_LayerList
'
'  This routine simply populates a combobox with the layers
'    in the current drawing. It was developed in AutoCAD 2000.
'  Demand load:  -vbarun;ad_LayerList.dvb!ad_LayerList;
'
'  version 1.00
'  7/22/2000
'
'  Copyright©2000-2003 ActiveDwg.com
'
'  This routine is provided for demonstration purposes only and must
'    not be used for critical applications without your verification
'    that this routine will perform as you intended.
'  This routine may be freely utilized for your own personal use so long
'    as the entire contents of this header remain intact.
'  This routine is provided "as-is" and no declaration, written or implied,
'    is made as to its reliability for any particular task. Any use of this
'    routine is solely at your own risk.
'
Option Explicit
Sub ad_LayerList()
    UserForm1.show
End Sub

Attribute VB_Name = "UserForm1"
Attribute VB_Base = "0{6511F43E-74B0-4F3D-B23D-EEB442743A22}{6DD19881-7A12-40F6-9C50-2ECDCAC49D93}"
Attribute VB_GlobalNameSpace = False
Attribute VB_Creatable = False
Attribute VB_PredeclaredId = True
Attribute VB_Exposed = False
Attribute VB_TemplateDerived = False
Attribute VB_Customizable = False
'
'  ad_LayerList
'
'  This routine populates a combobox with the layers in the current
'    drawing and makes the selected layer the current layer.
'    It was developed in AutoCAD 2000.
'  Demand load:  -vbarun;ad_LayerList.dvb!ad_LayerList;
'
'  version 1.00
'  7/22/2000
'
'  Copyright©2000-2003 ActiveDwg.com
'
'  This routine is provided for demonstration purposes only and must
'    not be used for critical applications without your verification
'    that this routine will perform as you intended.
'  This routine may be freely utilized for your own personal use so long
'    as the entire contents of this header remain intact.
'  This routine is provided "as-is" and no declaration, written or implied,
'    is made as to its reliability for any particular task. Any use of this
'    routine is solely at your own risk.
'
Option Explicit
Private Sub ComboBox1_Click()
    Dim PickLayer As String
    Dim NewLayer As AcadLayer
    
    PickLayer = ComboBox1.Text
    Set NewLayer = ThisDrawing.Layers(PickLayer)
    Unload Me
    ThisDrawing.ActiveLayer = NewLayer
End Sub

Private Sub CommandButton1_Click()
  Unload Me
End Sub

Private Sub UserForm_Initialize()
    Dim entry As AcadLayer
    For Each entry In ThisDrawing.Layers
        ComboBox1.AddItem entry.Name
    Next
End Sub
