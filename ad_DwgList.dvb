Attribute VB_Name = "Module1"
'
'  ad_DwgList
'
'  This routine creates a list of the currently open drawings
'     and writes them to the file "C:\adDwgList.txt". Each time
'     the routine is run, the file is overwritten.
'  It was developed in AutoCAD 2000.
'  Demand load:  -vbarun;ad_DwgList.dvb!ad_DwgList;
'
'  version 1.00
'  4/11/2001
'
'  Copyright©2001 ActiveDwg.com
'
'  This routine is provided for demonstration purposes only and must
'    not be used for critical applications without your verification
'    that this routine will perform as you intended.
'  This routine may be freely utilized for your own personal use so long
'    as the entire contents of this header remain intact.
'  This routine is provided "as-is" and no declaration, written or implied,
'    is made as to its reliability for any particular task. Any use of this
'    routine is solely at your own risk.
'

Option Explicit

Sub ad_DwgList()
  Dim adDwg As AcadDocument
  Dim adListFile As Integer
  Dim adList As String
  adList = ""
  For Each adDwg In Documents
    adList = adList & adDwg.Path & "\" & adDwg.Name & vbCrLf
  Next
  If Documents.Count > 0 Then
    adListFile = FreeFile()
    Open "C:/adDwgList.txt" For Binary As #adListFile
    Put #adListFile, , adList
  End If
  Close adListFile
End Sub
