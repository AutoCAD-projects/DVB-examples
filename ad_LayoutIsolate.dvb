Attribute VB_Name = "Module1"
'
'  ad_LayoutIsolate
'
'  This routine demonstrates a way to isolate entities according
'    to the layout on which they reside.
'
'  It was developed in AutoCAD 2002.
'  Demand load:  -vbarun;ad_LayoutIsolate.dvb!ad_LayoutIsolate;
'
'  version 1.00
'  7/18/2003
'
'  Copyright©2003 ActiveDwg.com
'
'  This routine is provided for demonstration purposes only and must
'    not be used for critical applications without your verification
'    that this routine will perform as you intended.
'  This routine may be freely utilized for your own personal use so long
'    as the entire contents of this header remain intact.
'  This routine is provided "as-is" and no declaration, written or implied,
'    is made as to its reliability for any particular task. Any use of this
'    routine is solely at your own risk.
'
Option Explicit

Sub ad_LayoutIsolate()
  Dim fType(0 To 1) As Integer, fData(0 To 1)
  Dim DataSS As AcadSelectionSet
  Dim dwgEnt As AcadEntity
  Dim adLayout As AcadLayout
  Dim itemType As String
  Dim itemCount As Integer
  
  On Error Resume Next
'first create a selection set of all items of the type you want to work with
  Set DataSS = ThisDrawing.SelectionSets("DataSS")
  If Err Then Set DataSS = ThisDrawing.SelectionSets.Add("DataSS")
  DataSS.Clear
  itemType = "TEXT"  'this holds the type of entity we'll be collecting
  fType(0) = 0: fData(0) = itemType
  fType(1) = 8: fData(1) = "*"     'Here you specify the layer. We'll use all layers
  DataSS.Select acSelectionSetAll, , , fType, fData

'now we cycle through all the layouts
  For Each adLayout In ThisDrawing.Layouts
    itemCount = 0
    ThisDrawing.ActiveLayout = adLayout
    For Each dwgEnt In DataSS
'this is where the items residing on the current layout are culled
      If LCase(ThisDrawing.ObjectIdToObject(dwgEnt.OwnerID).Layout.Name) = LCase(adLayout.Name) Then
        itemCount = itemCount + 1
      End If
    Next dwgEnt
    MsgBox "Report for " & itemType & " Entities-" & vbCrLf & _
           "Total in the active drawing: " & DataSS.Count & vbCrLf & _
           "Total on layout " & adLayout.Name & ": " & itemCount
  Next adLayout
  DataSS.Delete
End Sub
