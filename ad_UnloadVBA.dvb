Attribute VB_Name = "Module1"
'
'  ad_UnloadVBA
'
'  This routine demonstrates how to unload a macro after
'    it executes. The functional part of this routine is
'    the last code line, with SendCommand.
'    It was developed in AutoCAD 2000.
'  Demand load:  -vbarun;ad_UnloadVBA.dvb!ad_UnloadVBA;
'
'  version 1.00
'  7/24/2000
'
'  Copyright©2000 ActiveDwg.com
'
'  This routine is provided for demonstration purposes only and must
'    not be used for critical applications without your verification
'    that this routine will perform as you intended.
'  This routine may be freely utilized for your own personal use so long
'    as the entire contents of this header remain intact.
'  This routine is provided "as-is" and no declaration, written or implied,
'    is made as to its reliability for any particular task. Any use of this
'    routine is solely at your own risk.
'
Option Explicit
Sub ad_UnloadVBA()
    Dim Prefs As AcadPreferences
    Dim MenuDisplay As Boolean
    Set Prefs = ThisDrawing.Application.preferences
    MenuDisplay = preferences.Display.DisplayScreenMenu
    Prefs.Display.DisplayScreenMenu = Not (MenuDisplay)
    Prefs.Display.DisplayScreenMenu = Not (MenuDisplay)
    
    ThisDrawing.SendCommand "_vbaunload" & vbCr & "UnloadVBA.dvb" & vbCr
End Sub
