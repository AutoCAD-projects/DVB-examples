Attribute VB_Name = "Module1"
' Block extrema - Bill Kramer
' VBA example of using Bounding Box and Intersections
'
Sub Block_Extreme(Nam As String, MinPnt As Variant, MaxPnt As Variant)
  Dim B1 As AcadBlock
  Set B1 = ThisDrawing.Blocks.Item(Nam)
  Dim XMin, YMin, XMax, YMax As Double
  XMin = 999999.9: YMin = 999999.9
  XMax = -99999.9: YMax = -99999.9
  Dim E1 As Object
  Dim P1, P2 As Variant
  J = B1.Count - 1
  For I = 0 To J
    Set E1 = B1.Item(I)
    E1.GetBoundingBox P1, P2
    If P2(0) > XMax Then XMax = P2(0)
    If P2(1) > YMax Then YMax = P2(1)
    If P1(0) < XMin Then XMin = P1(0)
    If P1(1) < YMin Then YMin = P1(1)
  Next I
  P1(0) = XMin: P1(1) = YMin: MinPnt = P1
  P1(0) = XMax: P1(1) = YMax: MaxPnt = P1
End Sub
Sub PickBlock()
Dim PP1, PP2 As Variant
Dim PP0 As Variant
On Error Resume Next
PP0 = ThisDrawing.Utility.GetPoint(, "Pick an object: ")
Dim S1 As AcadSelectionSet
  Set S1 = ThisDrawing.SelectionSets.Add("SS1")
  If Err.Number <> 0 Then
    Set S1 = ThisDrawing.SelectionSets.Item("SS1")
    Err.Clear
  End If
  S1.Clear
  S1.SelectAtPoint (PP0)
  Dim E1 As Object
  Set E1 = S1.Item(0)
  If E1.EntityType = acBlockReference Then
     MsgBox "Found a block reference! - " & E1.Name
     Call Block_Extreme(E1.Name, PP1, PP2)
     MsgBox "Extreme found at : " & PP1(0) & ", " & PP1(1) & " and " & PP2(0) & ", " & PP2(1)
  End If
  ' ...

End Sub

Sub BlkInters()
Dim PP0, IPs, PP1, PP2 As Variant
  Dim S1 As AcadSelectionSet
  Dim E1, E2, E1S(0) As Object
  Dim IP(2) As Double
  '
  PP0 = ThisDrawing.Utility.GetPoint(, "Pick a block insert: ")
  'added test for existing set
  On Error Resume Next
  Set S1 = ThisDrawing.SelectionSets.Add("SS1")
  If Err.Number <> 0 Then
    Set S1 = ThisDrawing.SelectionSets.Item("SS1")
    Err.Clear
  End If
  'end modifications
  '
  S1.Clear
  S1.SelectAtPoint (PP0)
  Set E1 = S1.Item(0)
  'only work with block reference (insert) objects
  If E1.EntityType = acBlockReference Then
    'Get limits of inserted block
     E1.GetBoundingBox PP1, PP2
    'Build selection set of objects crossing the bounding box
     S1.Clear
     S1.Select acSelectionSetCrossing, PP1, PP2
     'Remove block reference from selection set
     Set E1S(0) = E1
     S1.RemoveItems E1S
     'Loop through selection set
     J = S1.Count - 1
     For I = 0 To J
        'Compute the intersection points
        Set E2 = S1.Item(I)
        IPs = E1.IntersectWith(E2, acExtendNone)
        'Go through the intersections found
        For K = LBound(IPs) To UBound(IPs)
           IP(0) = IPs(K): IP(1) = IPs(K + 1): IP(2) = IPs(K + 2)
           K = K + 2
           'draw a point at the intersection location.
           ThisDrawing.ModelSpace.AddPoint IP
        Next K
     Next I
    Else
     MsgBox "You selected the wrong type of entity!"
  End If

End Sub
