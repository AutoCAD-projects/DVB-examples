Attribute VB_Name = "basGlobal"
Option Explicit
Public Sub Plot_Information_TreeList()
    frmPlotting.Show

End Sub
Public Sub Plot_Information_Messagebox()
    Dim strMsg As String
    strMsg = ""
    With ThisDrawing
        Dim objPltCfgs As AcadPlotConfigurations
        Set objPltCfgs = .PlotConfigurations
        Dim objPltCfg As AcadPlotConfiguration
        Dim lngPltcnt As Long, LngI As Long
        lngPltcnt = objPltCfgs.Count
        For LngI = 0 To lngPltcnt - 1
            Set objPltCfg = objPltCfgs(LngI)
            strMsg = strMsg & "Plot Configuration name:"
            strMsg = strMsg & vbTab & objPltCfg.Name & vbCrLf
            strMsg = strMsg & "Associated plotter conf. name:" & vbTab & objPltCfg.ConfigName & vbCrLf
            strMsg = strMsg & "Associated paper units:" & vbTab & objPltCfg.PaperUnits & vbCrLf
            strMsg = strMsg & "Use plot styles?" & vbTab & objPltCfg.PlotWithPlotStyles & vbCrLf
            strMsg = strMsg & "Show plot styles?" & vbTab & objPltCfg.ShowPlotStyles & vbCrLf
        Next LngI
        
    End With
    MsgBox strMsg, , "Plot Object Information"
End Sub
Public Function Contains(strLine As String, strChar As String) As Boolean
' this routine returns true when at least one occurance of strChar
' is present in strLine. False is returned when it is not present.
    Dim bolResult As Boolean
    Dim lngCnt As Long
    For lngCnt = 1 To Len(strLine)
        If Mid(strLine, lngCnt, Len(strChar)) = strChar Then
            ' found it so set the result flag and exit the for loop
            bolResult = True
            Exit For
        End If
    Next lngCnt
    Contains = bolResult
End Function

Attribute VB_Name = "frmPlotting"
Attribute VB_Base = "0{D125F89B-FE39-11D2-99E9-00609761BD90}{D125F7F4-FE39-11D2-99E9-00609761BD90}"
Attribute VB_Creatable = False
Attribute VB_PredeclaredId = True
Attribute VB_Exposed = False
Attribute VB_TemplateDerived = False
Attribute VB_Customizable = False
Option Explicit
' Saved entity; used for un-highlighting
Dim mentLast As Object

' List item being processed
Dim mli As ListItem

' Image constants found in the image list control on the form
' under the custom property and the Images tab
' constant name = image index number
Const conImageArc = 1
Const conImageCircle = 2
Const conImageEllipse = 3
Const conImageLine = 4
Const conImagePoint = 5
Const conImageRay = 6
Const conImageDrawing = 7
Const conImageClosed = 8
Const conImageOpen = 9
Const conImagePlotCfg = 10
Const conImageProperties = 11
Const conImagePropertyData = 12
Public strPrintSpoolerPath As String
Public Sub LoadPlotDevicesAndStyles()
    ' create a layout object & set it to the modelspace layout
    Dim objLayout As AcadLayout
    Set objLayout = ThisDrawing.ModelSpace.Layout
    
    ' Refresh the current plot information for this session.
    objLayout.RefreshPlotDeviceInfo
    
    ' create a variant to hold the plot devices names array
    Dim plotDevices As Variant
    plotDevices = objLayout.GetPlotDeviceNames()
    ' List all the valid device names for the system
    Dim x As Integer
    For x = LBound(plotDevices) To UBound(plotDevices)
         lstPlotDevices.AddItem plotDevices(x)
    Next
    
    ' create a variant to hold the media names array
    Dim mediaNames As Variant
    mediaNames = objLayout.GetCanonicalMediaNames()
    Dim strMsg As String
    strMsg = ""
    ' List all the media names, and their localized version
    For x = LBound(mediaNames) To UBound(mediaNames)
        strMsg = strMsg & "MediaNames: " & mediaNames(x) & vbTab & "Local MediaName: " & objLayout.GetLocaleMediaName(mediaNames(x)) & vbCrLf
    Next
    If Len(strMsg) > 0 Then
        MsgBox strMsg, , "Media Names"
    End If
    Dim styleNames As Variant
    styleNames = objLayout.GetPlotStyleTableNames()
    ' List all the entries in the plot style table
    For x = LBound(styleNames) To UBound(styleNames)
        lstPlotStyles.AddItem styleNames(x)
    Next
End Sub

Private Sub btnBrowse_Click()
' this function calls the common dialog for saving files
' and passes back the selected path and filename into the edit box
' of the calling dialog
    Dim strFileName As String
    ' store the current filename
    strFileName = edFileName.Text
    ' setup the save dialog box
    CommonDialog1.DialogTitle = "Create Plot File"
    CommonDialog1.Filter = "Plot File (*.plt)"
    CommonDialog1.FileName = "Drawing.plt"
    
    CommonDialog1.DefaultExt = "plt"
    ' use the global var (set in the form initialize routine) for the initial directory
    CommonDialog1.InitDir = strPrintSpoolerPath
    CommonDialog1.ShowSave                  ' show the save dialog box
    
    ' pass back the select file and path
    edFileName.Text = CommonDialog1.FileName
    ' check if there is a path
    If Not Contains(edFileName.Text, "\") Then
        ' no path so restore the last filename to the parent edit box
        edFileName.Text = strFileName
    End If
    
End Sub

Private Sub btnDone_Click()
    End
End Sub

Private Sub btnPlotwithConfig_Click()
    Me.Hide
    Me.MousePointer = fmMousePointerHourGlass
    
    ' create a plot object to do the work
    Dim objPlot As AcadPlot
    Set objPlot = ThisDrawing.Plot
    
    ' create a layout object
    Dim objLayout As AcadLayout
    Set objLayout = ThisDrawing.ActiveLayout  ' set it to the active layout
    
    ' get the preferences object
'    Dim objPref As AcadPreferences
'    Set objPref = ThisDrawing.Application.Preferences
    ' get the active layout in the preferences object
'    Set objLayout = objPref.Application.ActiveDocument.ActiveLayout
    
    ' get the plot congifurations collection
    Dim colPlotConfigs As AcadPlotConfigurations
    Set colPlotConfigs = ThisDrawing.PlotConfigurations
    
    ' get the operator selected plot configuration object
    Dim objPlotConfig As AcadPlotConfiguration
    Set objPlotConfig = colPlotConfigs(cbPlotConfigs.Text)
    
    ' make all changes to this instance of the plot configuration here
    ' remember that the changes are to this instance of the plot configuration
    ' not to the original plotconfiguration object
    
    objLayout.PlotRotation = objPlotConfig.PlotRotation
    objPlotConfig.StandardScale = ac1_4     ' override the configuration's setting
    objPlotConfig.PlotWithPlotStyles = True
    objPlotConfig.ShowPlotStyles = True
    
    objPlotConfig.PlotType = acExtents  ' can't make centerplot true unless this property is NOT set to aclayout
    objPlotConfig.CenterPlot = True
    
    'objplot
    'objLayout.ViewToPlot
    'objLayout.PlotWithPlotStyles = True
    'objLayout.ShowPlotStyles = True
    'objLayout.PlotType = acView
    'objLayout.ViewToPlot = "plotview"
    
    'objPlotConfig.ViewToPlot = "plotview"
    
    ' Refresh the current plot information for this session.
    objLayout.RefreshPlotDeviceInfo
    objPlotConfig.RefreshPlotDeviceInfo
    'objLayout.Block
    'Dim layname(0) As String
    'layname(0) = objLayout.Name
    'Dim LayoutName As Variant
    'LayoutName = layname
    'objPlot.SetLayoutsToPlot LayoutName
    objPlot.DisplayPlotPreview acFullPreview    ' show it all
    Me.Show

    
    ' Plot it based upon their choice of device or file
    If frmDeviceChoice.Tag = "File" Then
        If Len(edFileName.Text) > 0 Then
            objPlot.PlotToFile edFileName.Text
        Else
            MsgBox "No filename was supplied for plotting to file choice. " & _
                    "Plotting to Drawing.plt in the working directory.", , "Error"
            objPlot.PlotToFile "Drawing.plt"
        End If
    Else
        objPlot.PlotToDevice
    End If
   
    Me.MousePointer = fmMousePointerDefault
    Me.Show

End Sub

Private Sub btnPlot_Click()
    
    Me.MousePointer = fmMousePointerHourGlass
    
    btnPlotwithConfig.Enabled = False
    
    ' create a plot object to do the work
    Dim objPlot As AcadPlot
    Set objPlot = ThisDrawing.Plot
    
    ' Plot it based upon their choice of device or file and
    ' using no plot configuration (the default is the current layout settings)
    If frmDeviceChoice.Tag = "File" Then
        If Len(edFileName.Text) > 0 Then
            objPlot.PlotToFile edFileName.Text
        Else
            MsgBox "No filename was supplied for plotting to file choice. " & _
                    "Plotting to Drawing.plt in the working directory.", , "Error"
            objPlot.PlotToFile "Drawing.plt"
        End If
    Else
        objPlot.PlotToDevice
    End If
    
    Me.MousePointer = fmMousePointerDefault

End Sub

Private Sub btnPlotPreview_Click()
    Me.Hide
    ' create a plot object
    Dim objPlot As AcadPlot
    Set objPlot = ThisDrawing.Plot
    ' check the radio buttons to determine which preview to use
    If frmPlotPreview.Tag = "Full" Then
        objPlot.DisplayPlotPreview acFullPreview    ' show it all
    Else
        objPlot.DisplayPlotPreview acPartialPreview ' show a partial
    End If
    Me.Show

End Sub

Private Sub btnSetCurrent_Click()
' this routine does programmitically what the tabs do for changing layouts
    ' get the layouts collection
    Dim colLayouts As AcadLayouts
    Set colLayouts = ThisDrawing.Layouts
    ' get the layout
    Dim objLayout As AcadLayout
    Set objLayout = colLayouts(lstLayouts.Text)
    ' get the preferences object
    Dim objPref As AcadPreferences
    Set objPref = ThisDrawing.Application.Preferences
    ' set the active layout in the preferences object using the layout object
    objPref.Application.ActiveDocument.ActiveLayout = objLayout
End Sub

Private Sub cbPlotConfigs_Change()
        btnPlotwithConfig.Enabled = True
End Sub

Private Sub lstLayouts_DblClick(ByVal Cancel As MSForms.ReturnBoolean)
    btnSetCurrent_Click
End Sub


Private Sub rdDevice_Click()
    frmDeviceChoice.Tag = "Device"
    edFileName.Enabled = False
    'edFileName.BackColor = "Menu Bar"
    edFileName.BackColor = &H80000004
    btnBrowse.Enabled = False
    edFileName.Text = ""

End Sub

Private Sub rdFile_Click()
    frmDeviceChoice.Tag = "File"
    edFileName.Enabled = True
    edFileName.BackColor = &H80000005
    'edFileName.BackColor = "Window background"
    btnBrowse.Enabled = True
End Sub

Private Sub rdFullPreview_Click()
    frmPlotPreview.Tag = "Full"
End Sub

Private Sub rdPartialPreview_Click()
    frmPlotPreview.Tag = "Partial"
End Sub

Private Sub tvwProperties_NodeClick(ByVal Node As ComctlLib.Node)
' this routine shows how to use the Treenode to display information on a
' form
    
    ' show only the configuration name data in a message box when selected
    Dim strTxt As String
    ' load the selected nodes first 14 characters of its key
    strTxt = Mid(Node.Key, 1, 14)
    ' now check for the configuration name data
    Select Case strTxt
        Case "ConfigNameData"
            ' they selected it so lets process it
            ' is the current plotter configuration file not set to None?
            If Node.Text <> "None" Then
                ' then process it
                ' is it a PC file?
                If Mid(Node.Text, Len(Node.Text) - 3, 3) = ".pc" Then
                    ' then go get the path from preferences and tack it on
                    Dim strPltPath As String
                    Dim objPref As AcadPreferences
                    Set objPref = ThisDrawing.Application.Preferences
                    strPltPath = objPref.Files.PrinterConfigPath
                    MsgBox strPltPath & "\" & Node.Text, , "Configuration File name"
                Else
                    ' not a pc file and not None so it must be a system printer
                    MsgBox "Using the system printer configuration: " & Node.Text, , "Configuration File name"
                End If
            Else
                ' None is set so tell them
                MsgBox "No path\filename or system configuration present", , "Configuration File name"
            End If
    End Select

End Sub

Private Sub userForm_Initialize()
    ' This may take a while, so turn on the hourglass
    Me.MousePointer = fmMousePointerHourGlass
    
    Build_PlotTree  ' build the Treenode list on the form
        
    Build_Layouts   ' build the layout listbox on the form
    
    ' set defaults for the form controls
    rdFullPreview.Value = True
    edFileName.Enabled = False
    rdDevice.Value = True
    btnBrowse.Enabled = False
    btnPlotwithConfig.Enabled = False
    
    ' build the avaiklable plot styles and devices listbox control
    Call LoadPlotDevicesAndStyles
    
    ' And turn off the hourglass
    Me.MousePointer = fmMousePointerDefault
    
End Sub
Private Sub Build_Layouts()
    
    Dim LngI As Long
    Dim lngCurrentLayoutIdx As Long
    
    ' get the preferences object
    Dim objPref As AcadPreferences
    Set objPref = ThisDrawing.Application.Preferences
    
    ' get the active layout
    Dim objLayout As AcadLayout
    Dim LayoutName As String
    Set objLayout = objPref.Application.ActiveDocument.ActiveLayout
    LayoutName = objLayout.Name ' get the active layouts name

    ' now get all of the layout names in the document and populate the list box
    Dim colLayouts As AcadLayouts
    Set colLayouts = ThisDrawing.Layouts
    With lstLayouts
        For LngI = 0 To colLayouts.Count - 1
            .AddItem colLayouts.Item(LngI).Name
            ' store the index setting for the active layout name
            If LayoutName = colLayouts.Item(LngI).Name Then
                lngCurrentLayoutIdx = LngI
            End If
        Next LngI
        ' select the active layout name listbox item
        .Selected(lngCurrentLayoutIdx) = True
    End With
    
    ' default to the selected layout list for the plot configuration list
    If lstPlotConfigurationObjects.ListIndex >= lngCurrentLayoutIdx Then
        lstPlotConfigurationObjects.Selected(lngCurrentLayoutIdx) = True
    End If

End Sub
Private Sub Build_PlotTree()
    ' This may take a while, so turn on the hourglass
    Me.MousePointer = fmMousePointerHourGlass
    
    ' setup - get the plot configuration collection and objects
    With ThisDrawing
        Dim colPltCfgs As AcadPlotConfigurations
        ' set a pltcfgs colloection object with all of this drawing's plot
        ' configurations
        Set colPltCfgs = .PlotConfigurations
        ' create a plot configuration object to work with later
        Dim objPltCfg As AcadPlotConfiguration
        Dim lngPltcnt As Long, LngI As Long
        ' load the number of plot confiurations in the drawing into the counter
        lngPltcnt = colPltCfgs.Count
        ' set the global plotting file path
        strPrintSpoolerPath = .Application.Preferences.Files.PrintSpoolerPath
    End With
    
    ' When we open the form, load the treeview of plot configurations
    ' and their properties
    
    Dim nodRoot As Node
    Dim nodConfigName As Node
    Dim nodConfigNameData As Node
    Dim nodPaperUnits As Node
    Dim nodPaperUnitsData As Node
    Dim nodPlotWithPlotStyles As Node
    Dim nodPlotWithPlotStylesData As Node
    Dim nodShowPlotStyles As Node
    Dim nodShowPlotStylesData As Node
    Dim nodStyleSheet As Node
    Dim nodStyleSheetData As Node
    Dim nodCanonicalMedia As Node
    Dim nodCanonicalMediaData As Node
    Dim nodPlotRotation As Node
    Dim nodPlotRotationData As Node
    
    ' Set the ImageList for the TreeView and ListView
    ' There's a UserForm bug that forces us to do this in code
    Set tvwProperties.ImageList = imgEnt
    Set lvwProperties.SmallIcons = imgEnt
    
    ' start at the beginning and spin through to the end of all of the
    ' plot configurations in the drawing
    For LngI = 0 To lngPltcnt - 1
        ' set the plot configuration object with a plot configuration
        ' from the collection
        Set objPltCfg = colPltCfgs(LngI)
        
        ' load the treelist control
        With tvwProperties
            ' set the root node
            Set nodRoot = .Nodes.Add(, , "Root" & LngI, objPltCfg.Name, conImagePlotCfg)
            
            ' set a child property node of the root node
            Set nodConfigName = .Nodes.Add(nodRoot, tvwChild, _
             "ConfigName" & LngI, "ConfigName", conImageProperties)
            ' set the data child node of the child property node
            Set nodConfigNameData = .Nodes.Add(nodConfigName, tvwChild, _
             "ConfigNameData" & LngI, "" & objPltCfg.ConfigName, conImagePropertyData)

            ' set a child property node of the root node
            Set nodCanonicalMedia = .Nodes.Add(nodRoot, tvwChild, _
             "CanonicalMedia" & LngI, "CanonicalMedia", conImageProperties)
            ' set the data child node of the child property node
            Set nodCanonicalMediaData = .Nodes.Add(nodCanonicalMedia, tvwChild, _
             "CanonicalMediaData" & LngI, "" & objPltCfg.CanonicalMediaName, conImagePropertyData)
            
            ' set a child property node of the root node
            Set nodPaperUnits = .Nodes.Add(nodRoot, tvwChild, _
             "PaperUnits" & LngI, "PaperUnits", conImageProperties)
            ' set the data child node of the child property node
            Set nodPaperUnitsData = .Nodes.Add(nodPaperUnits, tvwChild, _
             "PaperUnitsData" & LngI, "" & objPltCfg.PaperUnits, conImagePropertyData)
            
            ' set a child property node of the root node
            Set nodPlotRotation = .Nodes.Add(nodRoot, tvwChild, _
             "PlotRotation" & LngI, "PlotRotation", conImageProperties)
            ' set the data child node of the child property node
            Set nodPlotRotationData = .Nodes.Add(nodPlotRotation, tvwChild, _
             "PlotRotationData" & LngI, "" & objPltCfg.PlotRotation, conImagePropertyData)
            
            ' set a child property node of the root node
            Set nodPlotWithPlotStyles = .Nodes.Add(nodRoot, tvwChild, _
             "PlotWithPlotStyles" & LngI, "PlotWithPlotStyles", conImageProperties)
            ' set the data child node of the child property node
            Set nodPlotWithPlotStylesData = .Nodes.Add(nodPlotWithPlotStyles, tvwChild, _
             "PlotWithPlotStylesData" & LngI, "" & objPltCfg.PlotWithPlotStyles, conImagePropertyData)
            
            ' set a child property node of the root node
            Set nodShowPlotStyles = .Nodes.Add(nodRoot, tvwChild, _
             "ShowPlotStyles" & LngI, "Show Plot Styles", conImageProperties)
            ' set the data child node of the child property node
            Set nodShowPlotStylesData = .Nodes.Add(nodShowPlotStyles, tvwChild, _
             "ShowPlotStylesData" & LngI, "" & objPltCfg.ShowPlotStyles, conImagePropertyData)
            
            ' set a child property node of the root node
            Set nodStyleSheet = .Nodes.Add(nodRoot, tvwChild, _
             "StyleSheet" & LngI, "Style Sheet", conImageProperties)
            ' set the data child node of the child property node
            Set nodStyleSheetData = .Nodes.Add(nodStyleSheet, tvwChild, _
             "StyleSheetData" & LngI, "" & objPltCfg.StyleSheet, conImagePropertyData)
        End With
        
        ' load the listbox with just the config names
        With lstPlotConfigurationObjects
            .AddItem objPltCfg.ConfigName
        End With
        
        ' Load the plot congiration pop list on the Test Plot Object page
        With cbPlotConfigs
            .AddItem objPltCfg.Name
        End With
    Next LngI
    
    Me.MousePointer = fmMousePointerDefault

End Sub
