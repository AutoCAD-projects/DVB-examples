Attribute VB_Name = "EventHandler"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Implements IAcSmEvents

Private Sub IAcSmEvents_OnChanged(ByVal ev As AcSmEvent, ByVal comp As IAcSmPersist)
     ThisDrawing.Utility.Prompt (comp.GetTypeName & "  Modified!!!  " & vbCrLf)
End Sub

Attribute VB_Name = "SheetSet"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
Dim sheetCount As Integer
Dim sheetSetMgr As IAcSmSheetSetMgr
Dim sheetset As IAcSmSheetSet
Dim sheetdb As IAcSmDatabase
Dim eventHndlr As EventHandler
Dim eventSSMCookie As Long
Dim eventDbCookie As Long
Dim eventSSetCookie As Long
Dim dwtLayoutref As New AcSmAcDbLayoutReference 'default DWT
Dim fileRef As New AcSmFileReference 'default sheet location
Function isInitialized() As Boolean
    If sheetSetMgr Is Nothing Then
        ThisDrawing.Utility.Prompt "Sheetset manager not initialized!!"
        isInitialized = False
    End If
    
    If sheetset Is Nothing Then
        ThisDrawing.Utility.Prompt "Sheetset not initialized!!"
        isInitialized = False
    End If
    
    If sheetdb Is Nothing Then
        ThisDrawing.Utility.Prompt "Sheetset database not initialized!!"
        isInitialized = False
    End If
    
    isInitialized = True
End Function

Public Sub CreateSheetSet(name As String, _
                         path As String, _
                         desc As String, _
                         Optional dwtName As String = "", _
                         Optional dwtPath As String = "", _
                         Optional defaultSheetLoc As String = "")
    
    On Error Resume Next
    'Release previous db and sheet set
    Set sheetdb = Nothing
    Set sheetset = Nothing
    
    Dim fullPath As String
    Dim pos As Integer
    
    pos = Len(path)

    'check to see if user entered '\' for path at the end of the string
    'if not, append it
    If InStr(pos - 1, path, "\") = pos Then
        fullPath = path & name & ".dst"
    Else
        fullPath = path & "\" & name & ".dst"
    End If
     
    
    'Create a new database overwriting existing sheetset file
     Set sheetdb = sheetSetMgr.CreateDatabase(fullPath, "", True)
     
     'Lock the database before doing any operation on it
    Call LockDatabase
    
    'Get the sheet set from the database
    Set sheetset = sheetdb.GetSheetSet
    
     'Set name and description
    sheetset.SetName name
    sheetset.SetDesc "This is my sheet set " & name & ".dst"
    
    If Len(dwtPath) > 0 Then
        Set dwtLayoutref = New AcSmAcDbLayoutReference
        dwtLayoutref.InitNew sheetset
        dwtLayoutref.SetName dwtName
        dwtLayoutref.SetFileName dwtPath + "\" + dwtName
        dwtLayoutref.SetName "Sheet"
        
        'Set default dwg template
        sheetset.SetDefDwtLayout dwtLayoutref
     End If
     
    If Len(defaultSheetLoc) > 0 Then
        Set fileRef = New AcSmFileReference
        fileRef.InitNew sheetset
        fileRef.SetFileName (defaultSheetLoc)
        
        'set default sheet location
        sheetset.SetNewSheetLocation fileRef
    End If
     
    'Unlock database
    Call UnlockDatabase
    
    ThisDrawing.Utility.Prompt ("New sheet set " & fullPath & " created")
    ThisDrawing.Application.Update
                         
End Sub
                         
                         
Function AddSheet(parentCategory As IAcSmSubset, _
                  sheetName As String, _
                  sheetDesc As String, _
                  Optional layoutName As String = "", _
                  Optional layoutDWGPath As String = "") As IAcSmSheet
                  
    On Error Resume Next
    
    Dim newSheet As AcSmSheet
    
    If isInitialized = False Then
        Exit Function
    End If
    
    'Lock the database first
    LockDatabase
    
    If parentCategory Is Nothing Then
     'category to insert is the sheet set root
     Set parentCategory = sheetset
    End If
    
    If layoutName = "" Then
      If sheetset.GetDefDwtLayout Is Nothing Or sheetset.GetNewSheetLocation Is Nothing Then
        ThisDrawing.Utility.Prompt "Cannot add sheet :" & sheetName & vbCrLf
        ThisDrawing.Application.Update
        Exit Function
      Else
        'Create a fresh sheet
        Set newSheet = parentCategory.AddNewSheet(sheetName, sheetDesc)
        newSheet.SetTitle sheetName
        ' Now insert the sheet
        parentCategory.InsertComponent newSheet, Nothing
      End If
    Else
        'Create a sheet based on a layout
        Dim layoutRef As New AcSmAcDbLayoutReference
        
        layoutRef.InitNew sheetset
        
        'Set layout name and file name
        layoutRef.SetName layoutName
        layoutRef.SetFileName layoutDWGPath
        
        'Import a sheet based on a layout into the category
        Set newSheet = parentCategory.ImportSheet(layoutRef)
        
        'Now insert the sheet
        parentCategory.InsertComponent newSheet, Nothing
      
    End If
    
    'Increment sheet number
    sheetCount = sheetCount + 1
    
    'Give the new sheet a number based on sheet count
    newSheet.SetNumber sheetCount
    
    'Unlock database
    UnlockDatabase
    
    'retrun new sheet
   Set AddSheet = newSheet
    
End Function

Public Sub LockDatabase()
    On Error Resume Next
    If isInitialized = False Then
        Exit Sub
    End If
    Dim lockStatus As AcSmLockStatus
    Let lockStatus = sheetdb.GetLockStatus

    If lockStatus = AcSmLockStatus_UnLocked Then
      sheetdb.LockDb sheetdb
    End If
    
End Sub

Public Sub UnlockDatabase()
    On Error Resume Next
    If isInitialized = False Then
        Exit Sub
    End If
    Dim lockStatus As AcSmLockStatus
    If lockStatus = AcSmLockStatus_Locked_Local Or AcSmLockStatus_Locked_Remote Then
      sheetdb.UnlockDb sheetdb
    End If
End Sub

Function AddSheetCategory(name As String, _
                          desc As String, _
                          parentCat As IAcSmSubset) As IAcSmSubset
                           
    On Error Resume Next
    
    If isInitialized = False Then
        Exit Function
    End If
    
    Dim newCat As AcSmSubset
    
    If parentCat Is Nothing Then
     'parent category is the sheet set root
     Set parentCat = sheetset
    End If
    
    'Lock database before we add a category
    LockDatabase
    Set newCat = parentCat.CreateSubset(name, desc)
    'Unlock database
    UnlockDatabase
    
    'return the newly created category
    Set AddSheetCategory = newCat
    
End Function
' List all sheets and categories at the command line
Public Sub List(db As IAcSmDatabase)
    
    On Error Resume Next
    
    Dim iter As IAcSmEnumPersist
    Dim Item As IAcSmPersist
    Dim sheet As IAcSmSheet
    Dim subset As IAcSmSubset
    Dim cpbag As AcSmCustomPropertyBag
    Dim name As String
    Dim desc As String
    Dim value As String
    
    Set iter = db.GetEnumerator
    Set Item = iter.Next
    
    Do While Not Item Is Nothing
        Set sheet = Item
        Set subset = Item
        Set cpbag = Item
        
        'If Not subset Is Nothing Then
        If Item.GetTypeName = "AcSmSubset" Then
            'list the category (subset)
            name = subset.GetName
            desc = subset.GetDesc
            ThisDrawing.Utility.Prompt ("-------------------------------" & vbCrLf)
            ThisDrawing.Utility.Prompt ("SubSet Name :" & name & vbCrLf)
            ThisDrawing.Utility.Prompt ("SubSet Desc :" & desc & vbCrLf)
            ThisDrawing.Utility.Prompt ("-------------------------------" & vbCrLf)
            
        'ElseIf Not sheet Is Nothing Then
        ElseIf Item.GetTypeName = "AcSmSheet" Then
            'list the sheet
            name = sheet.GetName
            desc = sheet.GetDesc
            ThisDrawing.Utility.Prompt ("sheet Name :" & name & vbCrLf)
            ThisDrawing.Utility.Prompt ("sheet Desc :" & desc & vbCrLf)
        
        ElseIf Item.GetTypeName = "AcSmCustomPropertyBag" Then
        
            'Iterate through custom properties
             Dim propIter As IAcSmEnumProperty
             Set propIter = cpbag.GetPropertyEnumerator
            
            Dim propName As String
            Dim propval As AcSmCustomPropertyValue
            Do While True
                Set propval = Nothing
                propName = ""
                propIter.Next name, propval
                If propName = "" Then Exit Do 'jump out of loop
        
                If Not IsEmpty(propval) And Not IsObject(propval) Then
                    ThisDrawing.Utility.Prompt ("Property  " & propName & " : " & propval.GetValue & " " & vbCrLf)
                End If
            Loop
            End If
        
        Set Item = iter.Next
    Loop

    ThisDrawing.Application.Update
    
End Sub
Public Sub AddCalloutBlock(blockname As String, _
                            dwg As String)
                            
    On Error Resume Next
    If isInitialized = False Then
        Exit Sub
    End If
    
    LockDatabase
    Dim calloutBlocks As IAcSmCalloutBlocks
    Dim calloutRef As New AcSmAcDbBlockRecordReference

    Set calloutBlocks = sheetset.GetCalloutBlocks

    calloutRef.InitNew sheetdb
    calloutRef.SetFileName dwg
    calloutRef.SetName blockname
    
    calloutBlocks.Add calloutRef
    UnlockDatabase
    
End Sub

Public Sub AddLabelBlock(blockname As String, _
                            dwg As String)

    On Error Resume Next
    
    If isInitialized = False Then
        Exit Sub
    End If
    
    LockDatabase
    
    Dim labelRef As New AcSmAcDbLayoutReference
    labelRef.InitNew sheetdb
    labelRef.SetFileName dwg
    labelRef.SetName blockname
    
    sheetset.SetDefLabelBlk labelRef
    UnlockDatabase
End Sub

Public Sub AddResourceFileLocation(resource As String)
    On Error Resume Next
    
    If isInitialized = False Then
        Exit Sub
    End If
    
    LockDatabase
    Dim resources As IAcSmResources
    Dim fileRef As New AcSmFileReference

    Set resources = sheetset.GetResources
    fileRef.InitNew sheetdb
    fileRef.SetFileName resource
    
    resources.Add fileRef
    UnlockDatabase
End Sub
Function AddSheetSelectionSet(name As String, _
                               desc As String) As IAcSmSheetSelSet

    On Error Resume Next
    
    If isInitialized = False Then
        Exit Function
    End If
    
    'lock database
    LockDatabase

    Dim sheetSelSets As IAcSmSheetSelSets
    Dim sheetSelSet As IAcSmSheetSelSet
    Set sheetSelSets = sheetset.GetSheetSelSets

    sheetSelSets.Add name, desc, sheetSelSet

    'unlock database
    UnlockDatabase

    'return the selection set
    Set AddSheetSelectionSet = sheetSelSet
    
End Function
                            
Public Sub AddCustomProperty(key As String, _
                              value As String, _
                              comp As IAcSmComponent, _
                              propFlags As PropertyFlags)
    On Error Resume Next
    
    If isInitialized = False Then
        Exit Sub
    End If
    
    LockDatabase
    
    Dim bag As IAcSmCustomPropertyBag
    If comp Is Nothing Then
        Set comp = sheetset
    End If
    
    Set bag = comp.GetCustomPropertyBag
    
    Dim propval As New AcSmCustomPropertyValue
    propval.InitNew bag
    
    propval.SetFlags propFlags
    propval.SetValue value
    
    bag.SetProperty key, propval
    
    UnlockDatabase
End Sub
Public Sub NotifyStart()
    
    On Error Resume Next
    
    If isInitialized = False Then
        Exit Sub
    End If
    
    If Not eventHndlr Is Nothing Then
        Exit Sub
    End If
    
    Set eventHndlr = New EventHandler
    'register for sheet set manager events
    Let eventSSMCookie = sheetSetMgr.Register(eventHndlr)
    
     'register database events
    Let eventDbCookie = sheetdb.Register(eventHndlr)
     
     'register for sheet set events
    Let eventSSetCookie = sheetset.Register(eventHndlr)
    
End Sub
Public Sub NotifyEnd()
    On Error Resume Next
    If isInitialized = False Then
        Exit Sub
    End If
    
    sheetSetMgr.Unregister eventSSMCookie
    sheetdb.Unregister eventDbCookie
    sheetset.Unregister eventSSetCookie
    
    Set eventHndlr = Nothing
End Sub
Function GetSheetSet() As IAcSmSheetSet
    Set GetSheetSet = sheetset
End Function

Public Sub CleanUp(error As String)
    On Error Resume Next
    If sheetdb Is Nothing Then
        Exit Sub
    End If
    
    ThisDrawing.Utility.Prompt error & vbCrLf
    
    Dim lockStat As AcSmLockStatus
    Set lockStat = sheetdb.GetLockStatus
    If lockStat = AcSmLockStatus_Locked_Local Or AcSmLockStatus_Locked_Remote Then
        sheetdb.UnlockDb sheetdb
        Set sheetdb = Nothing
        Set sheetset = Nothing
        Set sheetSetMgr = Nothing
        Set eventHndlr = Nothing
        Set dwtLayoutref = Nothing
        Set fileRef = Nothing
    End If

End Sub
                           
Private Sub Class_Initialize()
    On Error Resume Next
    sheetCount = 0
    'Get the sheet set manager
    Set sheetSetMgr = New AcSmSheetSetMgr
End Sub

Private Sub Class_Terminate()
 On Error Resume Next
 Set sheetdb = Nothing
 Set sheetset = Nothing
 Set sheetSetMgr = Nothing
 Set eventHndlr = Nothing
 Set dwtLayoutref = Nothing
 Set fileRef = Nothing
End Sub

Attribute VB_Name = "ThisDrawing"
Attribute VB_Base = "0{8E75D913-3D21-11D2-85C4-080009A0C626}"
Attribute VB_GlobalNameSpace = False
Attribute VB_Creatable = False
Attribute VB_PredeclaredId = True
Attribute VB_Exposed = True
Attribute VB_TemplateDerived = False
Attribute VB_Customizable = True
Option Explicit
'This example creates a new sheet set and add sheets
Sub Example_SSC()

     Dim sheetset As New sheetset
     On Error Resume Next
     
     Dim sheet1 As IAcSmComponent
     Dim sheet2 As IAcSmComponent
     Dim sheet3 As IAcSmComponent
     Dim sheet4 As IAcSmComponent
     Dim categoryX As IAcSmComponent
     Dim categoryXX As IAcSmComponent
     
     Dim sheetSetName As String
     Dim dwtPath As String
     Dim defSheetLoc As String
     Dim path As String
    
     'This is the path where sheet1, sheet2 and sheet3 drawings are stored
     Dim sampleRootPath As String
     sampleRootPath = ThisDrawing.Application.path & "\Sample\ActiveX\SheetSetVBA"
     
     Dim resourcePath As String
     resourcePath = sampleRootPath
     
     'Set the default sheet location same as resource path
     defSheetLoc = sampleRootPath
     
     'set the location to dwt for the sheet set
     dwtPath = sampleRootPath

    'Get the name for the sheet set from the user
    Dim NoNull As Integer
    NoNull = 1    ' Disallow null
    ThisDrawing.Utility.InitializeUserInput NoNull
    sheetSetName = ThisDrawing.Utility.GetString(False, _
                                        "Enter the name of the sheet set(extension not needed): ")
    
    'Get the path where sheet set will be created
    Dim oShell As Shell32.Shell
    Dim oFolder As Shell32.Folder
    Dim oItems As Shell32.FolderItems
    Dim Item As Shell32.FolderItem

    Set oShell = New Shell ' ActiveX interface to shell32.dll
    Set oFolder = oShell.BrowseForFolder(0, "Select a path ", 0)
    If oFolder Is Nothing Then
      MsgBox "Path not selected... Exiting!!"
      GoTo CleanUp
    End If
    
    Set oItems = oFolder.Items
    Set Item = oItems.Item

    path = Item.path
    
   'Create a new sheet set
   sheetset.CreateSheetSet sheetSetName, _
                           path, _
                           "This is my VBA sheet set", _
                           "IRD.dwt", _
                           dwtPath, _
                           defSheetLoc
    
    'Exit if sheet set not created
    If sheetset.GetSheetSet Is Nothing Then
        MsgBox "Cannot create sheetset...Exiting!!"
        GoTo CleanUp
    End If
    
    
    'start notifications
     sheetset.NotifyStart
    
    'Add custom properties at sheet set level
    sheetset.AddCustomProperty "Custom Property 1", "XXXX", Nothing, CUSTOM_SHEETSET_PROP
    sheetset.AddCustomProperty "Custom Property 2", "YYYY", Nothing, CUSTOM_SHEETSET_PROP
    
    'Add resource file location
    sheetset.AddResourceFileLocation resourcePath
    
    'Add label block
    sheetset.AddLabelBlock "Label", resourcePath + "\" + "Label Block.dwg"
    
    'Add callout blocks
    sheetset.AddCalloutBlock "Right", resourcePath + "\" + "Pointer Blocks.dwg"
    sheetset.AddCalloutBlock "Left", resourcePath + "\" + "Pointer Blocks.dwg"
    sheetset.AddCalloutBlock "Up", resourcePath + "\" + "Pointer Blocks.dwg"
    sheetset.AddCalloutBlock "Down", resourcePath + "\" + "Pointer Blocks.dwg"
    
                           
    'Add a category "category X" to sheet set root
   Set categoryX = sheetset.AddSheetCategory("Category X", _
                                             "This is category X", _
                                             Nothing) 'parent is sheet set root
    
    'Add a nested category under "category X"
    Set categoryXX = sheetset.AddSheetCategory("Nested Category XX", _
                                             "This is nested category XX", _
                                             categoryX) 'parent is categoryX
                                             
                           
   'Add  sheet 1 to sheet set root
   Set sheet1 = sheetset.AddSheet(Nothing, _
                                  "Sheet 1", _
                                  "This is sheet1", _
                                  "Sheet 1", _
                                  resourcePath + "\" + "sheet1.dwg")
                                  
  'Add custom property for sheet 1

  sheetset.AddCustomProperty "ABCD", "####", sheet1, CUSTOM_SHEET_PROP

  'Add sheet2 based on a layout to category "category X"
  Set sheet2 = sheetset.AddSheet(categoryX, _
                                  "Sheet 2", _
                                  "This is sheet2", _
                                  "Sheet 2", _
                                  resourcePath + "\" + "sheet2.dwg")


  'Add sheet3 based on a layout to nested category "category XX"
  Set sheet3 = sheetset.AddSheet(categoryXX, _
                                  "Sheet 3", _
                                  "This is sheet3", _
                                  "Sheet 3", _
                                  resourcePath + "\" + "sheet3.dwg")
                     
    ' Add a fresh sheet4 not based on any layout
    
    Set sheet4 = sheetset.AddSheet(Nothing, _
                                   "Fresh Sheet", _
                                   "This is a fresh sheet")
    'Add selection set
    Dim selset As IAcSmSheetSelSet
    Set selset = sheetset.AddSheetSelectionSet("My Selection Set", "This is my selection set")
    
    sheetset.LockDatabase
    selset.Add sheet1
    selset.Add sheet2
    selset.Add sheet3
    sheetset.UnlockDatabase
    
    'end notifications
    sheetset.NotifyEnd
    
    ThisDrawing.Application.Update
    
CleanUp:
    Set oShell = Nothing
    Set oFolder = Nothing
    Set oItems = Nothing
    Set Item = Nothing
End Sub


                  
'This example lists all sheet sets
Sub Example_SSListAll()

    Dim sheetset As New sheetset
    ' Get the sheet set manager
    Dim ssMgr As New AcSmSheetSetMgr
    Dim dbIter As IAcSmEnumDatabase
    Dim db As IAcSmDatabase
    
    Set dbIter = ssMgr.GetDatabaseEnumerator
    
    Set db = dbIter.Next
    Do While Not db Is Nothing
        ThisDrawing.Utility.Prompt ("----------BEGIN------------" & vbCrLf)
        sheetset.List db
        Set db = Nothing
        Set db = dbIter.Next
        ThisDrawing.Utility.Prompt ("---------- END ------------" & vbCrLf)
    Loop
    
    Set dbIter = Nothing
    Set ssMgr = Nothing
    
    ThisDrawing.Application.Update

End Sub
